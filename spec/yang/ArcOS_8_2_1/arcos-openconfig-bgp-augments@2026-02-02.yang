module arcos-openconfig-bgp-augments {
  yang-version 1.1;
  namespace "http://yang.arrcus.com/arcos/openconfig/bgp/augments";
  prefix arc-oc-bgp-aug;

  import openconfig-bgp {
    prefix oc-bgp;
  }
  import openconfig-bgp-types {
    prefix oc-bgp-types;
  }

  import arcos-openconfig-bgp-types {
    prefix arc-oc-bgp-types;
  }

  import openconfig-yang-types {
    prefix oc-yang;
  }

  import ietf-yang-types {
    prefix yang;
  }

  import ietf-inet-types {
    prefix inet;
  }

  import openconfig-inet-types {
    prefix oc-inet;
  }

  import arcos-bgp-auto-peer-group {
    prefix arc-bgp-auto-peer-grp;
  }

  import arcos-bgp-rnh {
    prefix arc-bgp-rnh;
  }

  import openconfig-policy-types {
    prefix "oc-pol-types";
  }

  import openconfig-routing-policy {
    prefix oc-rpol;
  }

  import openconfig-network-instance {
    prefix oc-netinst;
  }

  import openconfig-mpls {
    prefix oc-mpls;
  }

  import openconfig-network-instance-types {
    prefix oc-netinst-types;
  }

  import arcos-openconfig-network-instance-types {
    prefix arc-oc-ni-types;
  }

  import openconfig-interfaces {
    prefix oc-if;
  }

  import arcos-bgp-types {
    prefix arc-bgp-types;
  }

  import arcos-openconfig-policy-types {
    prefix arc-oc-pol-types;
  }

  import arcos-srv6 {
    prefix arc-srv6;
  }

  import arcos-srv6-types {
    prefix arc-srv6-types;
  }

  import arcos-oam {
    prefix arc-oam;
  }

  import openconfig-bfd {
    prefix oc-bfd;
  }

  import arcos-features {
    prefix arc-features;
  }

  import openconfig-packet-match {
    prefix oc-match;
  }

  import arcos-evpn {
    prefix arc-evpn;
  }

  organization
    "Arrcus, Inc.";

  contact
    "Arrcus, Inc.
     2077 Gateway Place
     Suite 400
     San Jose, CA 95110
     E-mail: yang-support@arrcus.com";

  description
    "This module defines augmentation for Arrcus
     implementation of the openconfig BGP module.

     Copyright (c) 2016-2024 by Arrcus, Inc.
     All rights reserved.";

  revision 2026-02-02 {
    description
      "Fixing nbr-af-state issue and moving it to nbr-state-top";
  }

  revision 2026-01-27 {
    description
      "Add debugging counters for AF context revival tracking:
       - af-ctx-state: AF context object state visibility
       - af-ctx-flags: AF context object flags
       - revival-count: Track CLEANUP_WAIT revivals
       - nbr-af-state: Neighbor AF object state visibility
       - nbr-af-flags: Neighbor AF object flags";
  }

  revision 2025-07-17 {
    description "Enabling afi-safi-timer-config for all address family.";
  }

  revision 2025-04-28 {
    description "Adding global afi-safi-mup-timer-config.";
  }

  revision 2025-01-22 {
    description
      "Add State attribute for TCP MSS negotiated with neighbor";
  }

  revision 2025-01-10 {
    description "Adding global adj-rib-out-post control.";
  }

  revision 2025-01-10 {
    description "Add BGP EVPN commands for asymetric IRB feature:
                 evpn-route-options suppress-rt5-routes
                 rib-install use-l2-label-for-evpn-rt2-route";
  }

  revision 2024-08-23 {
    description "Make BGP l2 domain name leafref of NI domain name.";
  }
  
  revision 2024-08-22 {
    description
      "Adding support to display RTR (RPKI) cache entries";
  }

  revision 2024-08-02 {
    description
      "Expanding inbound-soft-reconfiguation config to all afi-safis";
  }

  revision 2024-07-17 {
    description
      "Adding BGP counters to all-neighbor";
  }

  revision 2024-07-09 {
    description
      "Adding display of additional counters";
  }

  revision 2024-06-17 {
    description
      "* Re-organize the auto-peer-group container hierarchy
       * Add counters for AF level next-hops";
  }

  revision 2024-05-18 {
    description
      "* Replace resolve ST1 interwork by resolve ST1 sid configuration.
       * Add resolve ST2 sid configuration.";
  }

  revision 2024-05-09 {
    description "Adding rtfilter support for MUP SAFI.";
  }

  revision 2024-03-26 {
    description
      "Add Data Center Interconnect (DCI) configuration
       * Add domain configuration
       * Add route-distinguisher and route-target configuration under domain";
  }

  revision 2024-03-05 {
    description
      "Support Drop Upon invalid SR Policy for BGP routes.";
  }

  revision 2024-02-29 {
    description
      "* Remove obsolete MUP interwork entry configuration.
       * Remplace segment DIRECT entry with segment DIRECT address.";
  }

  revision 2024-02-22 {
    description
      "Restrict the route-target and apply-policy for supported AFI/SAFIs";
  }

  revision 2024-02-15 {
    description
      "EVPN-VPWS Interface State-Machine operational data";
  }

  revision 2023-12-20 {
    description
      "* Add MUP interwork source configuration to support N6 ISD origination.
       * Allow both DIRECT and INTERWORK segment from the same network-instance.";
  }

  revision 2023-12-19 {
    description
      "RT afi-safi export policy for MUP usage correction";
  }

  revision 2023-12-10 {
    description
      "Add local address configuration for rtr server";
  }

  revision 2023-11-25 {
    description
      "Remove unsupported SR-TE based SRv6 MUP configuration";
  }

  revision 2023-11-19 {
    description
      "Add suppression of source address for MUP (ST1) path";
  }

  revision 2023-10-14 {
    description
      "Add RT afi-safi export policy for MUP";
  }

  revision 2023-10-11 {
    description
      "Add counters for EVPN type-1, type-2, type-4 routes at AFI/SAFI level";
  }

  revision 2023-08-10 {
    description
      "Add evpn vpws config under global L2VPN_EVPN";
  }

  revision 2023-08-07 {
    description
      "Adding unique for decapsulation locator and function configuration.";
  }

  revision 2023-08-03 {
    description
      "Add silent-drop knob to control silent dropping of
       BGP packets using control plane ACL";
  }

  revision 2023-06-14 {
    description
      "Changing mup-segment config model";
  }

  revision 2023-06-09 {
    description
      "Adding interwork resolve config under mup address family";
  }

  revision 2023-06-05 {
    description
      "Added reoriginate MUP ST1 support.";
  }

  revision 2023-06-02 {
    description
      "Move the MUP segment configuration to AFI/SAFI
       specific container";
  }

  revision 2023-06-01 {
    description
      "Add AF level ILM statistics.";
  }

  revision 2023-05-10 {
    description
      "Add new NBR AF counter (accepted) to indicate the
       number of paths accepted into BGP RIB after policy evaluation";
  }

  revision 2023-05-08 {
    description
      "Conditionally enable srv6 mobile features.";
  }
  
  revision 2023-05-04 {
    description
      "Add rib-validation knob for network command to control
       tracking of network prefix in RIB.";
  }

  revision 2023-04-27 {
    description
      "Added neighbor update-delay-time configuration";
  }

  revision "2023-04-15" {
    description
      "MPLS information in BGP";
  }

  revision 2023-04-03 {
    description
      "Added MUP resolve interwork configuration";
  }

  revision "2023-03-15" {
    description
      "Remove augment for segment-routing srgb";
  }

  revision 2023-02-19 {
    description
      "Use type identityref directly instead of leafref for afi-safi-name
       in all-neighbor, since all-neighbor represents only oper state.";
  }

  revision 2023-02-16 {
    description
      "RFC 8212 - Add mandate-ebgp-policy knob to influence
       default EBGP route propagation behavior without policies.";
  }

  revision 2023-01-23 {
    description
      "Updated to add support for multiple BFD profiles";
  }

  revision 2022-11-30 {
    description
      "Adding peer-as-range knob";
  }

  revision 2022-10-26 {
    description
      "Add state container for memory allocation counters
       at afi-safi level";
  }

  revision 2022-10-19 {
    description
      "Adding strict common afi-safi check knob for session formation";
  }

  revision 2022-10-05 {
    description
      "Added global compatibility suppress-nexthop-attribute setting
       to optionally suppress sending NEXT_HOP attribute in MP_REACH updates.";
  }

  revision 2022-08-10 {
      description "Added MUP SAFI support";
  }

  revision 2022-06-13 {
    description
      "* Add counters for configured and dynamic neighbors in
       shutdown and established state.
       * Change counters type from uint32 to gauge32 for global-neighbor-stats.";
  }

  revision 2022-04-19 {
    description
      "* Added auto-inbound-soft-reconfiguation to afi-safi oper state.";
  }

  revision 2022-03-16 {
    description
      "Adding accumulative and periodic counters
       for performance monitoring";
  }

  revision 2022-02-15 {
    description
      "* Unblock route-target command in model for L2P2P_EVPN network instance.
       * Add EVPN IMET label.";
  }

  revision 2018-08-14 {
    description
      "ArcOS release 2.2.1";
  }

  revision 2017-05-31 {
    description
      "Initial Revision
       * Add global/config/cluster-id.
       * Add global/state/cluster-id.
       * Add neighbor/add-paths/config/send.
       * Add neighbor/add-paths/state/send.
       * Add global/afi-safis/afi-safi/<AF>/networks.
       * Add global/afi-safis/afi-safi/state/versions.
       * Add global/afi-safis/afi-safi/state/total-route-reflector-clients.
       * Add neighbor/graceful-restart/state/restart-timer-expire and
         stale-routes-timer-expire
       * Add global/route-selection-options/config/selection-deferral-time.
       * Add global/route-selection-options/state/selection-deferral-time.
      ";

    reference
      "RFC 6020: YANG - A Data Modeling Language for the
       Network Configuration Protocol (NETCONF)";
  }

  grouping global-af-rib-install-state {
    leaf policy-runs {
      type yang:counter64;
      description
        "Number of times the rib-install policy was run";
    }

    leaf policy-passes {
      type yang:counter64;
      description
        "Number of times the rib-install policy resulted in a pass";
    }

    leaf policy-drops {
      type yang:counter64;
      description
        "Number of times the rib-install policy resulted in a drop";
    }

    leaf policy-qppb-updates {
      type yang:counter64;
      description
        "Number of times the rib-install policy updated QPPB parameters";
    }
  }

  grouping global-af-rib-install-config {
    leaf-list policy {
      type leafref {
        path "/oc-rpol:routing-policy/oc-rpol:policy-definitions/" +
             "oc-rpol:policy-definition/oc-rpol:name";
      }
      ordered-by user;
      max-elements 1;
      description
        "RPOL to filter or update paths installed into RIB.";
    }
    leaf use-l2-label-for-evpn-rt2-route {
      type boolean;
      description
        "Use L2 label for evpn type-2 routes when dowbnloading into RIB";
    }
  }

  grouping global-af-rib-install-top {
    container rib-install {
      description
        "RIB route installation parameters";

      container config {
        description
          "RIB installation configuration";

        uses global-af-rib-install-config;
      }

      container state {
        config false;

        description
          "RIB installation state";

        uses global-af-rib-install-config;
        uses global-af-rib-install-state;
      }
    }
  }

  grouping global-update-wait-data-plane-config {
    leaf update-wait-data-plane {
      type boolean;
      description
        "Defer BGP update generation till routes are installed in data plane";
    }
  }

  grouping route-target-retain-config {
    leaf retain-route-target-all {
      type boolean;
      description
        "Retain VPN routes with all route-targets";
    }
  }

  grouping global-disable-rib-config {
    leaf disable-rib-install {
      type boolean;
      description
        "Enable/Disable BGP route installation in RIB";
    }
  }

  grouping global-cluster-id-config {
    leaf cluster-id {
      type oc-yang:dotted-quad;
      description
        "route-reflector cluster id to use when local router is
        configured as a route reflector.  Commonly set at the group
        level, but allows a different cluster
        id to be set for each neighbor.";
    }
  }

  grouping global-shutdown-protocol-config {
    leaf shutdown-protocol {
      type boolean;
      description
        "Shutdown all BGP protocol";
    }
  }

  grouping global-shutdown-all-config {
    leaf shutdown-all-sessions {
      type boolean;
      description
        "Shutdown all BGP sessions";
    }
  }

  grouping global-mandate-ebgp-policy-config {
    leaf mandate-ebgp-policy {
      type boolean;
      default false;
      description
        "RFC 8212 - Default EBGP route propagation
        behavior without policies.
        When set to true, block EBGP routes without policy.
        When set to false, allow EBGP routes without policy.";
    }
  }

  grouping global-silent-drop-config {
    leaf silent-drop {
      type boolean;
      default false;
      description
        "Control silent dropping of BGP packets for using control plane ACL.
         When set to true, silently drop incoming BGP packets for unconfigured neighbors.
         When set to false, allow BGP packets for all neighbors.";
    }
  }

  grouping global-adj-rib-out-post-config {
    leaf adj-rib-out-post {
      type boolean;
      description
        "Enable/Disable keeping of adj-rib-out post export policy result.";
    }
  }

  grouping global-drop-upon-invalid-sr-policy-config {
    leaf drop-upon-invalid-sr-policy {
      type boolean;
      default false;
      description
        "Controls whether to use IGP Next Hop when a valid SR Policy Next Hop
        is not available";
    }
  }

  grouping global-update-gen-stats {
    leaf total-pending-updates {
      type uint32;
      description
        "Total number of outstanding update messages.";
    }
    leaf total-update-delays {
      type uint32;
      description
        "Total number of deplays due to too many outstanding updates.";
    }
  }

  grouping global-neighbor-stats {
    leaf total-configured-neighbors {
      type yang:gauge32;
      description
        "Total number of configured BGP neighbors.";
    }
    leaf total-established-neighbors {
      type yang:gauge32;
      description
        "Total number of established BGP neighbors.";
    }
    leaf total-dynamic-neighbor-prefixes {
      type yang:gauge32;
      description
        "Total number of configured BGP dynamic neighbor prefixes.";
    }
    leaf total-dynamic-neighbor-instances {
      type yang:gauge32;
      description
        "Total number of BGP dynamic neighbor instances.";
    }
    leaf established-configured-neighbors {
      type yang:gauge32;
      description
        "Number of established BGP neighbors.";
    }
    leaf established-dynamic-neighbors {
      type yang:gauge32;
      description
        "Number of established BGP dynamic neighbors.";
    }
    leaf shutdown-configured-neighbors {
      type yang:gauge32;
      description
        "Number of shutdown BGP neighbors.";
    }
    leaf shutdown-dynamic-neighbors {
      type yang:gauge32;
      description
        "Number of shutdown BGP dynamic neighbors.";
    }
  }

  grouping global-errors-group {
    container global-error-counts {
      description
        "Accumulated counts for various BGP processing errors";
  
      leaf total-netlink-local-address-errors {
        type uint64;
        description
          "Aggregate count of error messages in netlink local-addr handling area";
      }
      leaf total-netlink-duplicate-address-errors {
        type uint64;
        description
          "Aggregate count of error count for netlink updates with duplicate
           interface address";
      }
      leaf total-network-instance-errors {
        type uint64;
        description
          "Aggregate count of error messages in network instance (vrf) area";
      }
      leaf total-bufferevent-api-errors {
        type uint64;
        description
          "Aggregate count of error messages in APIs to bufferevent";
      }
      leaf total-socket-api-errors {
        type uint64;
        description
          "Aggregate count of error messages in APIs to socket/bind/sockopt";
      }
      leaf total-bfd-api-errors {
        type uint64;
        description
          "Aggregate count of error messages in APIs to BFD";
      }
    }
  }

  grouping selection-policy-config {
    leaf-list selection-policy {
      type leafref {
        path "/oc-rpol:routing-policy/oc-rpol:policy-definitions/" +
             "oc-rpol:policy-definition/oc-rpol:name";
      }
      ordered-by user;
      max-elements 1;
      description
        "RPOL to select eligible paths. Match/accept only.";
    }
  }

  grouping add-paths-select-config {
    leaf-list eligible-prefix-policy {
      type leafref {
        path "/oc-rpol:routing-policy/oc-rpol:policy-definitions/" +
             "oc-rpol:policy-definition/oc-rpol:name";
      }
      ordered-by user;
      max-elements 1;
      description
        "RPOL to select add-path eligible paths. Match/accept only.";
    }
  }

  grouping add-paths-calculate-config {
    leaf calculate {
      type identityref {
        base arc-oc-bgp-types:ADD_PATHS_OPTIONS;
      }
      description
        "To calculate specified options in best-path calculations. " +
        "ALL means calculating all available options.";
    }
  }

  grouping add-paths-install-config {
    leaf install-backup {
      type boolean;
      description
        "To install backup path in RIB.";
    }
  }

  grouping add-paths-options {
    container config {
      description
        "Network-instance afi-safi add-paths option configs";
      uses add-paths-select-config;
      uses add-paths-calculate-config;
      uses add-paths-install-config;
    }
    container state {
      config false;
      description
        "Network-instance afi-safi add-paths option states";
      uses add-paths-select-config;
      uses add-paths-calculate-config;
      uses add-paths-install-config;
    }
  }

  grouping global-add-paths-top {
    container add-paths {
      description
        "Network-instance afi-safi add-paths parameters";
      uses add-paths-options;
    }
  }

  grouping advertise-best-external-config {
    leaf advertise-best-external {
      type boolean;
      description
        "Advertise best-external path instead of best path";
    }
  }

  grouping srv6-oam-nexthop-health-config {
    leaf profile {
      type leafref {
        path "/arc-oam:oam/arc-oam:profiles/arc-oam:profile/arc-oam:name";
      }
      description
        "Track next-hop health status with OAM profile";
    }
    leaf-list selection-policy {
      when "../profile != ''" {
        description
          "Select alternate tracking profile based on next-hop";
      }
      type leafref {
        path "/oc-rpol:routing-policy/oc-rpol:policy-definitions/" +
          "oc-rpol:policy-definition/oc-rpol:name";
      }
      ordered-by user;
      max-elements 1;
    }
  }

  grouping srv6-oam-options {
    container config {
      description
        "Network-instance afi-safi srv6-oam option configs";
      uses srv6-oam-nexthop-health-config;
    }
    container state {
      config false;
      description
        "Network-instance afi-safi srv6-oam option states";
      uses srv6-oam-nexthop-health-config;
    }
  }

  grouping global-srv6-oam-top {
    container srv6-oam {
      description
        "Network-instance afi-safi srv6-oam parameters";
      uses srv6-oam-options;
    }
  }

  grouping hold-timer-expiration-state {
    leaf hold-timer-expire {
      type decimal64 {
        fraction-digits 2;
      }

      description
        "This timestamp indicates the time that the
        BGP session hold timer value.
        The value is time remaining in seconds.";
    }
  }

  grouping keepalive-timer-expiration-state {
    leaf keepalive-timer-expire {
      type decimal64 {
        fraction-digits 2;
      }

      description
        "This timestamp indicates the time that the
        BGP session keepalive timer value.
        The value is time remaining in seconds.";
    }
  }

  grouping remote-router-id-state {
    leaf remote-router-id {
      type oc-yang:dotted-quad;
      description
        "Remote Router id of the router - an unsigned 32-bit integer
        expressed in dotted quad notation.";
      reference
        "RFC4271 - A Border Gateway Protocol 4 (BGP-4),
        Section 4.2";
    }
  }

  grouping neighbor-bfd {
    leaf enable {
      type boolean;
      description
        "BFD Support for the neighbor.";
    }
    container strict {
      description
        "Parameters for bfd strict mode";
      leaf static {
        type boolean;
        description
          "BFD is mandatory for BGP neighbor peering. This implementation
           is a simplified version in that no bgp capability negotiation
           is needed. Hence named strict - static.";
      }
      reference
        "draft-merciaz-idr-bgp-bfd-strict-mode-02"; 
    }
    leaf profile {
      type leafref {
        path "/oc-bfd:bfd/oc-bfd:interfaces/oc-bfd:interface/oc-bfd:config" +
             "/oc-bfd:id";
      }
      description
        "A reference to the BFD profile.";
    }
  }

  grouping bfd-config {
    container config {
      description "Configuration data for BFD.";
      uses neighbor-bfd;
    }
  }

  grouping bfd-state {
    container state {
      config false;
      description "Operational data for BFD.";
      uses neighbor-bfd;
    }
  }

  grouping bfd-top {
    container bfd {
      description
        "Configuration parameters related to bfd";
      uses bfd-config;
      uses bfd-state;
    }
  }


  /*
   * Egress Peer Engineering augments.
   */
  grouping labeled-unicast-epe-common {
    leaf enable {
      type boolean;
      description
        "Enable/Disable BGP LU based Egress Traffic Engineering under the specified
        BGP neighbour.";
    }
  }
  grouping labeled-unicast-epe-config {
    container config {
      description "Configuration Information for BGP LU based Egress Traffic Engineering.";
      uses labeled-unicast-epe-common;
    }
  }

  grouping labeled-unicast-epe-next-hop-state {
    description
      "Grouping for BGP LU based Egress Traffic Engineering First-hop infomation.";

    list next-hop {
      key "ifindex";

      description
        "Egress TE Peer next-hop list.";

      leaf ifindex {
        type uint64;
        description
          "Interface index of the Egress-TE neighbor link";
      }

      leaf next-hop-address {
        type inet:ip-address;
        description
          "The next hop address.";
      }

      leaf label {
        type uint32;
        description
          "Egress TE label for this Egress-TE link";
      }
    }
  }

  grouping labeled-unicast-epe-state {
    container state {
      config false;
      description "Operational Information for BGP LU based Egress Traffic Engineering.";
      uses labeled-unicast-epe-common;
    }
  }

  grouping labeled-unicast-epe-top {
    container labeled-unicast {
      description
        "Configuration parameters related to BGP LU based Egress Traffic Engineering";
      uses labeled-unicast-epe-config;
      uses labeled-unicast-epe-state;
    }
  }

  grouping epe-top {
    container egress-peer-engineering {
      description
        "Container for Egress Peer Engineering feature config/state";
      uses labeled-unicast-epe-top;
    }
  }

  grouping ttl-security-hops-config {
    leaf ttl-security-hops {
      type uint8;
      must "not(../../oc-netinst:ebgp-multihop/oc-netinst:config" +
                "/oc-netinst:multihop-ttl)" {
        error-message "Please unconfigure multihop config first";
      }
      description
        "Max number of ttl-hops to the BGP neighbor";
    }
  }

  grouping ttl-security-hops-state {
    leaf ttl-security-hops {
      type uint8;
      description
        "Max number of ttl-hops to the BGP neighbor";
    }
  }

  grouping shutdown-config {
    leaf shutdown {
      type boolean;
      description
        "BGP Support for the neighbor shutdown.";
    }
  }

  grouping shutdown-reason-top {
    leaf shutdown-reason {
      type string;
      description
        "Reason for neighbor shutdown.";
    }
  }

  grouping state-reason-top {
    leaf state-reason-1 {
      type string;
      description
        "Reason for neighbor FSM state 1.";
    }
    leaf state-reason-2 {
      type string;
      description
        "Reason for neighbor FSM state 2.";
    }
    leaf state-reason-3 {
      type string;
      description
        "Reason for neighbor FSM state 3.";
    }
  }

  grouping disable-fast-deactivation-config {
    leaf disable-fast-deactivation {
      type boolean;
      description
        "Disable peer fast deactivation.";
    }
  }

  grouping session-last-reset-state {
    leaf last-reset-by-neighbor {
      type boolean;
      description
        "Last time the session was reset locally or by the neighbor.";
    }
    leaf last-reset-reason {
      type string;
      description
        "The reason for session being reset last time.";
    }
  }

  grouping nbr-srv6-config {
    leaf tunnel-endpoint {
      type arc-bgp-types:srv6-tunnel-endpoint-type;
      description
        "SRv6 global table ingress or egress tunnel endpoint";
    }
  }

  grouping nbr-srv6-config-top {
    container config {
      description
        "Configuration for SRv6 per neighbor.";
      uses nbr-srv6-config;
    }
  }

  grouping nbr-srv6-state-top {
    container state {
      config false;
      description
        "Operational data for SRv6 per neighbor.";
      uses nbr-srv6-config;
    }
  }

  grouping nbr-srv6-top {
    container srv6 {
        description
          "SRv6 configuration per neighbor";

      when "../../../../../../oc-netinst:name = 'default'" {
        description
          "Allow SRv6 tunnel endpoint configuration in
          network-instance default only";
      }

      uses nbr-srv6-config-top;
      uses nbr-srv6-state-top;
    }
  }

  grouping dscp-config {
    leaf dscp {
      type oc-inet:dscp;
      description
        "The value of Differentiated Services Code Point (DSCP)
        for BGP packets";
      reference
        "RFC 2474 Definition of the Differentiated Services Field
        (DS Field) in the IPv4 and IPv6 Headers";
    }
  }

  grouping neighbor-index-state {
    leaf neighbor-index {
      type uint32;
      description
        "Locally assigned neighbor-index for neighbor.";
    }
  }

  grouping enforce-first-as-config {
    leaf enforce-first-as {
      type boolean;
      description
        "Enable/Disable enforce first AS.";
    }
  }

  grouping message-counter-state {
    leaf OPEN {
      type uint64;
      description
        "No. of incoming and outgoing open messages";
    }

    leaf KEEPALIVE {
      type uint64;
      description
        "No. of incoming and outgoing keepalive";
    }

    leaf REFRESH {
      type uint64;
      description
        "No. of incoming and outgoing route refresh";
    }

    leaf total {
      type uint64;
      description
        "No. of incoming and outgoing messages";
    }

    leaf unknown {
      type uint64;
      description
        "No. of incoming unknown messages";
    }
  }

  grouping received-peer-as-state {
    leaf received-peer-as {
      type oc-inet:as-number;
      description
        "AS number of peer";
    }
  }

  grouping route-server-config {
    leaf route-server-client {
      type boolean;
      description
        "Configure the neighbor as a route server client";
    }
  }

  grouping route-server-top {
    container route-server {
      description "Route server parameters";

      container config {
        description
          "Configuration parameters relating to route server";
        uses route-server-config;
      }

      container state {
        config false;
        description
          "State information relating to route server";
        uses route-server-config;
      }
    }
  }

  grouping nbr-af-add-paths-config {
    leaf send {
      type identityref {
         base arc-oc-bgp-types:ADD_PATHS_OPTIONS;
      }
      description
        "Enable capability negotiation to send additional paths
        advertisements for an NLRI from the neighbor or group";
      reference
        "RFC 7911 - Advertisement of Multiple Paths in BGP";
    }

    leaf receive {
      type boolean;
      description
        "Enable capability negotiation to receive multiple path
        advertisements for an NLRI from the neighbor or group";
      reference
        "RFC 7911 - Advertisement of Multiple Paths in BGP";
    }
  }

  grouping nbr-af-add-paths-receive-state {
    leaf peer-receive {
      type boolean;
      description
        "Is the neighbor capable of receiving add-paths.";
    }

    leaf peer-send {
      type boolean;
      description
        "Is the neighbor capable of sending add-paths.";
    }
  }

  grouping nbr-af-add-paths-config-top {
    container config {
      description
        "Configuration parameters relating to ADD_PATHS";

      uses nbr-af-add-paths-config;
    }
  }

  grouping nbr-af-add-paths-state-top {
    container state {
      config false;
      description
        "State information relating to ADD_PATHS";

      uses nbr-af-add-paths-config;
      uses nbr-af-add-paths-receive-state;
    }
  }

  grouping nbr-af-add-paths-top {
    container add-paths {
      description
        "Parameters relating to the advertisement and receipt of
        multiple paths for a single NLRI (add-paths)";

      uses nbr-af-add-paths-config-top;
      uses nbr-af-add-paths-state-top;
    }
  }

  grouping nbr-af-aigp-config {
    leaf enable {
      type boolean;
      description
        "Enable send and receive AIGP metric attribute";
    }
  }

  grouping bgp-aigp-config {
    container config {
      description "Configurations for AIGP metric.";
      uses nbr-af-aigp-config;
    }
  }

  grouping bgp-aigp-state {
    container state {
      config false;
      description "Operational data for AIGP metric.";
      uses nbr-af-aigp-config;
    }
  }

  grouping bgp-aigp-top {
    container aigp {
      description
        "Neighbor AFI/SAFI AIGP metric configurations and states";

      uses bgp-aigp-config;
      uses bgp-aigp-state;
    }
  }

  grouping nbr-af-next-hop-top {
    leaf next-hop {
      type arc-bgp-types:bgp-next-hop-type;
      description
        "Configure next-hop type";
    }
  }

  grouping nbr-af-send-tracker-sid-top {
    leaf send-tracker-sid {
      type boolean;
      description
        "Configure send-tracker-sid";
    }
  }

  grouping nbr-af-extended-nexthop-config {
    leaf enable {
      type boolean;
      description
        "Enable/Disable extended nexthop encoding capability negotiation";
      reference
        "RFC 5549 - Advertising IPv4 Network Layer Reachability Information
         with an IPv6 Next Hop";
    }
  }

  grouping nbr-af-extended-nexthop-send-receive-state {
    leaf extended-nexthop-sent {
      type boolean;
      description
        "Is Extended Nexthop Encoding Capability sent";
    }

    leaf extended-nexthop-received {
      type boolean;
      description
        "Is Extended Nexthop Encoding Capability received";
    }
  }

  grouping nbr-af-extended-nexthop-config-top {
    container config {
      description
        "Configuration parameters relating to
         extended nexthop encoding capability";
      uses nbr-af-extended-nexthop-config;
    }
  }

  grouping nbr-af-extended-nexthop-state-top {
    container state {
      config false;
      description
        "State information relating to extended nexthop encoding capability";
      uses nbr-af-extended-nexthop-config;
      uses nbr-af-extended-nexthop-send-receive-state;
    }
  }

  grouping nbr-af-extended-nexthop-top {
    container extended-nexthop {
      description
        "Enable extended nexthop encoding capability negotiation";

      uses nbr-af-extended-nexthop-config-top;
      uses nbr-af-extended-nexthop-state-top;
    }
  }

  grouping default-originate-config {
    leaf enabled {
      type boolean;
      description
        "Enable advertisement of default route regardless of RIB state";
    }

    uses oc-rpol:apply-policy-export-config;
  }

  grouping default-originate-config-top {
    container config {
      description
        "Configuration parameters relating to default-originate";
      uses default-originate-config;
    }
  }

  grouping default-originate-state-top {
    container state {
      config false;
      description
        "State information relating to default-originate";
      uses default-originate-config;

      leaf advertised {
        type boolean;
        description
          "Boolean to indicate whether default route is advertised";
      }
    }
  }

  grouping default-originate-top {
    container default-originate {
      when "../oc-netinst:afi-safi-name = 'oc-bgp-types:IPV4_UNICAST' " +
        "or ../oc-netinst:afi-safi-name = 'oc-bgp-types:IPV6_UNICAST'" {
        description
          "Only allow default-originate to be configured
           when the address-family is IPv4 or IPv6 Unicast";
      }
      description
        "BGP default-originate parameters";
      uses default-originate-config-top;
      uses default-originate-state-top;
    }
  }

  grouping soft-reconfig-config-top {
    leaf inbound-soft-reconfiguration {
      type boolean;
      description
        "Configure inbound soft-reconfiguration";
    }
  }

  grouping soft-reconfig-state-top {
    leaf inbound-soft-reconfiguration {
      type boolean;
      description
        "Inbound soft-reconfiguration state";
    }
  }

  grouping nbr-af-prefixes-top {
    leaf accepted {
      type yang:gauge32;
      description
        "The number of paths that are received from the
        neighbor after applying any policies, and accepted into BGP RIB.";
    }
    leaf total-received {
      type uint64;
      description
        "The total number of prefixes received from the neighbor";
    }
    leaf total-sent {
      type uint64;
      description
        "The total number of prefixes advertised to the neighbor";
    }
    leaf withdrawn {
      type uint32;
      description
        "The number of prefixes withdrawn from the neighbor";
    }
    leaf deleted {
      type uint32;
      description
        "The number of prefixes withdrawn by the neighbor or locally deleted";
    }
    leaf deletion-pending {
      type uint32;
      description
        "The number of prefixes from the neighbor with deletion pending";
    }
    leaf denied {
      type uint32;
      description
        "The number of prefixes denied from the neighbor";
    }
    leaf adj-rib-in-pre-only {
      type uint32;
      description
        "The number of prefixes denied from the neighbor but retained
        when inbound soft-recofiguration is enabled";
    }
    leaf invalid {
      type uint64;
      description
        "The total number of prefixes received
         from the neighbor which are considered invalid";
    }
  }

  grouping maximum-paths-config {
    leaf maximum-paths {
      type uint32 {
        range 1..128;
      }
      default 1;
      description
        "Maximum number of parallel paths to consider when using
        BGP multipath. The default is use a single path.";
    }
  }

  grouping use-maximum-paths-config {
    container ebgp {
      description
        "Multipath parameters for eBGP";
      uses maximum-paths-config;
    }
    container ibgp {
      description
        "Multipath parameters for iBGP";
      uses maximum-paths-config;
    }
    container eibgp {
      description
        "Multipath parameters for eiBGP";
      uses maximum-paths-config;
    }
  }

  grouping common-maximum-paths {
    description
      "Common grouping used for both global and groups which provides
       configuration and state parameters relating to use of multiple
       paths";

    container use-maximum-paths {
      description
        "Parameters related to the use of multiple paths for the
        same NLRI";

      container config {
        description
          "Configuration parameters relating to multipath";
        uses use-maximum-paths-config;
      }
      container state {
        config false;
        description
          "State parameters relating to multipath";
        uses use-maximum-paths-config;
      }
    }
  }

  grouping aggregate-address-config {
    description
      "Configuration data for aggregate-address";
    leaf prefix {
      type inet:ip-prefix;
      description
        "The prefix for the IPv4 network.";
    }

    leaf summary-only {
      type boolean;
      description
        "filter more specific routes from update";
    }

    uses selection-policy-config;
    uses oc-rpol:apply-policy-export-config;
  }

  grouping aggregate-address-top {
    container aggregate-addresses {
      when "../oc-netinst:afi-safi-name = 'oc-bgp-types:IPV4_UNICAST' " +
        "or ../oc-netinst:afi-safi-name = 'oc-bgp-types:IPV6_UNICAST'" {
        description
          "Only allow aggregate addresses to be configured
          when the address-family is IPv4 or IPv6 Unicast";
      }
      description "List of aggregate-addresses";
      list aggregate-address {
        key "prefix";
        description "aggregate-address";
        leaf prefix {
          type leafref {
            path "../config/prefix";
          }
          description "Reference to prefix key.";
        }

        container config {
          description "Configuration data for aggregate-address.";
          uses aggregate-address-config;
        }

        container state {
          config false;
          description "Operational data for network.";
          uses aggregate-address-config;
        }
      }
    }
  }

  grouping rib-validation-config {
    leaf rib-validation {
      type boolean;
      default false;
      description
        "Enable/Disable rib validation for network prefix";
    }
  }
  grouping mup-aggregate-address-config {
    description
      "Configuration data for aggregate-address";
    leaf prefix {
      type string;
      description
        "The prefix for the MUP NLRI without route-distinguisher.";
    }

    leaf summary-only {
      type boolean;
      description
        "filter more specific routes from update";
    }

    uses selection-policy-config;
    uses oc-rpol:apply-policy-export-config;
  }

  grouping mup-aggregate-address-top {
    container aggregate-addresses {
      description "List of aggregate-addresses";
      list aggregate-address {
        key "prefix";
        description "aggregate-address";
        leaf prefix {
          type leafref {
            path "../config/prefix";
          }
          description "Reference to prefix key.";
        }

        container config {
          description "Configuration data for aggregate-address.";
          uses mup-aggregate-address-config;
        }

        container state {
          config false;
          description "Operational data for network.";
          uses mup-aggregate-address-config;
        }
      }
    }
  }

  grouping bgp-common-mp-ipv4-mup-group {
    description
      "Group for BGP IPv4 MUP configuration options";

    container ipv4-mup {
      when "../oc-netinst:afi-safi-name = 'arc-oc-bgp-types:IPV4_MUP'" {
        description
          "Include this container for IPV4 MUP specific
          configuration";
      }

      description "BGP IPV4 MUP configuration options";

      uses srv6-mobile-segment-top {
        when "../../../../../../../oc-netinst:name != 'default' and " +
            "../../../../../../.." +
            "/oc-netinst:config/oc-netinst:type = 'oc-netinst-types:L3VRF'" {
          description "MUP Segment configuration is applicable only for non-default L3 instances";
        }
      }

      uses mup-aggregate-address-top;
    }
  }

  grouping bgp-common-mp-ipv6-mup-group {
    description
      "Group for BGP IPv6 MUP configuration options";

    container ipv6-mup {
      when "../oc-netinst:afi-safi-name = 'arc-oc-bgp-types:IPV6_MUP'" {
        description
          "Include this container for IPV6 MUP specific
          configuration";
      }

      description "BGP IPv6 MUP configuration options";

      uses srv6-mobile-segment-top {
        when "../../../../../../../oc-netinst:name != 'default' and " +
            "../../../../../../.." +
            "/oc-netinst:config/oc-netinst:type = 'oc-netinst-types:L3VRF'" {
          description "MUP Segment configuration is applicable only for non-default L3 instances";
        }
      }

      // placeholder for BGP IPv6 MUP specific configuration options
      uses mup-aggregate-address-top;
    }
  }

  grouping ipv4-network-config {
    description
      "Configuration data for IPv4 network.";
    leaf prefix {
      type string;
      description
        "The normalized IPv4 network prefix, e.g., 10.9.0.0/16.";
    }

    uses oc-rpol:apply-policy-export-config;
    uses arc-oc-bgp-aug:rib-validation-config;
  }

  grouping ipv4-network-top {
    container networks {
      description "List of networks";
      list network {
        key "prefix";
        description "Originate a local IPv4 network prefix";

        leaf prefix {
          type leafref {
            path "../config/prefix";
          }
          description "Reference to prefix key.";
        }

        container config {
          description "Configuration data for network.";
          uses ipv4-network-config;
        }

        container state {
          config false;
          description "Operational data for network.";
          uses ipv4-network-config;
        }
      }
    }
  }

  grouping ipv6-network-config {
    description
      "Configuration data for IPv6 network.";
    leaf prefix {
      type string;
      description
        "The normalized IPv6 network prefix, e.g., 2a00::9d:0/112.";
    }

    uses oc-rpol:apply-policy-export-config;
    uses arc-oc-bgp-aug:rib-validation-config;
  }

  grouping ipv6-network-top {
    container networks {
      description "List of networks";
      list network {
        key "prefix";
        description "Originate a local IPv6 network prefix";

        leaf prefix {
          type leafref {
            path "../config/prefix";
          }
          description "Reference to prefix key.";
        }

        container config {
          description "Configuration data for network.";
          uses ipv6-network-config;
        }

        container state {
          config false;
          description "Operational data for network.";
          uses ipv6-network-config;
        }
      }
    }
  }

  grouping rtfilter-network-config {
    description
      "Network configuration for RTFILTER address family";

    leaf prefix {
      description "The RTFILTER prefix";

      type arc-oc-bgp-types:rtfilter-prefix;
    }
  }

  grouping rtfilter-network-top {
    description
      "Top-level grouping for configuring RTFILTER networks";

    container networks {
      description "Container for list of RTFILTER networks";

      list network {
        key "prefix";
        description "Network entries for RTFILTER address family";

        when "../../../oc-netinst:afi-safi-name = 'arc-oc-bgp-types:RTFILTER' ";

        leaf prefix {
          type leafref {
            path "../config/prefix";
          }
          description "Reference to prefix key";
        }

        container config {
          description "Configuration data for RTFILTER network entries";

          uses rtfilter-network-config;
        }

        container state {
          config false;
          description "Operational state data for RTFILTER network entries";

          uses rtfilter-network-config;
        }
      }
    }
  }

  grouping default-information-originate-config {
    leaf enabled {
      type boolean;
      description
        "Enable/Disable default-information originate";
    }
  }

  grouping default-information-originate-top {
    container default-information {
      when "../oc-netinst:afi-safi-name = 'oc-bgp-types:IPV4_UNICAST' " +
        "or ../oc-netinst:afi-safi-name = 'oc-bgp-types:IPV6_UNICAST'" {
        description
          "Only allow default-information originate to be configured
           when the address-family is IPv4 or IPv6 Unicast";
      }
      description
        "BGP support for default-information originate
         to allow default route to be installed from source
         routing protocol into BGP on redistribution";

      container originate {
        description
          "BGP support for default-information originate
           to allow default route to be installed from source
           routing protocol into BGP on redistribution";

        container config {
          description
            "Configuration parameters relating to default-information originate";
          uses default-information-originate-config;
        }

        container state {
          config false;
          description
            "State information relating to default information originate";
          uses default-information-originate-config;
        }
      }
    }
  }

  grouping af-version-top {
    container versions {
      description "AFI/SAFI version numbers";
      leaf path-version {
        type uint64;
        description
         "Path version";
      }
      leaf label-path-version {
        type uint64;
        description
          "Label path version";
      }
      leaf best-path-version {
        type uint64;
        description
          "Besh path version";
      }
      leaf rib-path-version {
        type uint64;
        description
          "RIB path version";
      }
      leaf update-path-version {
        type uint64;
        description
          "Update path version";
      }
    }
  }

  grouping af-errors-group {
    container af-error-counts {
      description
        "Accumulated counts for various BGP AF processing errors";
  
      leaf total-update-gen-errors {
        type uint64;
        description
          "Aggregate count of error messages in update gen area";
      }
      leaf total-label-mgr-api-errors {
        type uint64;
        description
          "Aggregate count of error messages in APIs to label mgr";
      }
      leaf total-rib-api-errors {
        type uint64;
        description
          "Aggregate count of error messages in APIs to rib";
      }
      leaf total-l2rib-api-errors {
        type uint64;
        description
          "Aggregate count of error messages in APIs to l2rib";
      }
      leaf total-brib-add-del-errors {
        type uint64;
        description
          "Aggregate count of error messages in BRIB path add/delete area";
      }
      leaf rib-ilm-install-errors {
        type yang:zero-based-counter64;
        description
          "Number of errors while installing ILM entries in RIB";
      }
      leaf rib-ilm-withdraw-errors {
        type yang:zero-based-counter64;
        description
          "Number of errors while withdrawing ILM entries from RIB";
      }
    }  
  }

  grouping af-stats-counters {
    leaf nlris-added {
      type uint64;
      description "NLRIs added into BGP";
    }
    leaf nlris-dropped {
      type uint64;
      description "NLRIs dropped as invalid in BGP";
    }
    leaf nlris-denied {
      type uint64;
      description "NLRIs denied in BGP";
    }
    leaf nlris-deleted {
      type uint64;
      description "NLRIs deleted in BGP";
    }
    leaf paths-added {
      type uint64;
      description "Paths added into BGP";
    }
    leaf paths-updated {
      type uint64;
      description "Paths updated in BGP";
    }
    leaf paths-mark_delete {
      type uint64;
      description "Paths marked for deletion in BGP";
    }
    leaf paths-deleted {
      type uint64;
      description "Paths deleted in BGP";
    }
    leaf paths-delete-failed {
      type uint64;
      description "Paths failed to delete in BGP";
    }
    leaf inbound-rpol-called {
      type uint64;
      description "Inbound RPOL called";
    }
    leaf inbound-rpol-cached {
      type uint64;
      description "Inbound RPOL cached";
    }
    leaf outbound-rpol-called {
      type uint64;
      description "Outbound RPOL called";
    }
    leaf outbound-rpol-cached {
      type uint64;
      description "Outbound RPOL cached";
    }
    leaf vpn-import-rpol-called {
      type uint64;
      description "VPN import RPOL called";
    }
    leaf vpn-import-rpol-cached {
      type uint64;
      description "VPN import RPOL cached";
    }
    leaf vrf-import-rpol-called {
      type uint64;
      description "VRF import RPOL called";
    }
    leaf vrf-import-rpol-cached {
      type uint64;
      description "VRF import RPOL cached";
    }
    leaf vrf-export-rpol-called {
      type uint64;
      description "VRF export RPOL called";
    }
    leaf vrf-export-rpol-cached {
      type uint64;
      description "VRF export RPOL cached";
    }
    leaf label-path-triggers {
      type uint64;
      description "Label path processing triggers";
    }
    leaf label-path-runs {
      type uint64;
      description "Label path processing runs";
    }
    leaf label-paths-processed {
      type uint64;
      description "Label paths processed";
    }
    leaf best-path-triggers {
      type uint64;
      description "Best path processing triggers";
    }
    leaf best-path-runs {
      type uint64;
      description "Best path processing runs";
    }
    leaf best-paths-processed {
      type uint64;
      description "Best paths processed";
    }
    leaf impexp-paths-processed {
      type uint64;
      description "Import/Export paths processed";
    }
    leaf rib-nlris-processed {
      type uint64;
      description "RIB NLRIs processed";
    }
    leaf rib-runs {
      type uint64;
      description "RIB processing runs";
    }
    leaf upd-paths-queued {
      type uint64;
      description "Paths queued into update paths processing";
    }
    leaf upd-paths-requeued {
      type uint64;
      description "Paths requeued into update paths after processing";
    }
    leaf upd-triggers {
      type uint64;
      description "Update paths processing triggers";
    }
    leaf upd-paths-refresh-triggers {
      type uint64;
      description "Update paths refresh processing triggers";
    }
  }

  grouping af-stats-counters-group {
    container af-stats-accu-counters {
      description
        "Accumulative stats counters for this AF.";
      uses af-stats-counters;
    }
    container af-stats-peri-counters {
      description
        "Periodic stats counters (reset every 30s) for this AF.";
      uses af-stats-counters;
    }
  }

  grouping af-state-top {
    leaf af-ctx-state {
      type string;
      description
        "AF context object state: NORMAL, CLEANUP_TRIGGER, CLEANUP_WAIT, CLEANUP_SYNC, DELETE_PENDING";
    }
    leaf af-ctx-flags {
      type uint32;
      description
        "AF context object flags in hex: CLEANUP=0x1, DELETE=0x2, REVIVE=0x4";
    }
    leaf revival-count {
      type uint16;
      description
        "Number of times this AF context has been revived from DELETE_PENDING state";
    }
    leaf total-route-reflector-clients {
      type uint32;
      description
        "Number of route-reflector client";
    }
    leaf time-since-first-best-path {
      type string;
      description
        "Elapsed time since the first best-path calculation of the afi/safi";
    }
    leaf time-since-last-best-path {
      type string;
      description
        "Elapsed time since the last best-path calculation of the afi/safi";
    }
    leaf first-path-received {
      type string;
      description
        "Timestamp for the first path received of the address-family";
    }
    leaf last-path-received {
      type string;
      description
        "Timestamp for the last path received of the address-family";
    }
    leaf last-update-sent {
      type string;
      description
        "Timestamp for last update sent of the address-family";
    }
    leaf last-rib-update {
      type string;
      description
        "Timestamp for last RIB update of the address-family";
    }
    leaf rib-install-eagain {
      type uint32;
      description
        "Number of EAGAINs (due to queue full) upon downloading
        routes to RIB";
    }
    leaf paths-received {
      type uint64;
      description
        "Aggregate of the actual paths received";
    }
    leaf paths-sent {
      type uint64;
      description
        "Aggregate of the actual paths sent";
    }
    leaf paths-imported {
      type uint64;
      description
        "Aggregate of the actual paths imported from VPN AF";
    }
    leaf paths-exported {
      type uint64;
      description
        "Aggregate of the actual paths exported to VPN AF";
    }
    leaf per-nexthop-labels-allocated {
      type uint64;
      description
        "Aggregate of the per-nexthop labels allocated";
    }
    leaf per-prefix-labels-allocated {
      type uint64;
      description
        "Aggregate of the per-prefix labels allocated";
    }
    leaf total-paths-received {
      type uint64;
      description
        "Aggregate of the total number of paths received";
    }
    leaf total-paths-sent {
      type uint64;
      description
        "Aggregate of the total number of paths sent";
    }
    leaf total-paths-withdrawn {
      type uint64;
      description
        "Aggregate of the total number of paths withdrawn";
    }
    leaf total-paths-skipped {
      type uint64;
      description
        "Aggregate of the total number of paths skipped (msg too big)";
    }
    leaf total-rib-install-policy-passes {
      type yang:counter64;
      description
        "Number of times the rib-install policy resulted in a pass";
    }
    leaf total-rib-install-policy-drops {
      type yang:counter64;
      description
        "Number of times the rib-install policy resulted in a drop";
    }
    leaf total-rib-installs {
      type uint64;
      description
        "Aggregate of the total number of prefixes installed to rib";
    }
    leaf total-rib-updates {
      type uint64;
      description
        "Aggregate of the total number of prefixes updated/modified in rib";
    }
    leaf total-rib-withdrawls {
      type uint64;
      description
        "Aggregate of the total number of prefixes withdrawn from rib";
    }
    leaf rib-install-prefixes {
      type uint64;
      description
        "Number of prefixes installed in rib";
    }
    leaf evpn-route-type-1-installs {
      type yang:zero-based-counter64;
      description
        "Aggregate of the total number of type-1 prefixes installed to l2rib";
    }
    leaf evpn-route-type-1-updates {
      type yang:zero-based-counter64;
      description
        "Aggregate of the total number of type-1 prefixes updated/modified in l2rib";
    }
    leaf evpn-route-type-1-withdrawls {
      type yang:zero-based-counter64;
      description
        "Aggregate of the total number of type-1 prefixes withdrawn from l2rib";
    }
    leaf evpn-route-type-1-installed-prefixes {
      type yang:zero-based-counter64;
      description
        "Number of type-1 prefixes installed in l2rib";
    }
    leaf evpn-route-type-2-installs {
      type yang:zero-based-counter64;
      description
        "Aggregate of the total number of type-2 prefixes installed to l2rib";
    }
    leaf evpn-route-type-2-updates {
      type yang:zero-based-counter64;
      description
        "Aggregate of the total number of type-2 prefixes updated/modified in l2rib";
    }
    leaf evpn-route-type-2-withdrawls {
      type yang:zero-based-counter64;
      description
        "Aggregate of the total number of type-2 prefixes withdrawn from l2rib";
    }
    leaf evpn-route-type-2-installed-prefixes {
      type yang:zero-based-counter64;
      description
        "Number of type-2 prefixes installed in l2rib";
    }
     leaf evpn-route-type-3-installs {
      type yang:zero-based-counter64;
      description
        "Aggregate of the total number of type-3 prefixes installed to l2rib";
    }
    leaf evpn-route-type-3-updates {
      type yang:zero-based-counter64;
      description
        "Aggregate of the total number of type-3 prefixes updated/modified in l2rib";
    }
    leaf evpn-route-type-3-withdrawls {
      type yang:zero-based-counter64;
      description
        "Aggregate of the total number of type-3 prefixes withdrawn from l2rib";
    }
    leaf evpn-route-type-3-installed-prefixes {
      type yang:zero-based-counter64;
      description
        "Number of type-3 prefixes installed in l2rib";
    }
    leaf evpn-route-type-4-installs {
      type yang:zero-based-counter64;
      description
        "Aggregate of the total number of type-4 prefixes installed to l2fm";
    }
    leaf evpn-route-type-4-updates {
      type yang:zero-based-counter64;
      description
        "Aggregate of the total number of type-4 prefixes updated/modified in l2fm";
    }
    leaf evpn-route-type-4-withdrawls {
      type yang:zero-based-counter64;
      description
        "Aggregate of the total number of type-4 prefixes withdrawn from l2fm";
    }
    leaf evpn-route-type-4-installed-prefixes {
      type yang:zero-based-counter64;
      description
        "Number of type-4 prefixes installed in l2fm";
    }
    leaf auto-inbound-soft-reconfiguration {
      type boolean;
      description
        "Auto inbound soft reconfiguration status";
    }
    leaf rib-ilm-labels {
      type uint32;
      description
        "Number of ILM labels installed in RIB";
    }
    leaf rib-ilm-installs {
      type yang:zero-based-counter64;
      description
        "Number of RIB ILM label install operations";
    }
    leaf rib-ilm-withdraws {
      type yang:zero-based-counter64;
      description
        "Number of RIB ILM label withdraw operations";
    }
    leaf total-next-hops {
      type uint32;
      description
        "Number of nexthops used by this AFI/SAFI";
    }
    leaf total-pending-next-hop-updates {
      type uint32;
      description
        "Number of nexthops pending for updates in this AFI/SAFI";
    }
    uses af-errors-group;
    uses af-stats-counters-group;
  }

  grouping nbr-af-version-top {
    container versions {
      description "Neighbor AFI/SAFI version numbers";
      leaf path-version {
        type uint64;
        description
         "Path version";
      }
      leaf refresh-path-version {
        type uint64;
        description
         "Refresh path version";
      }
      leaf update-marker-path-version {
        type uint64;
        description
         "Update marker path version";
      }
    }
  }

  grouping nbr-af-update-gen-stats {
    leaf updates-sent {
      type uint32;
      description
        "Number of update messages sent.";
    }
    leaf pending-updates {
      type uint32;
      description
        "Number of outstanding update messages.";
    }
    leaf update-delays {
      type uint32;
      description
        "Number of deplays due to too many outstanding updates.";
    }
  }

  grouping session-elapsed-time-state {
    leaf session-elapsed-time {
      type string;
      description
        "Elapsed time since the time the BGP session last transitioned
         in or out of the Established state";
    }
  }

  grouping restart-timer-expire-state {
    leaf restart-timer-expire {
      type uint16;
      description
        "This time value indicates the remaining time on BGP GR
        restart timer in seconds";
    }
  }

  grouping stale-routes-timer-expire-state {
    leaf stale-routes-timer-expire {
      type uint16;
      description
        "This time value indicates the remaining time on BGP GR
        stale-routes timer in seconds";
    }
  }

  grouping bestpath-selection-top {
    leaf selection-deferral-time {
      type uint16 {
        range 1..3600;
      }
      default 300;
      description
        "An upper-bound on the time (in seconds) that the best-path
        selection is deferred";
    }
    leaf med-missing-as-worst {
      type boolean;
      description
        "A route without MED is treated as with highest MED value";
    }
    leaf multipath-as-path-relax {
      type boolean;
      default true;
      description
        "Paths with different AS-Path but of same length can form ECMP";
    }
    leaf multipath-nexthop-relax {
      type boolean;
      default false;
      description
        "Enable BGP multi-path for paths with same next-hop";
    }
    leaf multipath-evpn-etree-ead-relax {
      type boolean;
      default true;
      description
        "Enable multipath for EVPN E-Tree EAD-ES routes regardless of
        attribute differences (local-pref, AS-path, origin, MED, IGP metric)";
    }
  }

  grouping selection-deferral-time-expire-state {
    leaf selection-deferral-time-expire {
      type uint16;
      description
        "This time value indicates the remaining time on BGP best-path
        selection deferral timer in seconds";
    }
  }

  grouping neighbor-local-as {
    leaf local-as {
      type oc-inet:as-number;
      description
        "The local autonomous system number that is to be used
        when establishing sessions with the remote peer or peer
        group, if this differs from the global BGP router
        autonomous system number.";
    }

    leaf no-prepend {
      type boolean;
      description
        "This boolean being set to true indicates that the local AS number
        shall not be prepended to the AS path of the prefix received from
        the BGP neighbor.";
    }

    leaf replace-as {
      type boolean;
      description
        "This boolean being set to true indicates that only the local AS
        number shall be prepended to the AS path of the prefix sent to the
        BGP neighbor.";
    }

    leaf dual-as {
      type boolean;
      description
        "This boolean being set to true indicates that either the configured
        local AS number or the global AS number can be used to connected with
        the BGP neighbor.";
    }
  }

  grouping ebgp-local-as-cfg {
    container config {
      description "Configuration data for local AS.";
      uses neighbor-local-as;
    }
  }

  grouping ebgp-local-as-state {
    container state {
      config false;
      description "Operational data for local AS.";
      uses neighbor-local-as;
    }
  }

  grouping ebgp-local-as-top {
    container ebgp-local-as {
      description "BGP neighbor local AS number.";
      uses ebgp-local-as-cfg;
      uses ebgp-local-as-state;
    }
  }

  grouping telemetry-routing-policy-top {
    leaf-list prefix-filter-policy {
      type leafref {
        path "/oc-rpol:routing-policy/oc-rpol:policy-definitions/" +
          "oc-rpol:policy-definition/oc-rpol:name";
      }
      ordered-by user;
      max-elements 1;
      description
        "A policy can be specified for prefixes filtering";
    }
  }

  grouping af-telemetry-config {
    leaf neighbor-stream-enabled {
      type boolean;
      description
        "Enable streaming the state of BGP neighbors with this AFI/SAFI
        via telemetry";
    }

    leaf prefix-stream-enabled {
      type boolean;
      description
       "Enable streaming BGP path information via telemetry";
    }

    uses telemetry-routing-policy-top {
      when "arc-oc-bgp-aug:prefix-stream-enabled = 'true'" {
        description
          "It is optional to specify a routing-policy for filtering
          if telemetry for paths is enabled";
      }
    }
  }

  grouping global-telemetry-config {
    leaf neighbor-stream-enabled {
      type boolean;
      description
        "Enable streaming the state of BGP neighbors in all
         network-instances via telemetry";
    }

    leaf prefix-stream-enabled {
      type boolean;
      description
       "Enable streaming BGP path information in all
        network-instances via telemetry";
    }
  }

  grouping global-telemetry-top {
    container telemetry {
      description
        "BGP-specific telemetry parameters";

      container config {
        description
          "Global telemetry configuration parameters";
        uses global-telemetry-config;
      }
      container state {
        config false;
        description
          "Global telemetry state information";
        uses global-telemetry-config;
      }
    }
  }

  grouping af-telemetry-top {
    container telemetry {
      description
        "BGP-specific telemetry parameters";

      container config {
        description
          "Telemetry configuration parameters";
        uses af-telemetry-config;
      }
      container state {
        config false;
        description
          "Telemetry state information";
        uses af-telemetry-config;

        leaf prefixes-streamed {
          type uint32;
          description
            "Count for unique prefixes that have been streamed out";
        }

        leaf prefixes-updated {
          type uint32;
          description
            "Count for existing prefixes that have been updated";
        }

        leaf prefixes-withdrawn {
          type uint32;
          description
            "Count for prefixes that have been streamed out and withdrawn";
        }
      }
    }
  }

  grouping rtr-server-config-top {
    leaf server-name {
      type string {
        length "1..50";
      }
      description
        "Name of the RTR server";
    }
    leaf address {
      type oc-yang:dotted-quad;
      mandatory true;
      description
        "IPv4 address of the RTR server";
    }
    leaf local-address {
      type union {
        type inet:ip-address;
        type oc-if:base-interface-ref;
      }
      description
        "Local transport address or interface for connecting to the RTR server";
    }
    leaf port {
      type uint16;
      mandatory true;
      description
        "TCP port the RTR server listens to";
    }
    leaf preference {
      type uint8 {
        range "0..254";
      }
      mandatory true;
      description
        "Preference of the RTR server; the server with lower value
        is more preferred";
    }
  }

  typedef ipv4-pfx-len {
    type uint8 {
      range "0 .. 32";
    }
    description
      "IPv4 Prefix Length.";
  }

  typedef ipv6-pfx-len {
    type uint8 {
      range "0 .. 128";
    }
    description
      "IPv6 Prefix Length.";
  }

  typedef subject-key-id {
    type binary {
      length 20;
    }
    description
      "Subject Key Identifier.";
  }

  grouping ipv4-roa-info {
    description
      "RTR IPv4 ROA information";

    leaf prefix {
      type inet:ip-address;
      description
        "The IPv4 prefix of the ROA.";
    }
    leaf min-len {
      type ipv4-pfx-len;
      description
        "Denotes the shortest prefix allowed. This
         MUST NOT be greater than the prefix length.";
    }
    leaf max-len {
      type ipv4-pfx-len;
      description
        "Denotes the longest prefix allowed. This
         MUST NOT be less than the prefix length.";
    }
    leaf asn {
      type inet:as-number;
      description
        "The origin AS number of the ROA.";
    }
    leaf server-address {
      type inet:ip-address;
      description
        "IP address of the RPKI cache server.";
    }
  }

  grouping ipv6-roa-info {
    description
      "RTR IPv6 ROA information";
    leaf prefix {
      type inet:ipv6-address;
      description
        "The IPv6 prefix of the ROA.";
    }
    leaf min-len {
      type ipv6-pfx-len;
      description
        "Denotes the shortest prefix allowed. This
         MUST NOT be greater than the prefix length.";
    }
    leaf max-len {
      type ipv6-pfx-len;
      description
        "Denotes the longest prefix allowed. This
         MUST NOT be less than the prefix length.";
    }
    leaf asn {
      type inet:as-number;
      description
        "The origin AS number of the ROA.";
    }
    leaf server-address {
      type inet:ip-address;
      description
        "IP address of the RPKI cache server.";
    }
  }

  grouping ipv4-roa-group {
    description
      "RTR IPv4 ROA information";
    list ipv4-roa {
      config false;
      key "prefix min-len";
      description
        "List of ROAs in the table keyed by IPv4 prefix.";
      uses ipv4-roa-info;
    }
  }

  grouping ipv6-roa-group {
    description
      "RTR IPv6 ROA information";
    list ipv6-roa {
      config false;
      key "prefix min-len";
      description
        "List of ROAs in the table keyed by IPv6 prefix.";
      uses ipv6-roa-info;
    }
  }

  grouping rpki-cache-top {
    description
      "Top-level grouping for RTR cache";

    container ipv4-roa-entries {
      description
        "List of RTR IPv4 ROA entries";
      uses ipv4-roa-group;
    }
    container ipv6-roa-entries {
      description
        "List of RTR IPv6 ROA entries";
      uses ipv6-roa-group;
    }
  }

  grouping rtr-server-state-top {
    leaf server-connected {
      type boolean;
      description
        "This boolean indicates if connection to the configured RTR server
        is successful";
    }
  }

  grouping bgp-rtr-server-base {
    description
      "Parameters related to a RTR server";

    container config {
      description
        "Configuration parameters relating to the RTR server";

      uses rtr-server-config-top;
    }

    container state {
      config false;
      description
        "State information relating to the RTR server";
      uses rtr-server-config-top;
      uses rtr-server-state-top;
    }
  }

  grouping bgp-rtr-server-list {
    description
      "The list of RPKI to router protocol server information";

    list rtr-server {
      key server-name;
      max-elements 5;
      unique "config/address config/port";
      description
        "List of configured RTR servers";

      leaf server-name {
        type leafref {
          path "../config/server-name";
        }
        description
          "Reference to the RTR server name used as a key in the
          RTR server list";
      }

      uses bgp-rtr-server-base;
    }
  }

  grouping global-segment-routing-config {
    description
      "Configuration parameters relating to segment routing within an
      IGP.";

    leaf enabled {
      type boolean;
      description
        "When this leaf is set to true, the segment routing extensions are
        utilised within the BGP.";
    }
  }

  grouping graceful-shutdown-config {
    leaf enable {
      type boolean;
      description
        "Enable graceful shutdown.";
    }
    leaf set-local-preference-zero {
      type boolean;
      description
        "Set local preference to minimum (0), which will be sent to iBGP neighbor.";
    }
    leaf set-med-maximum {
      type boolean;
      description
        "Set med value to maximum (2147483647).";
    }
  }

  grouping graceful-shutdown-top {
    container graceful-shutdown {
      description "BGP support for graceful shutdown.";

      container config {
        description
          "Configuration parameters relating to graceful shutdown.";
        must "(enable = 'true') or " +
             "(boolean(set-local-preference-zero) != 'true' and " +
             " boolean(set-med-maximum) != 'true')" {
          error-message "Graceful shutdown must be enabled if local preference
                         or MED is configured.";
        }
        uses graceful-shutdown-config;
      }

      container state {
        config false;
        description
          "State information relating to graceful shutdown.";
        uses graceful-shutdown-config;
      }
    }
  }

  grouping nl-intf-info {
    description
      "BGP Netlink information";

    leaf interface-name {
      type string;
      description
        "Name of the interface";
    }

    leaf network-instance-name {
      type string;
      description
        "Network instance name";
    }

    leaf network-instance-id {
      type uint32;
      description
        "Network instance identifier";
    }

    leaf-list addresses {
      type inet:ip-address;
      description
       "IP addresses on the interface";
    }

    leaf interface-state {
      type arc-bgp-types:bgp-interface-state;
      description
        "State of the interface";
    }
  }

  grouping nl-v4-pfx-info {
    description
      "BGP Netlink IPv4 prefix information";

    leaf address {
      type inet:ip-address;
      description
       "IP address on the entry";
    }

    leaf key-length {
      type uint16;
      description
        "Length for NL key";
    }

    leaf interface-name {
      type string;
      description
        "Name of the interface";
    }

    leaf interface-state {
      type arc-bgp-types:bgp-interface-state;
      description
        "State of the interface";
    }
  }

  grouping nl-v6-pfx-info {
    description
      "BGP Netlink IPv6 prefix information";

    leaf address {
      type inet:ipv6-address;
      description
       "IP address on the entry";
    }

    leaf key-length {
      type uint16;
      description
        "Length for NL key";
    }

    leaf interface-name {
      type string;
      description
        "Name of the interface";
    }

    leaf interface-state {
      type arc-bgp-types:bgp-interface-state;
      description
        "State of the interface";
    }
  }

  grouping nl-intf-group {
    description
      "BGP Netlink information";

    list nl-intf-entry {
      config false;
      key "interface-name";
      description
        "List of BGP Netlink entries";
      uses nl-intf-info;
    }
  }

  grouping nl-v4-pfx-group {
    list nl-v4-pfx-entry {
      config false;
      key "address key-length";
      description
        "List of BGP Netlink IPV4 prefix entries";
      uses nl-v4-pfx-info;
    }
  }

  grouping nl-v6-pfx-group {
    list nl-v6-pfx-entry {
      config false;
      key "address key-length";
      description
        "List of BGP Netlink IPV6 prefix entries";
      uses nl-v6-pfx-info;
    }
  }

  grouping nl-info-top {
    description
      "BGP Netlink information";

    container nl-intf-entries {
      description
        "List of BGP netlink entries from interfaces";
      uses nl-intf-group;
    }

    container nl-v4-pfx-entries {
      description
        "List of BGP Netlink IPV4 prefix entries";
      uses nl-v4-pfx-group;
    }

    container nl-v6-pfx-entries {
      description
        "List of BGP Netlink IPV6 prefix entries";
      uses nl-v6-pfx-group;
    }
  }

  grouping tunnel-details {
    description
      "BGP tunnel operational state";

    leaf tunnel-id {
      type uint32;

      description
        "Tunnel-id";
    }

    leaf tunnel-source {
      type inet:ip-address;

      description
        "Source ip address of the tunnel";
    }

    leaf tunnel-destination {
      type inet:ip-address;

      description
        "Destination address of the tunnel";
    }

    leaf loc-len {
      type uint32;

      description
        "platform locator length";
    }

    leaf tunnel-type {
      type string;

      description
        "Tunnel-type (IPV4 or IPV6)";
    }

    leaf tunnel-endpoint {
      type inet:ip-address;

      description
        "Endpoint address of the tunnel";
    }

    leaf endpoint-behavior {
      description
        "SRv6 endpoint behavior for the tunnel destination";
      type identityref {
        base arc-srv6-types:SRV6_ENDPOINT_BEHAVIOR_TYPE;
      }
    }

    leaf srv6-oam-state {
      type identityref {
        base arc-oc-bgp-types:SRV6_OAM_STATES;
      }
      description
        "For SRv6 Tunnel only: health state as reported by OAM";
    }

    leaf srv6-oam-profile {
      type string;
      description
        "For SRv6 Tunnel only: profile used in OAM tracking";
    }

    leaf refcount {
      type uint32;

      description
        "Number of routes pointing to this tunnel";
    }
  }

  grouping tunnels-top {
    description
      "BGP tunnels";

    container state {
      config false;
      description
        "Container for tunnel states created by BGP";

      list tunnel {

        key "tunnel-id";

        description
          "List of tunnels";

        uses tunnel-details;
      }
    }

    container stats {
      config false;
      description
        "Statistics for tunnel allocations by BGP";
      leaf count {
        type uint32;
        description
          "Total tunnel count";
      }
      leaf highest-tunnel-count {
        type uint32;
        description
          "Historically highest tunnel count reached";
      }
      leaf highest-tunnel-id {
        type uint32;
        description
          "Historically highest tunnel id allocated";
      }
    }
  }

  grouping rtfilter-af-config {
    description
      "Grouping for VPN Address Family Route Target Filter Configuration";

    container rtfilter {
      description
        "Parameters relating to Route Target filtering";

      leaf enabled {
        description "Enable Route Target filtering";

        type boolean;
      }
    }
  }

  grouping rtfilter-af-config-top {
    description "VPN address family configuration for route target filtering";

    container rtfilter {
      description
        "Container for VPN address family route target filter configuration";

      container config {
        description
          "Configuration for VPN address family route target filter configuration";

        uses rtfilter-af-config;
      }

      container state {
        config false;

        description
          "Operational state data for VPN address family route target filtering";

        uses rtfilter-af-config;
      }
    }
  }

  grouping rtfilter-global-config {
    description "Grouping for global RTFILTER configuration";

    leaf vpn-update-delay {
      description
        "Delay sending VPN updates for at most this many seconds
         waiting for End-of-Rib in RTFILTER Address Family";

      type uint32 {
        range 0..600;
      }
      units seconds;
      default 60;
    }
  }

  grouping rtfilter-global-config-top {
    description "Top-level grouping for global RTFILTER configuration";

    container rtfilter-global {
      description
        "Container for RTFILTER global configuration";

      container config {
        description
          "Configuration data for global RTFILTER address family";

        uses rtfilter-global-config;
      }

      container state {
        config false;

        description
          "Operational state data for global RTFILTER address family";

        uses rtfilter-global-config;
      }
    }
  }

  grouping nbr-af-rtfilter-top {
    description "Top-level grouping for neighbor RTFILTER data";

    container rtfilter {
      description
        "Parameters relating to RTFILTER address family neighbor configuration";

      when "../oc-netinst:afi-safi-name = 'arc-oc-bgp-types:RTFILTER' ";
      uses oc-bgp:bgp-common-mp-ipv4-ipv6-unicast-common;
    }
  }

  grouping rib-acks {
    leaf pending-rib-acks {
      type uint32;
      description
        "Number of prefixes that are waiting for RIB ACK";
    }
    leaf initial-rib-acks {
      type uint32;
      description
        "Number of initial RIB ACKs";
    }
    leaf queued-rib-acks {
      type uint32;
      description
        "Number of queued RIB ACKs";
    }
  }

  grouping disable-rib-resolution-config {
    leaf disable-rib-resolution {
      type boolean;
      description
        "Enable/Disable BGP route resolution in RIB";
    }
  }

  grouping global-import-export-readiness-top {
    leaf l3vpn-ipv4-export-readiness {
      type string;
      description
        "Export readiness of this network-instance";
    }
    leaf l3vpn-ipv4-import-readiness {
      type string;
      description
        "Import readiness of this network-instance";
    }
    leaf l3vpn-ipv6-export-readiness {
      type string;
      description
        "Export readiness of this network-instance";
    }
    leaf l3vpn-ipv6-import-readiness {
      type string;
      description
        "Import readiness of this network-instance";
    }
    leaf evpn-export-readiness {
      type string;
      description
        "Export readiness of this network-instance";
    }
    leaf evpn-import-readiness {
      type string;
      description
        "Import readiness of this network-instance";
    }
  }

  grouping deagg-label-top {
    leaf deaggregation-label {
      type uint32;
      description
        "Deaggreation label if allocated";
    }
  }

  grouping imet-label-top {
    leaf imet-label {
      type uint32;
      description
        "IMET label if allocated";
    }
  }

  grouping instance-sid-top {
    leaf instance-sid {
      type inet:ipv6-address;
      description
        "Locally allocated per-instance segment ID";
    }
  }

  grouping global-config {
    leaf route-distinguisher {
      type oc-netinst-types:route-distinguisher;
      description
        "The route distinguisher that should be used for the local
        VRF or VSI instance when it is signalled via BGP.";
    }
  }

  grouping global-allocation-config {
    leaf label-allocation-mode {
      type identityref {
        base oc-netinst-types:LABEL_ALLOCATION_MODE;
      }
      must "not(../sid-allocation-mode)" {
        error-message
          "label-allocation-mode and sid-allocation-mode cannot " +
          "co-exist";
      }
      must "not(/oc-netinst:network-instances" +
           "/oc-netinst:network-instance[oc-netinst:name='default']" +
           "/oc-netinst:protocols/oc-netinst:protocol" +
           "/oc-netinst:bgp/oc-netinst:global/srv6/config/locator)" {
        error-message
          "SRv6 configurations must be removed first";
      }
      description
        "The label allocation mode to be used for L3 entries
         in the network instance";
    }

    leaf sid-allocation-mode {
      type identityref {
        base arc-oc-bgp-types:SID_ALLOCATION_MODE;
      }
      must "not(../label-allocation-mode)" {
        error-message "label-allocation-mode and " +
                      "sid-allocation-mode cannot co-exist";
      }
      must "(../../srv6/config/locator) or " +
           "(/oc-netinst:network-instances" +
           "/oc-netinst:network-instance[oc-netinst:name='default']" +
           "/oc-netinst:protocols/oc-netinst:protocol" +
           "/oc-netinst:bgp/oc-netinst:global/srv6/config/locator)" {
        error-message "SRv6 locator name must be configured";
      }
      description
        "The segment ID allocation mode to be used for L3 entries
        in the network instance";
    }
  }

  grouping srv6-locator-top {
    leaf locator-registered {
      type boolean;
      description
        "Locator name is registered";
    }

    leaf micro-segment-enabled {
      type boolean;
      description
        "Locator has enabled micro-segment behavior";
    }
  }

  grouping srv6-mobile-encapsulation-config-top {
    leaf policy-color {
      description
        "Color community value to attach for MUP ST-1 routes";
      type uint32 {
        range "1..4294967295";
      }
    }

    leaf source-address {
      description
        "GTP source IP address";
      type inet:ipv4-address; 
    }

    leaf source-position {
      description
        "Bit position of GTP source IP address";
      type uint8;
    }

    leaf checksum-type {
      description
        "Checksum Type";
      type arc-bgp-types:srv6-checksum-type;
    }
  }

  grouping srv6-mobile-decapsulation-config-top {
    leaf id {
      description
        "SRv6 mobile decapsulation entry id";
      type uint16 {
        range "1..100";
      }
    }
  }

  grouping srv6-mobile-encapsulation-top {
    container encapsulation {
      description
        "SRv6 mobile encapsulation";

      container config {
        uses srv6-mobile-encapsulation-config-top;
      }

      container state {
        config false;
        uses srv6-mobile-encapsulation-config-top;
      }
      uses srv6-mobile-encapsulation-n4-ni-top;
    }
  }

  grouping srv6-locator-config-top {
    leaf locator {
      description
        "Reference to SRv6 locator key";
      type leafref {
        path "/oc-netinst:network-instances/oc-netinst:network-instance" +
            "/arc-srv6:srv6/arc-srv6:locator/arc-srv6:name";
      }
    }
  }

  grouping srv6-mobile-encapsulation-n4-ni-config-top {
    leaf access {
      description
        "Access instance";
      type string;
    }

    leaf import-policy {
      description
        "Import policy to be applied on the sessions";
      type leafref {
         path "/oc-rpol:routing-policy/oc-rpol:policy-definitions" +
              "/oc-rpol:policy-definition/oc-rpol:name";
       }
    }
  }

  grouping srv6-mobile-decapsulation-n4-ni-config-top {
    leaf core {
      description
        "Core instance";
      type string;
    }
  }

  grouping srv6-mobile-encapsulation-n4-ni-top {
    container n4-network-instance {
      container config {
        uses srv6-mobile-encapsulation-n4-ni-config-top;
      }

      container state {
        config false;
        uses srv6-mobile-encapsulation-n4-ni-config-top;
      }
    }
  }

  grouping srv6-mobile-decapsulation-n4-ni-top {
    container n4-network-instance {
      container config {
        uses srv6-mobile-decapsulation-n4-ni-config-top;
      }
      container state {
        config false;
        uses srv6-mobile-decapsulation-n4-ni-config-top;
      }
    }
  }

  grouping srv6-mobile-config-top {
    leaf decapsulation-source-prefix {
        description
          "IPv6 prefix for GTP source address";
        type inet:ipv6-prefix;
    }

    leaf decapsulation-fallback-table {
      description
        "Fallback network-instance for GTP-U";
      type oc-netinst:network-instance-ref;
    }
  }

  grouping srv6-mobile-decapsulation-top {
    container decapsulations {
      description
        "SRv6 mobile decapsulation";
      list decapsulation {
        key "id";
        unique "n4-network-instance/config/core";

        description
          "SRv6 mobile Decapsulation config";

        leaf id {
          type leafref {
            path "../config/id";
          }
          description
            "Entry ID";
        }
        container config {
          uses srv6-mobile-decapsulation-config-top;
        }

        container state {
          config false;
          uses srv6-mobile-decapsulation-config-top;
        }
        uses srv6-mobile-decapsulation-n4-ni-top;
        uses srv6-mobile-extended-community-list-top;
      }
    }
  }

  grouping srv6-mobile-top {
    container mobile {
      description "SRv6 Mobile";
      container config {
        uses srv6-mobile-config-top;
      }

      container state {
        config false;
        uses srv6-mobile-config-top;
      }

      uses srv6-mobile-encapsulation-top;
      uses srv6-mobile-decapsulation-top;
    }
  }

  grouping srv6-top {
    container srv6 {
      description
        "Global SRv6 configuration and state information";

      container config {
        description
          "Global SRv6 config information";
        uses srv6-locator-config-top;
      }

      container state {
        description
          "Global SRv6 state information";

        config false;
        leaf enabled {
          type boolean;
          description
            "SRv6 is currently enabled or disabled";
        }

        leaf sid-manager-connected {
          type boolean;
          description
            "Connection with segment ID manager is active";
        }

        uses srv6-locator-config-top;
        uses srv6-locator-top;
      }

      uses srv6-mobile-top {
        when "/arc-features:features" +
             "/arc-features:feature[arc-features:name='arc-features:ARCOS_SRV6_MUP']" +
             "/arc-features:supported = 'true'";
      }
    }
  }

  grouping global-compatibility-config {
    leaf suppress-nexthop-attribute {
      type boolean;
      default false;
      description
        "Do not send NEXT_HOP attribute in multi-protocol updates";
    }

    leaf strict-common-afi-safi-check {
      type boolean;
      default false;
      description
        "Enable/Disable BGP strict common afi-safi peers";
    }

    leaf l2-attr-local {
      type boolean;
      default false;
      description
        "Allow implicit matching of local control-word/flow-label configuration ";
    }
  }

  grouping srv6-mobile-segment-key-top {
    leaf segment-type {
      type identityref {
        base arc-oc-bgp-types:MUP_SEGMENT_TYPE;
      }
    }
  }

  grouping srv6-mobile-interwork-source-top {

   /*
    * The src-protocol-name is required to make the model future proof
    * for the multiple IGP instances support in the same network-instance.
    *
    * Use type identityref and string instead of leafref for
    * src-protocol-identifier and src-protocol-name because DIRECTLY_CONNECTED
    * is not explicitly configured.
    *
    * As YANG does not support NULL key, the backend assume the protocol name
    * of DIRECTLY_CONNECTED is always "directly_connected".
    */
    leaf src-network-instance {
      type leafref {
         path "/oc-netinst:network-instances/oc-netinst:network-instance" +
              "/oc-netinst:config/oc-netinst:name";
      }
      description
        "Interwork source network instance.";
    }
    leaf src-protocol-identifier {
      type identityref {
        base oc-pol-types:INSTALL_PROTOCOL_TYPE;
      }
      must "not(derived-from-or-self(current(), 'arc-oc-pol-types:RSVP'))" {
        error-message "src-protocol not supported yet";
      }
      description
        "Interwork source protocol identifier.";
    }
    leaf src-protocol-name {
      type string;
      description
        "Interwork source protocol name.";
    }
    uses oc-rpol:apply-policy-import-config;
  }

  grouping srv6-mobile-interwork-sources-top {
    container sources {
      list source {
        key "src-network-instance src-protocol-identifier src-protocol-name";
        leaf src-network-instance {
          type leafref {
            path "../config/src-network-instance";
          }
        }
        leaf src-protocol-identifier {
          type leafref {
            path "../config/src-protocol-identifier";
          }
        }
        leaf src-protocol-name {
          type leafref {
            path "../config/src-protocol-name";
          }
        }
        container config {
          uses srv6-mobile-interwork-source-top;
        }
        container state {
          config false;
          uses srv6-mobile-interwork-source-top;
        }
        description
          "ISD Source";
      }
    }
  }

  grouping srv6-mup-locator-config-top {
    leaf locator {
      type leafref {
        path "/oc-netinst:network-instances/oc-netinst:network-instance" +
             "/arc-srv6:srv6/arc-srv6:locator/arc-srv6:name";
      }
      description
        "Reference to SRv6 locator key";
    }
  }

  grouping srv6-mobile-interwork-top {
    container interwork {
      container config {
        uses srv6-mup-locator-config-top;
      }
      container state {
        config false;
        uses srv6-mup-locator-config-top;
      }
      uses srv6-mobile-interwork-sources-top;
    }
  }

  grouping srv6-mobile-extended-community-top {
    leaf community-value {
      type arc-oc-bgp-types:bgp-mup-ext-community-type;
      description
        "Extended MUP community attributes";
    }
  }

  grouping srv6-mobile-extended-community-list-top {
    container mup-ext-comms {
      list mup-ext-comm {
        key "community-value";
        leaf community-value {
          type leafref {
            path "../config/community-value";
          }
        }
        container config {
          uses srv6-mobile-extended-community-top;
        }
        container state {
          config false;
          uses srv6-mobile-extended-community-top;
        }
      }
    }
  }

  grouping srv6-mobile-direct-address-top {
    leaf address {
      type union {
        type inet:ip-address;
        type enumeration {
          enum "router-id";
        }
      }
      description
        "Direct Segemnt Entry address";
    }
  }

  grouping srv6-mobile-direct-addresses-top {
    container addresses {
      list address {
        key "address";
        max-elements 1;
        leaf address {
          type leafref {
            path "../config/address";
          }
        }
        container config {
          uses srv6-mobile-direct-address-top;
        }
        container state {
          config false;
          uses srv6-mobile-direct-address-top;
        }
        description
          "DSD Entry";
      }
    }
  }
  grouping srv6-mobile-direct-top {
    container direct {
      uses srv6-mobile-direct-addresses-top;
      uses srv6-mobile-extended-community-list-top;
    }
  }

 /*
  * The `segments` under IPV<4/6>_MUP has an issue,
  * when an idref is defined under leafref the completion callpoint
  * doesn't get called untill a segment name is entered manually
  * And even the tab completion doesn't work as expected.
  * Seems like a confd bug, workaround is to directly define idref
  * under leaf `segment-type`.
  */
  grouping srv6-mobile-segment-top {
    container segments {
      list segment {
        key "segment-type";
        description
          "MUP Segment Type";
        leaf segment-type {
          type identityref {
            base arc-oc-bgp-types:MUP_SEGMENT_TYPE;
          }
        }
        container config {
          uses srv6-mobile-segment-key-top;
        }
        container state {
          config false;
          uses srv6-mobile-segment-key-top;
        }
        uses srv6-mobile-direct-top {
          when "derived-from-or-self(./segment-type, 'arc-oc-bgp-types:DIRECT')";
        }
        uses srv6-mobile-interwork-top {
          when "derived-from-or-self(./segment-type, 'arc-oc-bgp-types:INTERWORK')";
        }
      }
    }
  }

  grouping global-compatibility-top {
    description
      "Grouping for BGP options useful for interop with other vendor implementations";

    container compatibility {
      description
        "BGP compatibility options";

      container config {
        description
          "BGP compatibility configuration";
        uses global-compatibility-config;
      }

      container state {
        config false;
        description
          "BGP compatibility state";
        uses global-compatibility-config;
      }

      when "../../../../../oc-netinst:config/oc-netinst:name = 'default'";
    }
  }

  grouping peer-as-range-inline {
    leaf-list ranges {
      type arc-oc-bgp-types:peer-as-range;
      max-elements 16;
      description
        "List of Peer AS number";
    }
  }

  grouping peer-as-range-inline-top-config {
    container config {
      uses peer-as-range-inline;
      description
        "Peer AS inline config";
    }
  }

  grouping peer-as-range-inline-top-state {
    container state {
      config false;
      uses peer-as-range-inline;
      description
        "Peer AS inline state";
    }
  }

  grouping peer-as-range-inline-top {
    container inline {
      description
        "Peer AS range inline configuration and state";

      uses peer-as-range-inline-top-config;
      uses peer-as-range-inline-top-state;
    }
  }

  grouping peer-as-range-top {
    container peer-as-range {
      uses peer-as-range-inline-top;
      description
        "Peer AS range configuration";
    }
  }

  grouping global-network-instance-id {
    leaf network-instance-id {
      type uint32;
      description
        "Network-instance ID assigned by the system";
    }
  }

  grouping memory-counter-attributes-top {
    leaf id {
      type uint16;
      description
        "Memory counter ID";
    }
    leaf type {
      type string;
      description
        "Memmory counter type";
    }
    leaf inuse-counter {
      type uint32;
      description
        "Memory in use counter";
    }
    leaf bytes-counter {
      type uint64;
      description
        "Bytes alloc counter";
    }
    leaf failed-counter {
      type uint32;
      description
        "Memory alloc failed counter";
    }
    leaf slab-counter {
      type uint32;
      description
        "Memory slab alloc counter";
    }
  }

  grouping memory-counters-top {
    description
      "Grouping for memory usage counters";
    container memory-counters {
      config false;
      list memory-counter {
        key "id";

        leaf id {
          type leafref {
            path "../state/id";
          }
          description
            "Counter ID";
        }
        container state {
          uses memory-counter-attributes-top;
        }
      }
    }
  }

  augment "/oc-netinst:network-instances/oc-netinst:network-instance" +
          "/oc-netinst:protocols/oc-netinst:protocol/oc-netinst:bgp" +
          "/oc-netinst:global" {
    uses global-compatibility-top;
  }

  /*
   * Augmentations for BGP commands
   */
  augment "/oc-netinst:network-instances/oc-netinst:network-instance" +
          "/oc-netinst:protocols/oc-netinst:protocol" +
          "/oc-netinst:bgp" {
    container netlink {
      uses nl-info-top;
    }
  }

  augment "/oc-netinst:network-instances/oc-netinst:network-instance" +
          "/oc-netinst:protocols/oc-netinst:protocol" +
          "/oc-netinst:bgp" +
          "/oc-netinst:global" {
    container tunnels {
      uses tunnels-top;
    }
  }

  augment "/oc-netinst:network-instances/oc-netinst:network-instance" +
          "/oc-netinst:protocols/oc-netinst:protocol" +
          "/oc-netinst:bgp" {
    container rpki-cache {
      uses rpki-cache-top;
    }
  }

  augment "/oc-netinst:network-instances/oc-netinst:network-instance" +
          "/oc-netinst:protocols/oc-netinst:protocol" +
          "/oc-netinst:bgp" +
          "/oc-netinst:global/oc-netinst:config" {
    uses global-cluster-id-config;
    uses global-disable-rib-config;
    uses global-shutdown-all-config;
    uses global-mandate-ebgp-policy-config;
    container segment-routing {
      uses global-segment-routing-config;
    }
    uses global-shutdown-protocol-config {
      when "../../../../../oc-netinst:config/oc-netinst:name = 'default'";
    }
    uses global-silent-drop-config {
      when "../../../../../oc-netinst:config/oc-netinst:name = 'default'";
    }
    uses global-drop-upon-invalid-sr-policy-config {
      when "../../../../../oc-netinst:config/oc-netinst:name = 'default'";
    }
    uses global-adj-rib-out-post-config {
      when "../../../../../oc-netinst:config/oc-netinst:name = 'default'";
    }
  }

  augment "/oc-netinst:network-instances/oc-netinst:network-instance" +
          "/oc-netinst:protocols/oc-netinst:protocol" +
          "/oc-netinst:bgp" +
          "/oc-netinst:global" {
    uses graceful-shutdown-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:state" {
    uses global-update-wait-data-plane-config;
    uses advertise-best-external-config;
    uses route-target-retain-config {
      when "oc-netinst:afi-safi-name = 'oc-bgp-types:L2VPN_EVPN' " +
        "or oc-netinst:afi-safi-name = 'oc-bgp-types:L3VPN_IPV4_UNICAST' " +
        "or oc-netinst:afi-safi-name = 'oc-bgp-types:L3VPN_IPV6_UNICAST' " +
        "or oc-netinst:afi-safi-name = 'arc-oc-bgp-types:IPV4_MUP' " +
        "or oc-netinst:afi-safi-name = 'arc-oc-bgp-types:IPV6_MUP' " {
        description
          "Retain VPN routes with all route-targets";
      }
    }

    uses rib-acks;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:state" {
    uses  oc-mpls:mpls-global_config;
    uses  disable-rib-resolution-config;
    uses  deagg-label-top;
    uses  imet-label-top;
    uses  instance-sid-top;
  }

  augment "/oc-netinst:network-instances/oc-netinst:network-instance" +
          "/oc-netinst:protocols/oc-netinst:protocol" +
          "/oc-netinst:bgp" +
          "/oc-netinst:global/oc-netinst:state" {
    uses global-cluster-id-config;
    uses global-disable-rib-config;
    uses global-shutdown-all-config;
    uses global-mandate-ebgp-policy-config;
    uses global-neighbor-stats;
    uses global-errors-group;
    uses global-config;
    uses global-network-instance-id;
    uses global-import-export-readiness-top;
    uses global-allocation-config;
    uses global-update-gen-stats;
    container segment-routing {
      uses global-segment-routing-config;
    }

    leaf local-tunnel-ip {
      type inet:ip-address;
      description
        "Local tunnel ip for this network-instance";
    }

    leaf tunnel-type {
      type string;
      description
        "Tunnel-type (VXLAN or MPLS)";
    }

    leaf control-word {
      type boolean;
      description
        "Control Word";
    }

    leaf  flow-label{
      type boolean;
      description
        "Flow Label";
    }

    leaf vni-evi {
      type uint32;
      description
        "VNI/EVI associated with this network-instance";
    }

    leaf router-mac {
      type string;
      description
        "Router-Mac to be used for this network-instance";
    }

    leaf v4-deaggregation-labels-allocated {
      type uint32;
      description
        "Deaggregation labels allocated for all network-instsances in IPv4";
    }

    leaf v6-deaggregation-labels-allocated {
      type uint32;
      description
        "Deaggregation labels allocated for all network-instsances in IPv6";
    }

    leaf v4-per-nexthop-labels-allocated {
      type uint32;
      description
        "Per-nexthop labels allocated for all network-instsances in IPv4";
    }

    leaf v6-per-nexthop-labels-allocated {
      type uint32;
      description
        "Per-nexthop labels allocated for all network-instsances in IPv6";
    }

    leaf v4-per-prefix-labels-allocated {
      type uint32;
      description
        "Per-prefix labels allocated for all network-instsances in IPv4";
    }

    leaf v6-per-prefix-labels-allocated {
      type uint32;
      description
        "Per-prefix labels allocated for all network-instsances in IPv6";
    }

    leaf network-instances-present {
      type uint32;
      description
        "Number of netwrok-instances present in BGP";
    }

    leaf platform-locator-length {
      type uint32;
      description
        "Platform locator length to be used for External TCAM";
    }

    uses route-targets-state;
    uses global-shutdown-protocol-config {
      when "../../../../../oc-netinst:config/oc-netinst:name = 'default'";
    }
    uses global-silent-drop-config {
      when "../../../../../oc-netinst:config/oc-netinst:name = 'default'";
    }
    uses global-drop-upon-invalid-sr-policy-config {
      when "../../../../../oc-netinst:config/oc-netinst:name = 'default'";
    }
    uses global-adj-rib-out-post-config {
      when "../../../../../oc-netinst:config/oc-netinst:name = 'default'";
    }
  }

  grouping bgp-mup-resolve-st1-sid-config {
    leaf enabled {
      type boolean;
      must "((not(boolean(/oc-netinst:network-instances/oc-netinst:network-instance[oc-netinst:name=current()/../../../../../../../../../../../oc-netinst:name]" +
           "/oc-netinst:protocols/oc-netinst:protocol/oc-netinst:bgp" +
           "/oc-netinst:global/oc-netinst:afi-safis/oc-netinst:afi-safi[oc-netinst:afi-safi-name='oc-bgp-types:IPV4_UNICAST']" +
           "/arc-oc-bgp-aug:resolve/arc-oc-bgp-aug:st1/arc-oc-bgp-aug:sid/arc-oc-bgp-aug:config/arc-oc-bgp-aug:enabled) = 'true' and" +
           "(boolean(/oc-netinst:network-instances/oc-netinst:network-instance[oc-netinst:name=current()/../../../../../../../../../../../oc-netinst:name]" +
           "/oc-netinst:protocols/oc-netinst:protocol/oc-netinst:bgp" +
           "/oc-netinst:global/oc-netinst:afi-safis/oc-netinst:afi-safi[oc-netinst:afi-safi-name='arc-oc-bgp-types:IPV4_MUP']" +
           "/arc-oc-bgp-aug:resolve/arc-oc-bgp-aug:st1/arc-oc-bgp-aug:sid/arc-oc-bgp-aug:config/arc-oc-bgp-aug:enabled) = 'true'))))" {
        error-message "Resolve ST1 SID can be enabled in only one afi-safi";
      }
      must "((not(boolean(/oc-netinst:network-instances/oc-netinst:network-instance[oc-netinst:name=current()/../../../../../../../../../../../oc-netinst:name]" +
           "/oc-netinst:protocols/oc-netinst:protocol/oc-netinst:bgp" +
           "/oc-netinst:global/oc-netinst:afi-safis/oc-netinst:afi-safi[oc-netinst:afi-safi-name='oc-bgp-types:IPV6_UNICAST']" +
           "/arc-oc-bgp-aug:resolve/arc-oc-bgp-aug:st1/arc-oc-bgp-aug:sid/arc-oc-bgp-aug:config/arc-oc-bgp-aug:enabled) = 'true' and" +
           "(boolean(/oc-netinst:network-instances/oc-netinst:network-instance[oc-netinst:name=current()/../../../../../../../../../../../oc-netinst:name]" +
           "/oc-netinst:protocols/oc-netinst:protocol/oc-netinst:bgp" +
           "/oc-netinst:global/oc-netinst:afi-safis/oc-netinst:afi-safi[oc-netinst:afi-safi-name='arc-oc-bgp-types:IPV6_MUP']" +
           "/arc-oc-bgp-aug:resolve/arc-oc-bgp-aug:st1/arc-oc-bgp-aug:sid/arc-oc-bgp-aug:config/arc-oc-bgp-aug:enabled) = 'true'))))" {
        error-message "Resolve ST1 SID can be enabled in only one afi-safi";
      }
      description
        "Enable/Disable resolve ST1 SID";
    }
  }

  grouping bgp-mup-resolve-st1-top {
    container st1 {
      container sid {
        container config {
          uses bgp-mup-resolve-st1-sid-config;
          description
            "MUP network segment resolve ST1 SID configuration";
        }
        container state {
          config false;
          uses bgp-mup-resolve-st1-sid-config;
          description
            "MUP network segment resolve ST1 SID state";
        }
      }
    }
  }

  grouping bgp-mup-resolve-st2-sid-config {
    leaf enabled {
      type boolean;
      description
        "Enable/Disable resolve ST2 SID";
    }
  }

  grouping bgp-mup-resolve-st2-top {
    container st2 {
      container sid {
        container config {
          uses bgp-mup-resolve-st2-sid-config;
          description
            "MUP network segment resolve ST2 SID configuration";
        }
        container state {
          config false;
          uses bgp-mup-resolve-st2-sid-config;
          description
            "MUP network segment resolve ST2 SID state";
        }
      }
    }
  }

  grouping bgp-mup-resolution-top {
    container resolve {
      uses bgp-mup-resolve-st1-top {
        description
          "ST1 route resolution";
      }
      uses bgp-mup-resolve-st2-top {
        when "../../../../../../../oc-netinst:name != 'default' and " +
             "(derived-from-or-self(../oc-netinst:afi-safi-name, 'arc-oc-bgp-types:IPV4_MUP') or " +
             "derived-from-or-self(../oc-netinst:afi-safi-name, 'arc-oc-bgp-types:IPV6_MUP'))";
        description
          "ST2 route resolution";
      }
    }
  }

  grouping afi-safi-best-path-timer-config {
    leaf min-delay {
      type uint32;
      units microseconds;
      description
        "Time in microseconds to wait to compute best path.";
    }
    leaf max-delay {
      type uint32;
      units microseconds;
      description
        "Max time in microseconds to wait to force best path recomputation.";
    }
    leaf pacing {
      type uint32;
      units microseconds;
      description
        "Time in microseconds to yield between subsequent bestpath computation.";
    }
  }
  grouping afi-safi-best-path-timers-top {
    container best-path {
      description
        "This container defines mup best-path timers.";

      container config {
        description
          "This container defines mup best-path timers.";

        uses afi-safi-best-path-timer-config;
      }
      container state {
        config false;
        description
          "Mup best-path timer state.";

        uses afi-safi-best-path-timer-config;
      }
    }
  }

  grouping bgp-afi-safi-timers-top {
    container timers {
      uses afi-safi-best-path-timers-top;
    }
  }

  augment "/oc-netinst:network-instances/oc-netinst:network-instance" +
          "/oc-netinst:protocols/oc-netinst:protocol/oc-netinst:bgp" +
          "/oc-netinst:global/oc-netinst:afi-safis/oc-netinst:afi-safi" {
    uses common-maximum-paths;
    uses bgp-mup-resolution-top {
      when "../../../../../../oc-netinst:name != 'default'" +
           "and (oc-netinst:afi-safi-name = 'oc-bgp-types:IPV4_UNICAST' " +
           "or oc-netinst:afi-safi-name = 'oc-bgp-types:IPV6_UNICAST' " +
           "or oc-netinst:afi-safi-name = 'arc-oc-bgp-types:IPV4_MUP' " +
           "or oc-netinst:afi-safi-name = 'arc-oc-bgp-types:IPV6_MUP')";
    }
    uses af-reoriginate-top {
      when "(../../../../../../oc-netinst:name != 'default' and " +
           "(derived-from-or-self(./oc-netinst:afi-safi-name, 'oc-bgp-types:IPV4_UNICAST') or " +
           "derived-from-or-self(./oc-netinst:afi-safi-name, 'oc-bgp-types:IPV6_UNICAST')))" {
        description
          "Reoriginate MUP ST1 only for IPv4/IPv6 Unicast in
           non-default network instance.";
      }
    }
    uses af-mup-compatibility-top {
      when "(/arc-features:features" +
           "/arc-features:feature[arc-features:name='arc-features:ARCOS_SRV6_MUP']" +
           "/arc-features:supported = 'true') and " +
           "(../../../../../../oc-netinst:name != 'default' and " +
           "(derived-from-or-self(./oc-netinst:afi-safi-name, 'arc-oc-bgp-types:IPV4_MUP') or " +
           "derived-from-or-self(./oc-netinst:afi-safi-name, 'arc-oc-bgp-types:IPV6_MUP')))" {
        description
          "MUP compatibility only for IPv4/IPv6 MUP in non-default network instance.";
      }
    }
  }

  augment "/oc-netinst:network-instances/oc-netinst:network-instance" +
          "/oc-netinst:protocols/oc-netinst:protocol/oc-netinst:bgp" +
          "/oc-netinst:global/oc-netinst:afi-safis/oc-netinst:afi-safi" { 
    uses aggregate-address-top;
    uses bgp-common-mp-ipv4-mup-group;
    uses bgp-common-mp-ipv6-mup-group;
  }

  augment "/oc-netinst:network-instances/oc-netinst:network-instance" +
          "/oc-netinst:protocols/oc-netinst:protocol" +
          "/oc-netinst:bgp" +
          "/oc-netinst:global/oc-netinst:afi-safis/oc-netinst:afi-safi" {
    uses rtfilter-global-config-top {
      when "oc-netinst:afi-safi-name = 'arc-oc-bgp-types:RTFILTER' ";
    }
  }

  augment "/oc-netinst:network-instances/oc-netinst:network-instance" +
          "/oc-netinst:protocols/oc-netinst:protocol" +
          "/oc-netinst:bgp" +
          "/oc-netinst:global/oc-netinst:afi-safis/oc-netinst:afi-safi" {
    uses rtfilter-af-config-top {
      when "oc-netinst:afi-safi-name = 'oc-bgp-types:L3VPN_IPV4_UNICAST'" +
        "or oc-netinst:afi-safi-name = 'oc-bgp-types:L3VPN_IPV6_UNICAST'" +
        "or oc-netinst:afi-safi-name = 'oc-bgp-types:L2VPN_EVPN'" +
        "or oc-netinst:afi-safi-name = 'arc-oc-bgp-types:IPV4_MUP'" +
        "or oc-netinst:afi-safi-name = 'arc-oc-bgp-types:IPV6_MUP'";
    }
  }

  augment "/oc-netinst:network-instances/oc-netinst:network-instance" +
          "/oc-netinst:protocols/oc-netinst:protocol" +
          "/oc-netinst:bgp" +
          "/oc-netinst:global/oc-netinst:afi-safis/oc-netinst:afi-safi" {
    uses default-information-originate-top;
  }

  augment "/oc-netinst:network-instances/oc-netinst:network-instance" +
          "/oc-netinst:protocols/oc-netinst:protocol" +
          "/oc-netinst:bgp" +
          "/oc-netinst:global" {
    uses srv6-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:ipv4-unicast"{
    uses ipv4-network-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:ipv6-unicast"{
    uses ipv6-network-top;
  }

  augment "/oc-netinst:network-instances/oc-netinst:network-instance" +
          "/oc-netinst:protocols/oc-netinst:protocol" +
          "/oc-netinst:bgp" +
          "/oc-netinst:global/oc-netinst:afi-safis/oc-netinst:afi-safi" +
          "/arc-oc-bgp-aug:rtfilter-global"{
    uses rtfilter-network-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:state" {
    uses af-version-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:state" {
    uses af-state-top;
  }

  augment "/oc-netinst:network-instances/oc-netinst:network-instance" +
          "/oc-netinst:protocols/oc-netinst:protocol" +
          "/oc-netinst:bgp" +
          "/oc-netinst:global/oc-netinst:afi-safis/oc-netinst:afi-safi" {
    uses arc-bgp-auto-peer-grp:bgp-auto-peer-group-list;
  }

  augment "/oc-netinst:network-instances/oc-netinst:network-instance" +
          "/oc-netinst:protocols/oc-netinst:protocol" +
          "/oc-netinst:bgp" +
          "/oc-netinst:global" {
    uses memory-counters-top;
  }

  augment "/oc-netinst:network-instances/oc-netinst:network-instance" +
          "/oc-netinst:protocols/oc-netinst:protocol" +
          "/oc-netinst:bgp" +
          "/oc-netinst:global/oc-netinst:afi-safis/oc-netinst:afi-safi" {
    uses memory-counters-top;
  }

  augment "/oc-netinst:network-instances/oc-netinst:network-instance" +
          "/oc-netinst:protocols/oc-netinst:protocol" +
          "/oc-netinst:bgp" +
          "/oc-netinst:global/oc-netinst:route-selection-options" +
          "/oc-netinst:config" {
    uses bestpath-selection-top;
  }

  augment "/oc-netinst:network-instances/oc-netinst:network-instance" +
          "/oc-netinst:protocols/oc-netinst:protocol" +
          "/oc-netinst:bgp" +
          "/oc-netinst:global/oc-netinst:route-selection-options" +
          "/oc-netinst:state" {
    uses bestpath-selection-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:state" {
    uses selection-deferral-time-expire-state;
  }

  augment "/oc-netinst:network-instances/oc-netinst:network-instance" +
          "/oc-netinst:protocols/oc-netinst:protocol" +
          "/oc-netinst:bgp" +
          "/oc-netinst:global/oc-netinst:afi-safis/oc-netinst:afi-safi" {
    uses af-telemetry-top;
  }

  augment "/oc-netinst:network-instances/oc-netinst:network-instance" +
          "/oc-netinst:protocols/oc-netinst:protocol" +
          "/oc-netinst:bgp" +
          "/oc-netinst:global/oc-netinst:afi-safis/oc-netinst:afi-safi" {
    uses bgp-afi-safi-timers-top;
  }

  augment "/oc-netinst:network-instances/oc-netinst:network-instance" +
          "/oc-netinst:protocols/oc-netinst:protocol" +
          "/oc-netinst:bgp/oc-netinst:global" {
    uses global-telemetry-top {
      when "../../../../oc-netinst:name = 'default'" {
        description
          "Allow global telemetry configs in network-instance default only";
      }
    }
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:config" {
    uses route-target-retain-config {
      when "oc-netinst:afi-safi-name = 'oc-bgp-types:L2VPN_EVPN' " +
        "or oc-netinst:afi-safi-name = 'oc-bgp-types:L3VPN_IPV4_UNICAST' " +
        "or oc-netinst:afi-safi-name = 'oc-bgp-types:L3VPN_IPV6_UNICAST' " +
        "or oc-netinst:afi-safi-name = 'arc-oc-bgp-types:IPV4_MUP' " +
        "or oc-netinst:afi-safi-name = 'arc-oc-bgp-types:IPV6_MUP' " {
        description
          "Retain VPN routes with all route-targets";
      }
    }
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:config" {
    uses advertise-best-external-config;
    uses global-update-wait-data-plane-config {
      when "oc-netinst:afi-safi-name = 'oc-bgp-types:IPV4_UNICAST' " +
        "or oc-netinst:afi-safi-name = 'oc-bgp-types:IPV6_UNICAST'" {
        description
          "Defer BGP update generation under specific AFI/SAFI";
      }
    }
  }

  /*
   * Augmenetations for neighbor.
   */
  grouping bgp-neighbor-configs-top {
    uses disable-fast-deactivation-config;
    uses ttl-security-hops-config;
    uses shutdown-config;
    uses dscp-config;
    uses enforce-first-as-config;
  }

  grouping bgp-neighbor-states-top {
    uses hold-timer-expiration-state;
    uses keepalive-timer-expiration-state;
    uses remote-router-id-state;
    uses received-peer-as-state;
    uses neighbor-index-state;
    uses disable-fast-deactivation-config;
    uses ttl-security-hops-state;
    uses shutdown-config;
    uses shutdown-reason-top;
    uses state-reason-top;
    uses session-last-reset-state;
    uses session-elapsed-time-state;
    uses dscp-config;
    uses enforce-first-as-config;
  }

  grouping bgp-neighbor-transport-state-aug-top {
    leaf negotiated-tcp-mss {
      type uint16;
      description
        "TCP MSS negotiated with the neighbor";
    }
  }

  grouping nbr-timers-config {
    leaf update-delay-time {
      type decimal64 {
        fraction-digits 2;
        range "1..3600";
      }
      units seconds;
      description
        "Time in seconds that the first update is delayed
         for a BGP session after it becomes ESTABLISHED.";
    }
  }

  augment "/oc-netinst:network-instances/oc-netinst:network-instance" +
          "/oc-netinst:protocols/oc-netinst:protocol" +
          "/oc-netinst:bgp" +
          "/oc-netinst:neighbors/oc-netinst:neighbor" +
          "/oc-netinst:config" {
    uses bgp-neighbor-configs-top;
  }

  augment "/oc-netinst:network-instances/oc-netinst:network-instance" +
          "/oc-netinst:protocols/oc-netinst:protocol" +
          "/oc-netinst:bgp" +
          "/oc-netinst:neighbors/oc-netinst:neighbor" +
          "/oc-netinst:state" {
    uses bgp-neighbor-states-top;
  }

  augment "/oc-netinst:network-instances/oc-netinst:network-instance" +
          "/oc-netinst:protocols/oc-netinst:protocol" +
          "/oc-netinst:bgp/oc-netinst:neighbors" +
          "/oc-netinst:neighbor/oc-netinst:transport" +
          "/oc-netinst:state" {
    uses bgp-neighbor-transport-state-aug-top;
  }

  augment "/oc-netinst:network-instances/oc-netinst:network-instance" +
          "/oc-netinst:protocols/oc-netinst:protocol" +
          "/oc-netinst:bgp" +
          "/oc-netinst:neighbors/oc-netinst:neighbor" +
          "/oc-netinst:state/oc-netinst:messages/oc-netinst:sent" {
    uses message-counter-state;
  }

  augment "/oc-netinst:network-instances/oc-netinst:network-instance" +
          "/oc-netinst:protocols/oc-netinst:protocol" +
          "/oc-netinst:bgp" +
          "/oc-netinst:neighbors/oc-netinst:neighbor" +
          "/oc-netinst:state/oc-netinst:messages/oc-netinst:received" {
    uses message-counter-state;
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:state/arc-oc-bgp-aug:messages/arc-oc-bgp-aug:sent" {
    uses message-counter-state;
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:state/arc-oc-bgp-aug:messages/arc-oc-bgp-aug:received" {
    uses message-counter-state;
  }

  augment "/oc-netinst:network-instances/oc-netinst:network-instance" +
          "/oc-netinst:protocols/oc-netinst:protocol" +
          "/oc-netinst:bgp" +
          "/oc-netinst:neighbors/oc-netinst:neighbor" +
          "/oc-netinst:timers/oc-netinst:config" {
    uses nbr-timers-config;
  }

  augment "/oc-netinst:network-instances/oc-netinst:network-instance" +
          "/oc-netinst:protocols/oc-netinst:protocol" +
          "/oc-netinst:bgp" +
          "/oc-netinst:neighbors/oc-netinst:neighbor" +
          "/oc-netinst:timers/oc-netinst:state" {
    uses nbr-timers-config;
  }

  augment "/oc-netinst:network-instances/oc-netinst:network-instance" +
          "/oc-netinst:protocols/oc-netinst:protocol" +
          "/oc-netinst:bgp" +
          "/oc-netinst:neighbors/oc-netinst:neighbor" {
    uses ebgp-local-as-top;
    uses graceful-shutdown-top;
    uses bfd-top;
    uses epe-top;
    uses nbr-srv6-top;
    uses route-server-top;
    uses peer-as-range-top;
  }
  augment "/oc-netinst:network-instances/oc-netinst:network-instance" +
          "/oc-netinst:protocols/oc-netinst:protocol" +
          "/oc-netinst:bgp" +
          "/oc-netinst:neighbors/oc-netinst:neighbor" +
          "/arc-oc-bgp-aug:egress-peer-engineering" +
          "/arc-oc-bgp-aug:labeled-unicast/arc-oc-bgp-aug:state" {
    uses labeled-unicast-epe-next-hop-state;
  }

  augment "/oc-netinst:network-instances/oc-netinst:network-instance" +
          "/oc-netinst:protocols/oc-netinst:protocol" +
          "/oc-netinst:bgp" +
          "/oc-netinst:neighbors/oc-netinst:neighbor" +
          "/oc-netinst:graceful-restart/oc-netinst:state" {
    uses restart-timer-expire-state;
    uses stale-routes-timer-expire-state;
  }


  /*
   * Augmentations for neighbor AF.
   */
  grouping nbr-af-config-top {
    uses nbr-af-next-hop-top;
    uses nbr-af-send-tracker-sid-top;
    uses soft-reconfig-config-top;
  }

  grouping nbr-af-state-top {
    uses nbr-af-next-hop-top;
    uses nbr-af-send-tracker-sid-top;
    uses soft-reconfig-state-top;
    uses nbr-af-version-top;
    uses nbr-af-update-gen-stats;
    leaf end-of-rib-received {
      type boolean;
      description
        "End-of-RIB marker has been received from the neighbor
        for the address-family";
    }
    leaf nbr-af-state {
      type string;
      description
        "Neighbor AF object state: NORMAL, CLEANUP_TRIGGER, CLEANUP_WAIT, CLEANUP_SYNC, DELETE_PENDING";
    }

    leaf nbr-af-flags {
      type uint32;
      description
        "Neighbor AF object flags in hex: CLEANUP=0x1, DELETE=0x2, REVIVE=0x4";
    }
  }

  augment "/oc-netinst:network-instances/oc-netinst:network-instance" +
          "/oc-netinst:protocols/oc-netinst:protocol" +
          "/oc-netinst:bgp" +
          "/oc-netinst:neighbors/oc-netinst:neighbor/oc-netinst:afi-safis" +
          "/oc-netinst:afi-safi/oc-netinst:config" {
    uses nbr-af-config-top;
  }

  augment "/oc-netinst:network-instances/oc-netinst:network-instance" +
          "/oc-netinst:protocols/oc-netinst:protocol" +
          "/oc-netinst:bgp" +
          "/oc-netinst:neighbors/oc-netinst:neighbor/oc-netinst:afi-safis" +
          "/oc-netinst:afi-safi/oc-netinst:state" {
    uses nbr-af-state-top;
  }

  augment "/oc-netinst:network-instances/oc-netinst:network-instance" +
          "/oc-netinst:protocols/oc-netinst:protocol" +
          "/oc-netinst:bgp" +
          "/oc-netinst:neighbors/oc-netinst:neighbor" +
          "/oc-netinst:afi-safis/oc-netinst:afi-safi/oc-netinst:state/oc-netinst:prefixes" {
    uses nbr-af-prefixes-top;
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:config" {
    uses oc-mpls:mpls-global_config {
      when "oc-netinst:afi-safi-name = 'oc-bgp-types:IPV4_LABELED_UNICAST' " +
           "or oc-netinst:afi-safi-name = 'oc-bgp-types:IPV6_LABELED_UNICAST'" {
        description
          "Explicit/Implicit null configuration under specific AFI/SAFI";
      }
    }
    uses disable-rib-resolution-config {
      when "oc-netinst:afi-safi-name = 'oc-bgp-types:IPV4_LABELED_UNICAST' " +
           "or oc-netinst:afi-safi-name = 'oc-bgp-types:IPV6_LABELED_UNICAST'" {
        description
          "Enable/Disable BGP route resolution in RIB under specific AFI/SAFI";
      }
    }
  }

  augment "/oc-netinst:network-instances/oc-netinst:network-instance" +
          "/oc-netinst:protocols/oc-netinst:protocol" +
          "/oc-netinst:bgp" +
          "/oc-netinst:neighbors/oc-netinst:neighbor" +
          "/oc-netinst:afi-safis/oc-netinst:afi-safi" {
    uses nbr-af-add-paths-top;
    uses nbr-af-extended-nexthop-top;
    uses bgp-aigp-top;
    uses default-originate-top;
    uses nbr-af-advertise-reoriginated-top {
      when "(/arc-features:features" +
           "/arc-features:feature[arc-features:name='arc-features:ARCOS_SRV6_MUP']" +
           "/arc-features:supported = 'true') and " +
           "(derived-from-or-self(./oc-netinst:afi-safi-name, 'oc-bgp-types:L3VPN_IPV4_UNICAST') or " +
           "derived-from-or-self(./oc-netinst:afi-safi-name, 'oc-bgp-types:L3VPN_IPV6_UNICAST') or " +
           "(../../../../../../../oc-netinst:name != 'default' and " +
           "(derived-from-or-self(./oc-netinst:afi-safi-name, 'oc-bgp-types:IPV4_UNICAST') or " +
           "derived-from-or-self(./oc-netinst:afi-safi-name, 'oc-bgp-types:IPV6_UNICAST'))))" {
        description
          "Advertise reoriginated MUP ST1 only for IPv4/IPv6 Unicast in
           non-default network instance or L3VPN IPV4/IPV6 unicast in default
           network instance.";
      }
    }
  }

  augment "/oc-netinst:network-instances/oc-netinst:network-instance" +
          "/oc-netinst:protocols/oc-netinst:protocol" +
          "/oc-netinst:bgp" +
          "/oc-netinst:neighbors/oc-netinst:neighbor" +
          "/oc-netinst:afi-safis/oc-netinst:afi-safi" {
    uses nbr-af-rtfilter-top;
  }

  augment "/oc-netinst:network-instances/oc-netinst:network-instance" +
          "/oc-netinst:protocols/oc-netinst:protocol" +
          "/oc-netinst:bgp" +
          "/oc-netinst:peer-groups/oc-netinst:peer-group" +
          "/oc-netinst:afi-safis/oc-netinst:afi-safi" {
    uses nbr-af-rtfilter-top;
  }

  grouping route-targets-state {
    leaf evpn-l2-import-route-targets {
      type string;
      description
        "import route-targets for this network-instance";
    }

    leaf evpn-v4-import-route-targets {
      type string;
      description
        "import route-targets for this network-instance";
    }

    leaf evpn-v6-import-route-targets {
      type string;
      description
        "import route-targets for this network-instance";
    }

    leaf vpn-v4-import-route-targets {
      type string;
      description
        "import route-targets for this network-instance";
    }

    leaf vpn-v6-import-route-targets {
      type string;
      description
        "import route-targets for this network-instance";
    }

    leaf evpn-l2-export-route-targets {
      type string;
      description
        "export route-targets for this network-instance";
    }

    leaf evpn-v4-export-route-targets {
      type string;
      description
        "export route-targets for this network-instance";
    }

    leaf evpn-v6-export-route-targets {
      type string;
      description
        "export route-targets for this network-instance";
    }

    leaf vpn-v4-export-route-targets {
      type string;
      description
        "export route-targets for this network-instance";
    }

    leaf vpn-v6-export-route-targets {
      type string;
      description
        "export route-targets for this network-instance";
    }
    
    leaf fs-vpn-v4-import-route-targets {
      type string;
      description
        "FS import route-targets for this network-instance";
    }

    leaf fs-vpn-v6-import-route-targets {
      type string;
      description
        "FS import route-targets for this network-instance";
    }

    leaf fs-vpn-v4-export-route-targets {
      type string;
      description
        "FS export route-targets for this network-instance";
    }

    leaf fs-vpn-v6-export-route-targets {
      type string;
      description
        "FS export route-targets for this network-instance";
    }
  }

  grouping route-target-config {

    description
      "Configuration data for route-targets";
    leaf route-target {
      type oc-netinst-types:route-target;
      description
       "A Route Target is an 8-octet BGP extended community
        initially identifying a set of sites in a BGP VPN
        (RFC 4364).  However, it has since taken on a more general
        role in BGP route filtering.  A Route Target consists of two
        or three fields: a 2-octet Type field, an administrator
        field, and, optionally, an assigned number field.

        According to the data formats for types 0, 1, 2, and 6 as
        defined in RFC 4360, RFC 5668, and RFC 7432, the encoding
        pattern is defined as:

        0:2-octet-asn:4-octet-number
        1:4-octet-ipv4addr:2-octet-number
        2:4-octet-asn:2-octet-number
        6:6-octet-mac-address

        Additionally, a generic pattern is defined for future
        Route Target types:

        2-octet-other-hex-number:6-octet-hex-number

        Some valid examples are 0:100:100, 1:1.1.1.1:100,
        2:1234567890:203, and 6:26:00:08:92:78:00.";
    }

    leaf route-target-type {
      description
        "Route Target type.";
      type oc-netinst-types:route-target-type;
    }
  }

  grouping suppress-rt5-routes-config {

    description
      "Top level grouping for suppress route-type-5 routes for export and import";

    leaf suppress-rt5-routes {
      type boolean;
      description
        "Suppress all EVPN type-5 routes for import and export.";
    }
  }

  grouping evpn-route-options-top {

    description
      "Top level grouping for EVPN route options under rt-afi-safi";

    container evpn-route-options {
      description
        "route options for EVPN routes";

      container config {
        uses suppress-rt5-routes-config;
      }

      container state {
        config false;
        uses suppress-rt5-routes-config;
      }
    }
  }

  grouping route-targets-top {

    description
      "Top level grouping for route-targets of a network-instance";

    container route-targets {
      description
        "route-targets for a network-instance";

      list route-target {
        key "route-target route-target-type";

        description
          "List of route-targets";

        leaf route-target {
          description
            "Reference to route-target key";
          type leafref {
            path "../config/route-target";
          }
        }

        leaf route-target-type {
          description
            "Reference to route-target type";
          type leafref {
            path "../config/route-target-type";
          }
        }

        container config {
          description
            "Configuration data for route-targets";
          uses route-target-config;
        }

        container state {
          description
            "Operational data for route-target configuration";
          config false;
          uses route-target-config;
        }
      }
    }
  }

  grouping rt-afi-safis-config {
    description
      "Configuration for address-family";

    leaf rt-afi-safi-name {
      type identityref {
        base oc-bgp-types:AFI_SAFI_TYPE;
      }

      must ". = 'oc-bgp-types:L2VPN_EVPN' or " +
           ". = 'oc-bgp-types:L3VPN_IPV4_UNICAST' or " +
           ". = 'oc-bgp-types:L3VPN_IPV6_UNICAST' or " +
           ". = 'arc-oc-bgp-types:IPV4_MUP' or " +
           ". = 'arc-oc-bgp-types:IPV6_MUP' or " +
           ". = 'arc-oc-bgp-types:L3VPN_IPV4_FLOWSPEC' or " +
           ". = 'arc-oc-bgp-types:L3VPN_IPV6_FLOWSPEC'" {
        error-message
          "only L2VPN_EVPN, VPN_IPV4/IPV6_UNICAST and IPV4/IPV6_MUP are supported";
      }

      description "AFI,SAFI";
    }
  }

  grouping rt-afi-safis-top {
    container rt-afi-safis {
      description
        "Enclosing container for address family list";

      list rt-afi-safi {
        key "rt-afi-safi-name";
        description
          "list of afi-safi types";

        leaf rt-afi-safi-name {
          type leafref {
            path "../config/rt-afi-safi-name";
          }
          description
            "Reference to the list key";
        }

        container config {
          description
            "Operational state data for the BGP list";

          uses rt-afi-safis-config;
        }

        container state {
          config false;
          description
            "Operational state data for the BGP list";

          uses rt-afi-safis-config;
        }
      }
    }
  }

  augment "/oc-netinst:network-instances/oc-netinst:network-instance" +
          "/oc-netinst:protocols/oc-netinst:protocol" +
          "/oc-netinst:bgp" +
          "/oc-netinst:global/oc-netinst:config" {
    uses global-config {
      when "../../../../../oc-netinst:name != 'default'" {
        description
          "Allow SRv6 global configs in network-instance default only";
      }
    }
    uses global-allocation-config;
  }

  /*
   * l2 route-targets - to be deprecated and folded under rt-afi-safi L2VPN_EVPN
   */
  augment "/oc-netinst:network-instances/oc-netinst:network-instance" +
          "/oc-netinst:protocols/oc-netinst:protocol" +
          "/oc-netinst:bgp" {
    uses route-targets-top {
      when "../../../oc-netinst:config/oc-netinst:type = 'oc-netinst-types:L2VLAN' or " +
           "../../../oc-netinst:config/oc-netinst:type = 'arc-oc-ni-types:L2P2P_EVPN' or " +
           "../../../oc-netinst:config/oc-netinst:type = 'arc-oc-ni-types:L2VLAN_AWARE_BUNDLE'" {
        description
          "L2 route-targets only supported for L2 network-instance";
      }
    }
    uses oc-rpol:apply-policy-group {
      when "../../../oc-netinst:config/oc-netinst:type = 'oc-netinst-types:L2VLAN' or " +
           "../../../oc-netinst:config/oc-netinst:type = 'arc-oc-ni-types:L2P2P_EVPN' or " +
           "../../../oc-netinst:config/oc-netinst:type = 'arc-oc-ni-types:L2VLAN_AWARE_BUNDLE'" {
        description
          "L2 route-targets only supported for L2 network-instance";
      }
    }
  }

  /*
   * l3 route-targets
   */
  augment "/oc-netinst:network-instances/oc-netinst:network-instance" +
          "/oc-netinst:protocols/oc-netinst:protocol" +
          "/oc-netinst:bgp" +
          "/oc-netinst:global/oc-netinst:afi-safis/oc-netinst:afi-safi" {
    uses rt-afi-safis-top {
      when "(../../../../../.." +
           "/oc-netinst:config/oc-netinst:type = 'oc-netinst-types:L3VRF' and " +
           "(oc-netinst:config/oc-netinst:afi-safi-name = 'oc-bgp-types:IPV4_UNICAST' or " +
           "oc-netinst:config/oc-netinst:afi-safi-name = 'oc-bgp-types:IPV6_UNICAST' or " +
           "oc-netinst:config/oc-netinst:afi-safi-name = 'arc-oc-bgp-types:IPV4_MUP' or " +
           "oc-netinst:config/oc-netinst:afi-safi-name = 'arc-oc-bgp-types:IPV6_MUP' or " +
           "oc-netinst:config/oc-netinst:afi-safi-name = 'arc-oc-bgp-types:IPV4_FLOWSPEC' or " +
           "oc-netinst:config/oc-netinst:afi-safi-name = 'arc-oc-bgp-types:IPV6_FLOWSPEC')) or " +
           "(not(derived-from-or-self(../../../../../../oc-netinst:config/oc-netinst:type, " +
           "'oc-netinst-types:L3VRF')) and " +
           "(derived-from-or-self(oc-netinst:config/oc-netinst:afi-safi-name, " +
           "'oc-bgp-types:L2VPN_EVPN')))" {
        description
          "route-targets only supported for IPV4/IPV6_UNICAST, IPV4/IPV6 FLOWSPEC or " +
          "IPV4/IPV6_MUP or L2VPN_EVPN";
      }
    }
  }

  augment "/oc-netinst:network-instances/oc-netinst:network-instance" +
          "/oc-netinst:protocols/oc-netinst:protocol" +
          "/oc-netinst:bgp/oc-netinst:global" +
          "/oc-netinst:afi-safis/oc-netinst:afi-safi" +
          "/arc-oc-bgp-aug:rt-afi-safis/arc-oc-bgp-aug:rt-afi-safi" {
    uses route-targets-top {
         description
           "Per RT-AF route-targets in network-instance afi-safis";
    }
    uses oc-rpol:apply-policy-group {
         description
           "Per RT-AF import/export policies";
    }
    uses evpn-route-options-top {
      when "(../arc-oc-bgp-aug:rt-afi-safi/arc-oc-bgp-aug:rt-afi-safi-name = 'oc-bgp-types:L2VPN_EVPN')" {
        description
          "Route options specific to EVPN";
      }
    }
  }

  /*
   * Augmentations for peer-group commands
   */
  grouping peer-group-members-state {
    leaf neighbor-count {
      type uint32;
      description
        "Number of neigbors in this peer-group";
    }
    leaf-list neighbors {
      type string;
      description
        "List of neighbors in the peer-group";
    }
    leaf dynamic-neighbor-count {
      type uint32;
      description
        "Number of neigbors in this peer-group";
    }
    leaf-list dynamic-neighbors {
      type string;
      description
        "List of neighbors in the peer-group";
    }
  }

  augment "/oc-netinst:network-instances/oc-netinst:network-instance" +
          "/oc-netinst:protocols/oc-netinst:protocol" +
          "/oc-netinst:bgp" +
          "/oc-netinst:peer-groups/oc-netinst:peer-group/oc-netinst:state" {
    uses peer-group-members-state;
  }

  augment "/oc-netinst:network-instances/oc-netinst:network-instance" +
          "/oc-netinst:protocols/oc-netinst:protocol" +
          "/oc-netinst:bgp" +
          "/oc-netinst:peer-groups/oc-netinst:peer-group/oc-netinst:config" {
    uses bgp-neighbor-configs-top;
  }

  augment "/oc-netinst:network-instances/oc-netinst:network-instance" +
          "/oc-netinst:protocols/oc-netinst:protocol" +
          "/oc-netinst:bgp" +
          "/oc-netinst:peer-groups/oc-netinst:peer-group/oc-netinst:state" {
    uses bgp-neighbor-configs-top;
  }

  augment "/oc-netinst:network-instances/oc-netinst:network-instance" +
          "/oc-netinst:protocols/oc-netinst:protocol" +
          "/oc-netinst:bgp" +
          "/oc-netinst:peer-groups/oc-netinst:peer-group" {
    uses ebgp-local-as-top;
    uses graceful-shutdown-top;
    uses bfd-top;
    uses epe-top;
    uses nbr-srv6-top;
    uses route-server-top;
    uses peer-as-range-top;
  }

  augment "/oc-netinst:network-instances/oc-netinst:network-instance" +
          "/oc-netinst:protocols/oc-netinst:protocol" +
          "/oc-netinst:bgp" +
          "/oc-netinst:peer-groups/oc-netinst:peer-group" +
          "/oc-netinst:afi-safis/oc-netinst:afi-safi/oc-netinst:config" {
    uses nbr-af-config-top;
  }

  augment "/oc-netinst:network-instances/oc-netinst:network-instance" +
          "/oc-netinst:protocols/oc-netinst:protocol" +
          "/oc-netinst:bgp" +
          "/oc-netinst:peer-groups/oc-netinst:peer-group" +
          "/oc-netinst:afi-safis/oc-netinst:afi-safi/oc-netinst:state" {
    uses nbr-af-config-top;
  }

  augment "/oc-netinst:network-instances/oc-netinst:network-instance" +
          "/oc-netinst:protocols/oc-netinst:protocol" +
          "/oc-netinst:bgp" +
          "/oc-netinst:peer-groups/oc-netinst:peer-group" +
          "/oc-netinst:afi-safis/oc-netinst:afi-safi" {
    uses nbr-af-add-paths-top;
    uses bgp-aigp-top;
    uses nbr-af-extended-nexthop-top;
    uses default-originate-top;
    uses nbr-af-advertise-reoriginated-top {
      when "(/arc-features:features" +
           "/arc-features:feature[arc-features:name='arc-features:ARCOS_SRV6_MUP']" +
           "/arc-features:supported = 'true') and " +
           "(./oc-netinst:afi-safi-name = 'oc-bgp-types:L3VPN_IPV4_UNICAST' or " +
           "./oc-netinst:afi-safi-name = 'oc-bgp-types:L3VPN_IPV6_UNICAST' or " +
           "(../../../../../../../oc-netinst:name != 'default' and " +
           "(./oc-netinst:afi-safi-name = 'oc-bgp-types:IPV4_UNICAST' or " +
           "./oc-netinst:afi-safi-name = 'oc-bgp-types:IPV6_UNICAST')))" {
        description
          "Advertise reoriginated MUP ST1 only for IPv4/IPv6 Unicast in
           non-default network instance or L3VPN IPV4/IPV6 unicast in default
           network instance.";
      }
    }
  }

  /*
   * Dynamic neighbor prefixes.
   */
  grouping bgp-dynamic-neighbor-config {
    description
      "Configuration parameters relating to an individual prefix from
      which dynamic neighbors are accepted.";

    leaf prefix {
      type inet:ip-prefix;
      description
        "The IP prefix within which the source address of the remote
        BGP speaker must fall to be considered eligible to the
        dynamically configured.";
    }

    leaf neighbor-limit {
      type uint32 {
        range "1..5000";
      }
      description
        "Maximum number of dynamic neighbors allowed under this prefix";
    }

    leaf peer-group {
      type leafref {
        path "/oc-netinst:network-instances/oc-netinst:network-instance" +
             "/oc-netinst:protocols/oc-netinst:protocol" +
             "/oc-netinst:bgp/oc-netinst:peer-groups/oc-netinst:peer-group" +
             "/oc-netinst:config/oc-netinst:peer-group-name";
      }
      description
        "The peer-group within which the dynamic neighbor will be
        configured.  The configuration parameters used for the dynamic
        neighbor are those specified within the referenced peer
        group.";
    }
  }

  grouping dynamic-neighbor-states {
    description
      "State data for dynamic-neighbors";
    leaf local-address-set {
      type boolean;
      description
        "Is the listener active for this prefix.";
    }
    leaf neighbor-count {
      type uint16;
      description
        "Number of neighbor instances under this prefix.";
    }
    leaf-list neighbors {
      type inet:ip-address;
      description
        "Dyanmic neighbor instances.";
    }
  }

  grouping dynamic-neighbor-prefixes-top {
    container dynamic-neighbor-prefixes {
      description
        "A list of IP prefixes from which the system should:
          - Accept connections to the BGP daemon
          - Dynamically configure a BGP neighbor corresponding to the
            source address of the remote system, using the parameters
            of the specified peer-group.
         For such neighbors, an entry within the neighbor list should
         be created, indicating that the peer was dynamically
         configured, and referencing the peer-group from which the
         configuration was derived.";

      list dynamic-neighbor-prefix {
        key "prefix";
        description
          "An individual prefix from which dynamic neighbor
          connections are allowed.";

        leaf prefix {
          type leafref {
            path "../config/prefix";
          }
          description
            "Reference to the IP prefix from which source connections
            are allowed for the dynamic neighbor group.";
        }

        container config {
          description
            "Configuration parameters relating to the source prefix
            for the dynamic BGP neighbor connections.";

          uses bgp-dynamic-neighbor-config;
        }

        container state {
          config false;
          description
            "Operational state parameters relating to the source
            prefix for the dynamic BGP neighbor connections.";

          uses bgp-dynamic-neighbor-config;
          uses dynamic-neighbor-states;
        }
      }
    }
  }

  augment "/oc-netinst:network-instances/oc-netinst:network-instance" +
          "/oc-netinst:protocols/oc-netinst:protocol" +
          "/oc-netinst:bgp" {
    uses dynamic-neighbor-prefixes-top;
  }

  /*
   * Augmentations for BGP all-neighbors subtree that is state-only, i.e.,
   * structurally identical to the bgp neighbor structure in OC but with
   * only the "state" containers and leafs.
   */
  grouping bgp-common-mp-afi-safi-config {
    description
      "Configuration parameters used for all BGP AFI-SAFIs";

    leaf afi-safi-name {
      type identityref {
        base oc-bgp-types:AFI_SAFI_TYPE;
      }
      description "AFI,SAFI";
    }

    leaf enabled {
      type boolean;
      description
        "This leaf indicates whether the IPv4 Unicast AFI,SAFI is
        enabled for the neighbour or group";
    }
  }

  grouping bgp-neighbor-afi-safi-state {
    description
      "Operational state parameters relating to an individual AFI,
      SAFI for a neighbor";

    leaf active {
      type boolean;
      description
        "This value indicates whether a particular AFI-SAFI has
        been succesfully negotiated with the peer. An AFI-SAFI
        may be enabled in the current running configuration, but a
        session restart may be required in order to negotiate the new
        capability.";
    }

    container prefixes {
      description "Prefix counters for the BGP session";
      leaf received {
        type uint32;
        description
          "The number of prefixes received from the neighbor";
      }

      leaf sent {
        type uint32;
        description
          "The number of prefixes advertised to the neighbor";
      }

      leaf installed {
        type uint32;
        description
          "The number of advertised prefixes installed in the
          Loc-RIB";
      }
    }
  }

  grouping bgp-common-mp-all-afi-safi-common {
    description
      "Grouping for configuration common to all AFI,SAFI";

    container prefix-limit {
      description
        "Configure the maximum number of prefixes that will be
        accepted from a peer";

        container state {
        description
          "State information relating to the prefix-limit for the
          AFI-SAFI";
        uses oc-bgp:bgp-common-mp-all-afi-safi-common-prefix-limit-config;
      }
    }
  }

  grouping bgp-evpn-vpws-interface-fsm-state {
    description
      "Grouping for EVPN-VPWS Interface Finite-State-Machine data";

    leaf current-state {
      type identityref {
        base arc-bgp-types:EVPN_VPWS_INTERFACE_FSM_STATE;
      }
      description
        "State-machine current state";
    }

    leaf previous-state {
      type identityref {
        base arc-bgp-types:EVPN_VPWS_INTERFACE_FSM_STATE;
      }
      description
        "State-machine previous state";
    }

    leaf last-event {
      type identityref {
        base arc-bgp-types:EVPN_VPWS_INTERFACE_FSM_EVENT;
      }
      description
        "State-machine last event";
    }

    leaf service-wait-timer-expiry {
      type uint32;
      description
        "Number of seconds until expiry of service-wait-timer";
    }

    leaf oper-wait-timer-expiry {
      type uint32;
      description
        "Number of seconds until expiry of oper-wait-timer";
    }

    leaf events {
      type yang:zero-based-counter32;
      description
        "State-machine total number of events";
    }

    leaf transitions {
      type yang:zero-based-counter32;
      description
        "State-machine total number of state transitions";
    }
  }

  grouping bgp-l2vpn-evpn-vpws-top {
    description
        "Top-level grouping for EVPN VPWS tables ";

    container bgp-l2vpn-evpn-vpws {
      config false;
      
      description
        "Enclosing container for list of vpws in the evpn-vpws
        table.";
      
      list vpws {
        key "network-instance local-sid";
        
        description
          "List of vpws in the table, keyed by the network-instance
          & local-sid.";
        
        uses bgp-evpn-vpws-common-keys;
        
        container state {
          description
            "Operational state data for vpws entries in the
            BGP EVPN-VPWS";
          
          leaf network-instance {
            description
              "Reference to network-instance";
            type leafref {
              path "/oc-netinst:network-instances" +
                   "/oc-netinst:network-instance" +
                   "/oc-netinst:name";
            }
          }

          leaf local-sid {
            type uint32;
            description
              "Local SID";
          }

          leaf remote-sid {
            type uint32;
            description
              "Remote SID";
          }
        
          leaf interface {
            type leafref {
              path "/oc-if:interfaces/oc-if:interface/oc-if:name";
            }
            description
              "Reference to a base interface";
          }

          leaf l2-mtu {
            type uint32;
            description
              "L2 Maximum Transmission Unit";
          }
        
          leaf esi {
            type yang:hex-string;
            description
              "Ethernet Segment Identifier";
          }
        
          leaf operation-status {
            type string;
            description
              "operational state UP or DOWN";
          }

          leaf is_control-word {
            type boolean;
            description
              "Control Word";
          }

          leaf link-loss-forwarding {
            type boolean;
            description
              "Link-loss-forwarding feature";
          }
        }

        container interface-fsm {
          description
            "EVPN-VPWS Interface Finite-State-Machine info";

          container state {
            description
              "Operational state data for EVPN-VPWS Interface Finite-State-Machine";

            uses bgp-evpn-vpws-interface-fsm-state;
          }
        }
      }
    }
  }

  grouping bgp-evpn-vpws-common-keys {
    description
      "Common references used in keys for EVPN VPWS entries";

    leaf network-instance {
      type leafref {
        path "../state/network-instance";
      }
      description
        "Network Instance";
    }

    leaf local-sid {
      type leafref {
        path "../state/local-sid";
      }
      description
        "Local SID";
    }
  }

  grouping bgp-common-mp-ipv4-ipv6-unicast-common {
    description
      "Common configuration that is applicable for IPv4 and IPv6
      unicast";

    // include common afi-safi options.
    uses bgp-common-mp-all-afi-safi-common;

    container state {
      description
        "State information for common IPv4 and IPv6 unicast
        parameters";
      uses oc-bgp:bgp-common-mp-ipv4-ipv6-unicast-common-config;
    }
  }

  grouping af-reoriginate-config {
    leaf enabled {
      type boolean;
      default false;
      description
        "When set to true, specified routes are reoriginated.";
    }
  }

  grouping af-mup-reoriginate-top {
    container mup-st1 {
      container config {
        uses af-reoriginate-config;
      }
      container state {
        config false;
        uses af-reoriginate-config;
      }
    }
  }

  grouping af-reoriginate-top {
    container reoriginate {
      container evpn-l3vpn-dci {
        container config {
          uses af-reoriginate-config;
        }
        container state {
          config false;
          uses af-reoriginate-config;
        }
      }
      uses af-mup-reoriginate-top {
        when "(/arc-features:features" +
             "/arc-features:feature[arc-features:name='arc-features:ARCOS_SRV6_MUP']" +
             "/arc-features:supported = 'true')" {
          description
            "Reoriginate MUP ST1 only for IPv4/IPv6 Unicast in
             non-default network instance.";
        }
      }
    }
  }

  grouping af-mup-compatibility-config {
    leaf st1-suppress-source {
      type boolean;
      default false;
      description
        "Do not send source address in MUP ST1 route";
    }
  }

  grouping af-mup-compatibility-top {
    container compatibility {
      container config {
        uses af-mup-compatibility-config;
      }
      container state {
        config false;
        uses af-mup-compatibility-config;
      }
    }
  }

  grouping nbr-af-advertise-reoriginated-config {
    leaf enabled {
      type boolean;
      default false;
      description
        "Enable/Disable advertisement of reoriginated MUP ST1 route";
    }
  }

  grouping nbr-af-advertise-reoriginated-top {
    container advertise {
      container reoriginated {
        container mup-st1 {
          container config {
            uses nbr-af-advertise-reoriginated-config;
          }
          container state {
            config false;
            uses nbr-af-advertise-reoriginated-config;
          }
        }
      }
    }
  }

  grouping all-neighbors-top {
    container all-neighbors {
      config false;
      description
        "A list of all bgp neighbor state info, used for show commands";

      list all-neighbor {
        key "neighbor-address";
        description
          "A list of BGP peers and their config/oper states";

        leaf neighbor-address {
          type leafref {
            path "../state/neighbor-address";
          }
          description
            "option 1: IP address
             option 2: String representing local interface name (swp1, swp1.1 etc.)";
        }

        container state {
          description
            "BGP dynamic neighbor instance states";

          leaf neighbor-address {
            type union {
              type inet:ip-address;
              type leafref {
                path "/oc-if:interfaces/oc-if:interface/oc-if:name";
              }
            }
            description
              "option 1: IP address
               option 2: String representing local interface name (swp1, swp1.1 etc.)";
          }

          leaf peer-group {
            type leafref {
              path "/oc-netinst:network-instances/oc-netinst:network-instance" +
                   "/oc-netinst:protocols/oc-netinst:protocol" +
                   "/oc-netinst:bgp/oc-netinst:peer-groups/oc-netinst:peer-group" +
                   "/oc-netinst:peer-group-name";
            }
            description
              "The peer-group with which this neighbor is associated";
          }

          leaf enabled {
            type boolean;
            description
              "Whether the BGP peer is enabled.";
          }

          uses oc-bgp:bgp-common-neighbor-group-config;
          uses oc-bgp:bgp-neighbor-state;
          uses bgp-neighbor-states-top;
        }

        container timers {
          description
            "Timers related to a BGP neighbor";
          container state {
            config false;
            description
              "State information relating to the timers used for the BGP
              neighbor";
            uses oc-bgp:bgp-common-neighbor-group-timers-config;
            uses oc-bgp:bgp-neighbor-timers-state;
            uses nbr-timers-config;
          }
        }

        container transport {
          description
            "Transport session parameters for the BGP neighbor";
          container state {
            description
              "State information relating to the transport session(s)
              used for the BGP neighbor";
            uses oc-bgp:bgp-common-neighbor-group-transport-config;
            uses oc-bgp:bgp-neighbor-transport-state;
            uses bgp-neighbor-transport-state-aug-top;
          }
        }

        container graceful-restart {
          description
            "Parameters relating the graceful restart mechanism for BGP";
          container state {
            description
              "State information associated with graceful-restart";
            uses oc-bgp:bgp-common-graceful-restart-config;
            uses oc-bgp:bgp-neighbor-graceful-restart-state;
          }
        }

        container graceful-shutdown {
          description
            "Parameters relating to graceful shutdown for BGP";
          container state {
            description
              "State information relating to graceful shutdown";
            uses graceful-shutdown-config;
          }
        }

        container ebgp-multihop {
          description
            "eBGP multi-hop parameters";
          container state {
            description
              "State information for eBGP multihop, for the BGP neighbor
              or group";
            uses oc-bgp:bgp-common-neighbor-group-multihop-config;
          }
        }

        container route-reflector {
          description
            "Route reflector parameters";
          container state {
            description
              "State information relating to route reflection for the
              BGP group";
            uses oc-bgp:bgp-common-neighbor-group-route-reflector-config;
          }
        }

        container route-server {
          description
            "Route server parameters";
          container state {
            description
              "State information relating to route server for the
              BGP neighbor or group";
            uses route-server-config;
          }
        }

        container as-path-options {
          description
            "AS_PATH manipulation parameters for the BGP neighbor or
            group";
          container state {
            description
              "State information relating to the AS_PATH manipulation
              mechanisms for the BGP peer or group";

            leaf allow-own-as {
              type uint8;
              description
                "Specify the number of occurrences of the local BGP speaker's
                AS that can occur within the AS_PATH before it is rejected.";
            }
          }
        }

        container afi-safis {
          description
            "Per-address-family configuration parameters associated with
            the neighbor";

          list afi-safi {
            key "afi-safi-name";

            description
              "AFI,SAFI configuration available for the
              neighbor or group";

            leaf afi-safi-name {
              type identityref {
                base oc-bgp-types:AFI_SAFI_TYPE;
              }
              description
                "AFI,SAFI";
            }

            container state {
              description
                "State information relating to the AFI-SAFI";
              uses bgp-common-mp-afi-safi-config;
              uses bgp-neighbor-afi-safi-state;
              uses nbr-af-state-top;
            }

            container graceful-restart {
              description
                "Parameters relating to BGP graceful-restart";
              container state {
                description
                  "State information for BGP graceful-restart";
                uses oc-bgp:bgp-common-mp-afi-safi-graceful-restart-config;
                uses oc-bgp:bgp-neighbor-afi-safi-graceful-restart-state;
              }
            }

            container apply-policy {
              description
                "Anchor point for routing policies in the model.
                 Import and export policies are with respect to the local
                 routing table, i.e., export (send) and import (receive),
                 depending on the context.";

              container state {
                description
                  "Operational state for routing policy";
                uses oc-rpol:apply-policy-config;
                uses oc-rpol:apply-policy-state;
              }
            }

            container ipv4-unicast {
              when "../afi-safi-name = 'oc-bgp-types:IPV4_UNICAST'" {
                description
                  "Include this container for IPv4 Unicast specific
                  configuration";
              }

              description "IPv4 unicast configuration options";

              // include common IPv[46] unicast options
              uses bgp-common-mp-ipv4-ipv6-unicast-common;

              // placeholder for IPv4 unicast  specific configuration
            }

            container ipv6-unicast {
              when "../afi-safi-name = 'oc-bgp-types:IPV6_UNICAST'" {
                description
                  "Include this container for IPv6 Unicast specific
                  configuration";
              }

              description "IPv6 unicast configuration options";

              // include common IPv[46] unicast options
              uses bgp-common-mp-ipv4-ipv6-unicast-common;

              // placeholder for IPv6 unicast specific configuration
            }

            container ipv4-labeled-unicast {
              when "../afi-safi-name = 'oc-bgp-types:IPV4_LABELED_UNICAST'" {
                description
                  "Include this container for IPv4 Labeled Unicast specific
                  configuration";
              }

              description "IPv4 Labeled unicast configuration options";

              uses bgp-common-mp-all-afi-safi-common;

              // placeholder for IPv4 Labeled unicast  specific configuration
            }

            container ipv6-labeled-unicast {
              when "../afi-safi-name = 'oc-bgp-types:IPV6_LABELED_UNICAST'" {
                description
                  "Include this container for IPv6 Labeled Unicast specific
                  configuration";
              }

              description "IPv6 Labeled unicast configuration options";

              uses bgp-common-mp-all-afi-safi-common;

              // placeholder for IPv6 Labeled unicast  specific configuration
            }

            container l3vpn-ipv4-unicast {
              when "../afi-safi-name = 'oc-bgp-types:L3VPN_IPV4_UNICAST'" {
                description
                  "Include this container for L3VPN IPv4 Unicast specific
                  configuration";
              }

              description "L3VPN IPv4 unicast configuration options";

              uses bgp-common-mp-all-afi-safi-common;

              // placeholder for L3VPN IPv4 unicast  specific configuration
            }

            container l3vpn-ipv6-unicast {
              when "../afi-safi-name = 'oc-bgp-types:L3VPN_IPV6_UNICAST'" {
                description
                  "Include this container for L3VPN IPv6 Unicast specific
                  configuration";
              }

              description "L3VPN IPv6 unicast configuration options";

              uses bgp-common-mp-all-afi-safi-common;

              // placeholder for L3VPN IPv6 unicast specific configuration
            }

            container l3vpn-ipv4-multicast {
              when "../afi-safi-name = 'oc-bgp-types:L3VPN_IPV4_MULTICAST'" {
                description
                  "Include this container for L3VPN IPv4 Multicast specific
                  configuration";
              }

              description "L3VPN IPv4 multicast configuration options";

              uses bgp-common-mp-all-afi-safi-common;

              // placeholder for L3VPN IPV4 multicast  specific configuration
            }

            container l3vpn-ipv6-multicast {
              when "../afi-safi-name = 'oc-bgp-types:L3VPN_IPV6_MULTICAST'" {
                description
                  "Include this container for L3VPN IPv6 Multicast specific
                  configuration";
              }

              description "L3VPN IPv6 multicast configuration options";

              uses bgp-common-mp-all-afi-safi-common;

              // placeholder for L3VPN IPv6 Multicast specific configuration
            }

            container l2vpn-evpn {
              when "../afi-safi-name = 'oc-bgp-types:L2VPN_EVPN'" {
                description
                  "Include this container for L2VPN EVPN specific
                  configuration";
              }

              description "L2VPN EVPN configuration options";

              uses bgp-common-mp-all-afi-safi-common;

              // placeholder for L2VPN EVPN specific configuration
            }

            container rtfilter {
              when "../afi-safi-name = 'arc-oc-bgp-types:RTFILTER'" {
                description
                  "Include this container for RTFILTER specific
                  configuration";
              }

              description "RTFILTER configuration options";

              uses bgp-common-mp-ipv4-ipv6-unicast-common;
            }

            // uses oc-bgp:bgp-neighbor-use-multiple-paths; --- not supported
          }
        }
      } // list all-neighbor
    } // container all-neighbors
  } // all-neighbors-top

  augment "/oc-netinst:network-instances/oc-netinst:network-instance" +
          "/oc-netinst:protocols/oc-netinst:protocol" +
          "/oc-netinst:bgp" {
      uses all-neighbors-top;
  }

  augment "/oc-netinst:network-instances" + 
          "/oc-netinst:network-instance" +
          "/oc-netinst:protocols/oc-netinst:protocol" +
          "/oc-netinst:bgp" +
          "/oc-netinst:global/oc-netinst:afi-safis" + 
          "/oc-netinst:afi-safi" {
    uses bgp-l2vpn-evpn-vpws-top {
      when "oc-netinst:afi-safi-name = 'oc-bgp-types:L2VPN_EVPN'" +
           " and " +
           "../../../../../../oc-netinst:name = 'default'"  {
          description
            "Show vpws for l2vpn evpn afi-safi";
      }
    }
  }

  augment "/oc-netinst:network-instances/oc-netinst:network-instance" +
          "/oc-netinst:protocols/oc-netinst:protocol" +
          "/oc-netinst:bgp" +
          "/arc-oc-bgp-aug:all-neighbors" +
          "/arc-oc-bgp-aug:all-neighbor" {
    container ebgp-local-as {
      description "Operational data for local AS.";

      uses ebgp-local-as-state;
    }
  }

  augment "/oc-netinst:network-instances/oc-netinst:network-instance" +
          "/oc-netinst:protocols/oc-netinst:protocol" +
          "/oc-netinst:bgp" +
          "/arc-oc-bgp-aug:all-neighbors" +
          "/arc-oc-bgp-aug:all-neighbor" {
    container bfd {
      description "Operational data for BFD.";

      uses bfd-state;
    }
  }

  augment "/oc-netinst:network-instances/oc-netinst:network-instance" +
          "/oc-netinst:protocols/oc-netinst:protocol" +
          "/oc-netinst:bgp" +
          "/arc-oc-bgp-aug:all-neighbors" +
          "/arc-oc-bgp-aug:all-neighbor" {
    container srv6 {
      description "Operational data for SRv6.";

      when "../../../../../../oc-netinst:name = 'default'" {
        description
          "SRv6 tunnel endpoint in network-instance default only";
      }
      uses nbr-srv6-state-top;
    }
    container peer-as-range {
      description "Operational data for peer-as-range.";
      container inline {
        description "Operational data for inline peer-as-range";
        uses peer-as-range-inline-top-state;
      }
    }
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:graceful-restart/arc-oc-bgp-aug:state" {
    uses restart-timer-expire-state;
    uses stale-routes-timer-expire-state;
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:afi-safis/arc-oc-bgp-aug:afi-safi/arc-oc-bgp-aug:state" +
          "/arc-oc-bgp-aug:prefixes" {
    uses nbr-af-prefixes-top;
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:afi-safis/arc-oc-bgp-aug:afi-safi" {
    container add-paths {
      description
        "Parameters relating to the advertisement and receipt of
        multiple paths for a single NLRI (add-paths)";

      uses nbr-af-add-paths-state-top;
    }

    container aigp {
      description
        "Neighbor AFI/SAFI AIGP metric states";

      uses bgp-aigp-state;
    }

    container extended-nexthop {
      description
        "Parameters relating to extended nexthop encoding capability";
      uses nbr-af-extended-nexthop-state-top;
    }

    container default-originate {
      description
        "Parameters relating to default route origination";
      uses default-originate-state-top;
    }

    container advertise {
      container reoriginated {
        container mup-st1 {
          container state {
            config false;
            uses nbr-af-advertise-reoriginated-config;
          }
        }
      }
    }
  }

  /*
   * RTR server augments.
   */
  augment "/oc-netinst:network-instances/oc-netinst:network-instance" +
          "/oc-netinst:protocols/oc-netinst:protocol" +
          "/oc-netinst:bgp" {
    container rtr-servers {
      when "../../../../oc-netinst:name = 'default'" {
        description
          "Allow rtr-server configs in network-instance default only";
      }
      description
        "Configuration for RTR servers";

      uses bgp-rtr-server-list;
    }
  }

  /*
   * eRPL server augments.
   */
  grouping erpl-server-config-top {
    leaf server-name {
      type string {
        length "1..50";
      }
      description
        "Name of the eRPL server";
    }
    leaf address {
      type inet:ip-address;
      mandatory true;
      description
        "IP address of the eRPL server";
    }
    leaf port {
      type uint16;
      mandatory true;
      description
        "TCP port the eRPL server listens to";
    }
    leaf preference {
      type uint8 {
        range "0..254";
      }
      mandatory true;
      description
        "Preference of the eRPL server; the server with lower value
        is more preferred";
    }
  }

  grouping erpl-server-state-top {
    leaf server-connected {
      type boolean;
      description
        "This boolean indicates if connection to the configured eRPL server
        is successful";
    }
  }

  grouping bgp-erpl-server-base {
    description
      "Parameters related to a eRPL server";

    container config {
      description
        "Configuration parameters relating to the eRPL server";

      uses erpl-server-config-top;
    }

    container state {
      config false;
      description
        "State information relating to the eRPL server";
      uses erpl-server-config-top;
      uses erpl-server-state-top;
    }
  }

  grouping bgp-erpl-server-list {
    description
      "The list of External Routing Polocy Language server information";

    list server {
      key server-name;
      max-elements 5;
      unique "config/address config/port";
      unique "config/preference";
      description
        "List of configured eRPL servers";

      leaf server-name {
        type leafref {
          path "../config/server-name";
        }
        description
          "Reference to the eRPL server name used as a key in the
          eRPL server list";
      }

      uses bgp-erpl-server-base;
    }
  }

  grouping erpl-generic-config-top {
    leaf connection-wait-time {
      type uint16;
      default 5;
      description
        "Maximum time in seconds for establishing connection to a server";
    }
    leaf server-restart-time {
      type uint16;
      default 60;
      description
        "Maximum time in seconds for waiting for eRPL server to reconnect";
    }
    leaf reset-connection-on-error {
      type boolean;
      description
        "BGP shall reset the connection to eRPL server for error handling";
    }
  }

  grouping erpl-generic-state-top {
    leaf server-protocol-version {
      type string;
      description
        "The version of the protocol being suppored by eRPL server";
    }
    leaf client-protocol-version {
      type string;
      description
        "The version of the protocol being suppored by BGP";
    }
    leaf path-order-enforced {
      type boolean;
      description
        "eRPL server will send export path results back to
        BGP in the same order the server receives them";
    }
    leaf server-restart-timer-expire {
      type uint16;
      description
        "This time value indicates the remaining time on eRPL
        server restart timer in seconds";
    }
  }

  grouping bgp-erpl-generic-top {
    description
      "Generic eRPL configuration and state";

    container config {
      description
        "Generic eRPL configuration parameters";

      uses erpl-generic-config-top;
    }
    container state {
      config false;
      description
        "Generic eRPL state information";

      uses erpl-generic-config-top;
      uses erpl-generic-state-top;
    }
  }

  augment "/oc-netinst:network-instances/oc-netinst:network-instance" +
          "/oc-netinst:protocols/oc-netinst:protocol" +
          "/oc-netinst:bgp" {
    container erpl {
      when "../../../../oc-netinst:name = 'default'" {
        description
          "Allow eRPL server configs in network-instance default only";
      }
      description
        "Configuration for eRPL servers";

      uses bgp-erpl-generic-top;

      container servers {
        description
          "Configuration for eRPL servers";

        uses bgp-erpl-server-list;
      }
    }
  }

  grouping nbr-af-erpl-config {
    leaf import-erpl {
      type string {
        length "1..50";
      }
      description
        "Enable/Disable import eRPL under neighbor AFI/SAFI";
    }
  }

  grouping nbr-af-erpl-config-top {
    container config {
      description
        "Configuration parameters relating to eRPL under neighbor AFI/SAFI";

      uses nbr-af-erpl-config;
    }
  }

  grouping nbr-af-erpl-state-top {
    container state {
      config false;
      description
        "State information relating to eRPL under neighbor AFI/SAFI";

      uses nbr-af-erpl-config;
    }
  }

  grouping nbr-af-erpl-top {
    container apply-erpl {
      description
        "Enable external routing policy language capability";

      uses nbr-af-erpl-config-top;
      uses nbr-af-erpl-state-top;
    }
  }

  augment "/oc-netinst:network-instances/oc-netinst:network-instance" +
          "/oc-netinst:protocols/oc-netinst:protocol" +
          "/oc-netinst:bgp" +
          "/oc-netinst:neighbors/oc-netinst:neighbor" +
          "/oc-netinst:afi-safis/oc-netinst:afi-safi" {
    uses nbr-af-erpl-top {
      when "oc-netinst:afi-safi-name = 'oc-bgp-types:IPV4_UNICAST' or
            oc-netinst:afi-safi-name = 'oc-bgp-types:IPV6_UNICAST'";
    }
  }

  augment "/oc-netinst:network-instances/oc-netinst:network-instance" +
          "/oc-netinst:protocols/oc-netinst:protocol" +
          "/oc-netinst:bgp" +
          "/oc-netinst:peer-groups/oc-netinst:peer-group" +
          "/oc-netinst:afi-safis/oc-netinst:afi-safi" {
    uses nbr-af-erpl-top;
  }

  augment "/oc-netinst:network-instances/oc-netinst:network-instance" +
          "/oc-netinst:protocols/oc-netinst:protocol" +
          "/oc-netinst:bgp" +
          "/oc-netinst:peer-groups/oc-netinst:peer-group" +
          "/oc-netinst:timers/oc-netinst:config" {
    uses nbr-timers-config;
  }

  augment "/oc-netinst:network-instances/oc-netinst:network-instance" +
          "/oc-netinst:protocols/oc-netinst:protocol" +
          "/oc-netinst:bgp" +
          "/oc-netinst:peer-groups/oc-netinst:peer-group" +
          "/oc-netinst:timers/oc-netinst:state" {
    uses nbr-timers-config;
  }

  augment "/oc-netinst:network-instances/oc-netinst:network-instance" +
          "/oc-netinst:protocols/oc-netinst:protocol" +
          "/oc-netinst:bgp" +
          "/arc-oc-bgp-aug:all-neighbors/arc-oc-bgp-aug:all-neighbor" +
          "/arc-oc-bgp-aug:afi-safis/arc-oc-bgp-aug:afi-safi" {
    container apply-erpl {
      description
        "Parameters relating to eRPL configuration for a neighbor AFI/SAFI";
      uses nbr-af-erpl-state-top;
    }
  }

  grouping l2-domain-config {
    description
      "Configuration data for Data Center Interconnect Domains";

    leaf domain-name {
      type leafref {
        path "../../../../../../../oc-netinst:config/arc-evpn:domain/arc-evpn:name";
      }
      description "EVPN Domain Name";
    }

    leaf route-distinguisher {
      type oc-netinst-types:route-distinguisher;
      mandatory true;
      description
        "The route distinguisher that should be used for the domain";
    }
  }

  grouping l2-domain-state {
    description
      "State data for Data Center Interconnect Domains";

    leaf domain-id {
      type uint16;
      description
        "The Data Center Interconnect domain id";
    }

    leaf local-tunnel-ip {
      type inet:ip-address;
      description
        "Local tunnel ip for this domain";
    }

    leaf tunnel-type {
      type string;
      description
        "Tunnel-type (VXLAN or MPLS)";
    }

    leaf control-word {
      type boolean;
      description
        "Control Word";
    }

    leaf  flow-label{
      type boolean;
      description
        "Flow Label";
    }

    leaf vni-evi {
      type uint32;
      description
        "VNI/EVI associated with the domain";
    }

    leaf evpn-l2-import-route-targets {
      type string;
      description
        "import route-targets for this network-instance";
    }

    leaf evpn-l2-export-route-targets {
      type string;
      description
        "export route-targets for this network-instance";
    }
  }

  grouping l2-domain-top {

    description
      "Top level grouping for Data Center Interconnect (DCI) domains";

    container domains {
      description "List of Data Center Interconnect(DCI) Domains";

      list domain {
        key "domain-name";
        description "List of DCI domain names";

        leaf domain-name {
          type leafref {
            path "../config/domain-name";
          }
          description "Reference to domain name key";
        }

        container config {
          description "Configuration for Data Center Interconnect Domains";
          uses l2-domain-config;
          uses rt-afi-safis-top;
        }

        container state {
          config false;
          description "Operational state for Data Center Interconnect Domains";
          uses l2-domain-config;
          uses l2-domain-state;
        }
      }
    }
  }

  /*
   * DCI Domain augment.
   */
  augment "/oc-netinst:network-instances/oc-netinst:network-instance" +
          "/oc-netinst:protocols/oc-netinst:protocol" +
          "/oc-netinst:bgp" {
    uses l2-domain-top {
      when "../../../oc-netinst:config/oc-netinst:type = 'oc-netinst-types:L2VLAN' or " +
           "../../../oc-netinst:config/oc-netinst:type = 'arc-oc-ni-types:L2P2P_EVPN' or " +
           "../../../oc-netinst:config/oc-netinst:type = 'arc-oc-ni-types:L2VLAN_AWARE_BUNDLE'" {
        description
          "DCI domains only supported for L2 network-instance";
      }
    }
  }

  augment "/oc-netinst:network-instances/oc-netinst:network-instance" +
          "/oc-netinst:protocols/oc-netinst:protocol" +
          "/oc-netinst:bgp" +
          "/arc-oc-bgp-aug:domains/arc-oc-bgp-aug:domain" +
          "/arc-oc-bgp-aug:config" +
          "/arc-oc-bgp-aug:rt-afi-safis/arc-oc-bgp-aug:rt-afi-safi" {
    uses route-targets-top {
      description
        "Per RT-AF route-targets for DCI domain";
    }
    uses oc-rpol:apply-policy-group;
  }

  /*
   * global afi-safi add-paths + import/export policies
   * DCI TBD -- import/export policies at this level to be phased out. use per rt-af policy instead.
   */
  augment "/oc-netinst:network-instances/oc-netinst:network-instance" +
          "/oc-netinst:protocols/oc-netinst:protocol" +
          "/oc-netinst:bgp" +
          "/oc-netinst:global/oc-netinst:afi-safis/oc-netinst:afi-safi" {
    uses global-add-paths-top;
    uses oc-rpol:apply-policy-group {
      when "(not(derived-from-or-self(./oc-netinst:afi-safi-name, 'arc-oc-bgp-types:IPV4_MUP'))) and " +
           "(not(derived-from-or-self(./oc-netinst:afi-safi-name, 'arc-oc-bgp-types:IPV6_MUP'))) and " +
           "((derived-from-or-self(../../../../../../oc-netinst:config/oc-netinst:type, 'oc-netinst-types:L3VRF')) or " +
            "(derived-from-or-self(../../../../../../oc-netinst:config/oc-netinst:type, 'oc-netinst-types:L2P2P')) or " +
            "(derived-from-or-self(../../../../../../oc-netinst:config/oc-netinst:type, 'oc-netinst-types:L2VLAN')))" {
        description "Per AF routing policy is supported only L2/L3 network-instances excluding MUP SAFI";
      }
    }
  }

  /*
   * global afi-safi srv6-oam
   */
  augment "/oc-netinst:network-instances/oc-netinst:network-instance" +
          "/oc-netinst:protocols/oc-netinst:protocol" +
          "/oc-netinst:bgp" +
          "/oc-netinst:global/oc-netinst:afi-safis/oc-netinst:afi-safi" {
    uses global-srv6-oam-top {
      when "oc-netinst:afi-safi-name = 'oc-bgp-types:IPV6_UNICAST' " +
        "or oc-netinst:afi-safi-name = 'oc-bgp-types:IPV4_UNICAST' " +
        "or oc-netinst:afi-safi-name = 'oc-bgp-types:L3VPN_IPV4_UNICAST' " +
        "or oc-netinst:afi-safi-name = 'oc-bgp-types:L3VPN_IPV6_UNICAST' " {
          description
            "SRv6 OAM related configurataions";
      }
    }
  }

  /*
   * global afi-safi rib-install
   */
  augment "/oc-netinst:network-instances/oc-netinst:network-instance" +
          "/oc-netinst:protocols/oc-netinst:protocol" +
          "/oc-netinst:bgp" +
          "/oc-netinst:global/oc-netinst:afi-safis/oc-netinst:afi-safi" {

    uses global-af-rib-install-top {
      when "oc-netinst:afi-safi-name = 'oc-bgp-types:IPV6_UNICAST' " +
           "or oc-netinst:afi-safi-name = 'oc-bgp-types:IPV4_UNICAST' " {

        description
          "RIB route installation.";
      }
    }
  }

  /*
   * For test only, route injection
   */
  grouping test-route-inject-config {
    leaf route-base {
      type inet:ip-address;
      description
        "First route of the batch to be injected";
      must "boolean(../count) = 'true'" {
        error-message
          "'count' must be configured also";
      }
    }
    leaf count {
      type uint32;
      description
       "Number of routes to be injected starting from the route-base";
      must "boolean(../route-base) = 'true'" {
        error-message
          "route-base must be configured also";
      }
    }
  }

  augment "/oc-netinst:network-instances/oc-netinst:network-instance" +
          "/oc-netinst:protocols/oc-netinst:protocol" +
          "/oc-netinst:bgp" +
          "/oc-netinst:global/oc-netinst:afi-safis/oc-netinst:afi-safi" +
          "/oc-netinst:config" {
    container test-route-injection-len32 {
      when "../oc-netinst:afi-safi-name = 'oc-bgp-types:IPV4_UNICAST'";
      description
        "Inject v4 /32 prefixes for test purpose.";
      uses test-route-inject-config;
    }

    container test-route-injection-len24 {
      when "../oc-netinst:afi-safi-name = 'oc-bgp-types:IPV4_UNICAST'";
      description
        "Inject v4 /24 prefixes for test purpose.";
      uses test-route-inject-config;
    }

    container test-route-injection-len16 {
      when "../oc-netinst:afi-safi-name = 'oc-bgp-types:IPV4_UNICAST'";
      description
        "Inject v4 /16 prefixes for test purpose.";
      uses test-route-inject-config;
    }

    container test-route-injection-len128 {
      when "../oc-netinst:afi-safi-name = 'oc-bgp-types:IPV6_UNICAST'";
      description
        "Inject v6 /128 prefixes for test purpose.";
      uses test-route-inject-config;
    }

    container test-route-injection-len96 {
      when "../oc-netinst:afi-safi-name = 'oc-bgp-types:IPV6_UNICAST'";
      description
        "Inject v6 /96 prefixes for test purpose.";
      uses test-route-inject-config;
    }

    container test-route-injection-len64 {
      when "../oc-netinst:afi-safi-name = 'oc-bgp-types:IPV6_UNICAST'";
      description
        "Inject v6 /64 prefixes for test purpose.";
      uses test-route-inject-config;
    }
  }

  augment "/oc-netinst:network-instances/oc-netinst:network-instance" +
          "/oc-netinst:protocols/oc-netinst:protocol" +
          "/oc-netinst:bgp/oc-netinst:global" {

    container mpls {
      description
        "MPLS information in BGP";
    }
  }
  
  grouping flowspec-action-config {
    description
      "Config of action type";

    leaf forwarding-action {
      type identityref {
        base arc-oc-bgp-types:FORWARDING_ACTION;
      }
      must ". = 'arc-oc-bgp-types:DROP' or " +
           ". = 'arc-oc-bgp-types:ACCEPT'" {
        error-message
          "only DROP and ACCEPT actions are supported";
      }
      mandatory true;
      description
        "Specifies the forwarding action.  One forwarding action
        must be specified for each Flowspec entry";
    }
  }

  grouping flowspec-config {
    description
      "Configuration for flowpsec rules";

    leaf sample-and-drop {
      type boolean;
      default false;
      description "Enable or Disable Sampling of packets dropped by flowspec";
    }

    container rt-redirect {
      description
        "Configuration for flowpsec rediect-rt actions";
      leaf next-hop {
        type identityref {
          base arc-oc-bgp-types:RT_REDIRECT_NEXT_HOPS;
        }
        description
          "Next-Hop to be used for flowpsec rules with Redirect to VRF action";
        
      }
    }
  }

  grouping flowspec-action-state {
    description
      "State information of action type";

  }

  grouping flowspec-action-top {
    description
      "Flowspec action type top level container";

    container action {
      description
        "Enclosing container for Flowspec action associated
        with an entry";

      container config {
        description
          "Config data for Flowspec action";
        uses flowspec-action-config;
      }

      container state {
        config false;
        description
          "State information for Flowspec action";
        uses flowspec-action-config;
        uses flowspec-action-state;
      }
    }
  }

  grouping ipv4-flowspec-rules-config {
    description
      "Configuration data for IPv4 flowspec.";

    leaf id {
      type uint32;
      description
       "flowspec rule id number";
    }
  }

  grouping ipv4-flowspec-rules-top {
    container flowspecs {
      description "List of flowspec rule";
      list flowspec {
        key "id";
        description "Originate a local IPv4 flowspec prefix";

        leaf id {
          type leafref {
            path "../config/id";
          }
          description "Reference to id key.";
        }

        container config {
          description "Configuration data for flowspec.";
          uses ipv4-flowspec-rules-config;
        }

        container state {
          config false;
          description "Operational data for flowspec.";
          uses ipv4-flowspec-rules-config;
        }

        container match {
          description
          "IPv4 Flowpsec match components";
          uses oc-match:ipv4-protocol-fields-top;
        }
        uses flowspec-action-top;
      }
    }
  }

  grouping ipv6-flowspec-rules-config {
    description
      "Configuration data for IPv6 flowspec.";

    leaf id {
      type uint32;
      description
       "flowspec rule id number";
    }
  }

  grouping ipv6-flowspec-rules-top {
    container flowspecs {
      description "List of flowspecs";
      list flowspec {
        key "id";
        description "Originate a local IPv6 flowspec prefix";

        leaf id {
          type leafref {
            path "../config/id";
          }
          description "Reference to id key.";
        }

        container config {
          description "Configuration data for flowspec.";
          uses ipv6-flowspec-rules-config;
        }

        container state {
          config false;
          description "Operational data for flowspec.";
          uses ipv6-flowspec-rules-config;
        }

        container match {
          description
          "IPv6 Flowpsec match components";

          uses oc-match:ipv6-protocol-fields-top;
        }
        uses flowspec-action-top;
      }
    }
  }

  grouping ipv4-flowspec-top {
    container ipv4-flowspec {
      uses ipv4-flowspec-rules-top;
      uses flowspec-config;
    }
  }

  grouping ipv6-flowspec-top {
    container ipv6-flowspec {
      uses ipv6-flowspec-rules-top;
      uses flowspec-config;
    }
  }

  augment "/oc-netinst:network-instances/oc-netinst:network-instance" +
          "/oc-netinst:protocols/oc-netinst:protocol" +
          "/oc-netinst:bgp" +
          "/oc-netinst:global/oc-netinst:afi-safis/oc-netinst:afi-safi" {
    uses ipv4-flowspec-top {
       when "oc-netinst:afi-safi-name = 'arc-oc-bgp-types:IPV4_FLOWSPEC' ";
    }
  }

  augment "/oc-netinst:network-instances/oc-netinst:network-instance" +
          "/oc-netinst:protocols/oc-netinst:protocol" +
          "/oc-netinst:bgp" +
          "/oc-netinst:global/oc-netinst:afi-safis/oc-netinst:afi-safi" {
    uses ipv6-flowspec-top {
       when "oc-netinst:afi-safi-name = 'arc-oc-bgp-types:IPV6_FLOWSPEC' ";
    }
  }
}
