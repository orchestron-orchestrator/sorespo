module arcos-platform-transceiver {
  yang-version 1.1;
  namespace "http://yang.arrcus.com/arcos/platform/transceiver";
  prefix arc-transceiver;
  
  // import some basic types
  import openconfig-platform { prefix oc-platform; }
  import openconfig-platform-types { prefix oc-platform-types; }
  import ietf-yang-types { prefix yang; }

  organization
    "Arrcus, Inc.";

  contact
    "Arrcus, Inc.
     Customer Service
     Postal: 2077 Gateway Place
     San Jose, CA 95110
     Tel: +1 408 884-1965
     E-mail: yang-support@arrcus.com";

  description
    "This module defines Arrcus implementation
     of the transceiver platform model.

     Copyright (c) 2016-2024 by Arrcus, Inc.
     All rights reserved.";
  
  revision 2026-02-04 {
    description
      "Updated fraction-digits to 12 for FEC thresholds";
  }

  revision 2025-01-10 {
    description
      "Adding configurartion for transceivers";
  }

  typedef grid-space-types {
    type enumeration {
      enum G_3_125GHz {
        value 0;
        description "Grid spacing of 3.125 GHz.";
      }
      enum G_6_25GHz {
        value 1;
        description "Grid spacing of 6.25 GHz.";
      }
      enum G_12_5GHz {
        value 2;
        description "Grid spacing of 12.5 GHz.";
      }
      enum G_25GHz {
        value 3;
        description "Grid spacing of 25 GHz.";
      }
      enum G_50GHz {
        value 4;
        description "Grid spacing of 50 GHz.";
      }
      enum G_100GHz {
        value 5;
        description "Grid spacing of 100 GHz.";
      }
      enum G_33GHz {
        value 6;
        description "Grid spacing of 33 GHz.";
      }
      enum G_75GHz {
        value 7;
        description "Grid spacing of 75 GHz.";
      }
    }
  }

  // threshold configs
  grouping fec-thresholds {
    description
      "Configuration data for FEC thresholds";

    leaf raise {
      type decimal64 {
        fraction-digits 12;
      }
      must "../clear" {
        error-message "A threshold 'clear' must be configured";
      }
      description
        "FEC BER threshold to be set active";
    }

    leaf clear {
      type decimal64 {
        fraction-digits 12;
      }
      must "../raise" {
        error-message "A threshold 'raise' must be configured";
      }
      description
        "FEC BER threshold to be set clear";
    }
  }

  grouping fec-thresh-types {
    description
      "Configuration data for FEC threshold types";

    container excess-degrade {
      description
        "FEC BER threshold for FEC Excessive Degrade (FED)";

      uses fec-thresholds;
    }

    container detected-degrade {
      description
        "FEC BER threshold for FEC Detected Degrade (FDD)";

      uses fec-thresholds;
    }
  }

  grouping thresh-types {
    description
      "Configuration data for threshold types";

    container fec-threshold {
      description
        "FEC thresholds";

      uses fec-thresh-types;
    }
  }

  grouping lane-thresh {
    description
      "Configuration data for lanes thresholds types like media/host";

    container media {
      description
        "Thresholds related to Media";

      when "../index = 1" {
        description "Only available for lanes 1";
      }

      uses thresh-types;
    }

    container host {
      description
        "Thresholds related to Host";

      when "../index = 1 or ../index = 3 or ../index = 5 or ../index = 7" {
        description "Only available for lanes 1, 3, 5, and 7.";
      }

      uses thresh-types;
    }
  }

  grouping lanes-config {
    description
      "Configuration data for lanes";

    leaf tx-grid-spacing {
      description
        "Tx Grid spacing";

      type grid-space-types;
      must "../tx-center-frequency" {
        error-message "A 'tx-center-frequency' must be configured";
      }
    }

    leaf tx-center-frequency {
      type uint32 {
        range "191250000..196125000"; // Range from 191.250 THz to 196.125 THz
      }

      description
        "Tx Center frequency in MHz";
      must "../tx-grid-spacing" {
        error-message "A 'tx-grid-spacing' must be configured";
      }
    }

    leaf tx-target-output-power {
      type int16;
      description
        "Tx Target output power in units of 0.01 dBm";
    }

    uses lane-thresh;
  }

  grouping lanes-top {
    description
      "Lane configuartion data for each lane";

    container lanes {
      description
        "Enclosing container for the list of lanes associated
        with a physical interface";

      list lane {
        key index;

        description
          "The list of lanes associated with a physical interface";

        leaf index {
          type uint8 {
            range "1..8";  // Set the range to limit index values
          }
          description
            "The index number of the lane (1-8)";
        }

        uses lanes-config;
      }
    }
  }

  typedef cmis-app-types {
    type enumeration {
      enum APP_400G_400ZR_SW {
        value 4415; // 0x113F
        description
          "Host: 400GAUI-8 C2M - Media: 400ZR, Single Wavelength, Unamplified";
      }
      enum APP_4x100G_400ZR_SW {
        value 3391; // 0x0D3F
        description
          "Host: 100GAUI-2 C2M - Media: 400ZR, Single Wavelength, Unamplified";
      }
      enum APP_400G_400ZR_DWDM {
        value 4414; // 0x113E
        description
          "Host: 400GAUI-8 C2M - Media: 400ZR, DWDM, Amplified";
      }
      enum APP_4x100G_400ZR_DWDM {
        value 3390; // 0x0D3E
        description
          "Host: 100GAUI-2 C2M - Media: 400ZR, DWDM, Amplified";
      }
      enum APP_400G_ZR400_OFEC_16QAM {
        value 4422; // 0x1146
        description
          "Host: 400GAUI-8 C2M - Media: ZR400-OFEC-16QAM";
      }
      enum APP_4x100G_ZR400_OFEC_16QAM {
        value 3398; // 0x0D46
        description
          "Host: 100GAUI-2 C2M - Media: ZR400-OFEC-16QAM";
      }
    }
  }

  grouping transceiver-config {
    description
      "configuration data for transceiver";

    leaf application-select {
       description
         "QSFP-DD CMIS application-select";

       type cmis-app-types;
    }

    uses lanes-top;
  }

  grouping transceiver-config-top {
    description
      "Transceivers config top";

    container config {
      list transceiver {
        key name;

        description
          "List of transceivers, keyed by transceiver name.";

        leaf name {
          type string;

          description
            "Name of the transceiver.";
        }

        container config {
          description
            "Configuration data for transceiver data";

          uses transceiver-config;
        }
      }
    }
  }

  grouping transceiver-oper-top {
    description
      "Transceivers Oper top";

    container state {
      config false;
      list transceiver {
        key name;

        description
          "List of transceivers, keyed by transceiver name.";

        leaf name {
          type string;

          description
            "Name of the transceiver.";
        }

        container state {
          config false;

          description
            "Operational data for transceiver data";

          leaf type {
            type union {
              type identityref {
                base oc-platform-types:OPENCONFIG_HARDWARE_COMPONENT;
              }
              type identityref {
                base oc-platform-types:OPENCONFIG_SOFTWARE_COMPONENT;
              }
            }
            description
              "Type of component as identified by the system";
          }

          leaf id {
            type string;
            description
              "Unique identifier assigned by the system for the
              component";
          }

          leaf description {
            type string;
            description
              "System-supplied description of the component";
          }

          leaf removable {
            type boolean;
            description
              "If true, this component is removable or is a field
              replaceable unit";
          }
        }

        container properties {
          description
            "Enclosing container ";

          list property {
            key "name";
            description
              "List of system properties for the component";

            leaf name {
              type string;

              description
                "Name of the property.";
            }
          
            container state {
              config false;

              description
                "Operational state data for each property";

              uses oc-platform:platform-component-properties-config;
            }
          }
        }
      }
    }
  }

  augment "/oc-platform:components" {
    container transceivers {
      uses transceiver-config-top;
      uses transceiver-oper-top;
    }
  }
}
