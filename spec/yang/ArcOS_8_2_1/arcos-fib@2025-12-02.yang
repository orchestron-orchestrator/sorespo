module arcos-fib {
  yang-version 1.1;
  namespace "http://yang.arrcus.com/arcos/fib";
  prefix arc-fib;

  import openconfig-network-instance {
    prefix oc-netinst;
  }
  import openconfig-network-instance-types {
    prefix oc-ni-types;
  }
  import openconfig-yang-types {
    prefix oc-yang;
  }
  import ietf-inet-types {
    prefix inet;
  }
  import openconfig-mpls-types {
    prefix oc-mplst;
  }
  import openconfig-types {
    prefix oc-types;
  }
  import ietf-yang-types {
    prefix yang;
  }

  import arcos-srv6-types {
    prefix arc-srv6-types;
  }

  import arcos-platform {
    prefix arc-platform;
  }

  organization
    "Arrcus, Inc";

  contact
    "Arrcus, Inc.
     2077 Gateway Place,
     San Jose, CA 95110
     Tel: +1 (408) 884-1965
     E-mail: yang-support@arrcus.com";

  description
    "This module lists the FIB related information.
     Copyright 2019-2022 by Arrcus, Inc.
     All rights reserved.";

  revision 2025-12-02 {
    description
      "Add published-level attribute to ipv6-nexthop-entry";
  }

  revision 2025-10-27 {
    description
      "Add SR flag to path object and published-level attribute to nexthop object";
  }

  revision 2025-10-01 {
    description
      "Add overlay-ifindex state";
  }

  revision 2025-07-20 {
    description
      "Add dpal publish stats";
  }

  revision 2024-10-21 {
    description
      "Add jmirror header state to tunnels";
  }

  revision 2024-08-11 {
    description
      "Add NHT stats in fib stats output";
  }

  revision 2024-08-01 {
    description
      "Separation of ipv* and ipv*-eos0-nh container-id tables";
  }

  revision 2024-07-30 {
    description
      "* Change RNH list keys to include type along with value
       * Define bits for nexthop and prefix flags";
  }

  revision 2024-06-04 {
    description
      "Support for state information of GTP-U forward entries";
  }

  revision 2024-04-30 {
    description
      "Add LI tunnel type";
  }

  revision 2024-03-22 {
    description
      "* Add domain-name to IPv4 and IPv6 label entry and IPv4 tunnel entry.";
  }

  revision 2024-03-19 {
    description
      "Add the nexthop information for tunnel termination entries";
  }

  revision 2024-03-11 {
    description
      "* Add IP UNNUMBERED display bit for path.";
  }

  revision 2024-02-21 {
    description
      "* Add control-word and flow-label to IPv4 and IPv6 label entry.";
  }

  revision 2024-02-14 {
    description
      "Add RNH ID as a key type for nexthop tracking";
  }

  revision 2023-05-13 {
    description
      "* Add Nexthop-type for the path and recursive-nexthops
       * Type changes for flags attribute in path
       * SR-Policy recursive nexthops is merged with IPv4/IPv6 recursive nexthops";
  }
  revision 2022-12-12 {
    description
      "* Add flood-and-learn attribute to support static vxlan.";
  }

  revision 2021-11-11 {
    description
      "* Add ifindex to label entry.";
  }

  typedef fib-path-type {
    type enumeration {
      enum "RECURSIVE" {
        value 1;
      }
      enum "CONNECTED_V4" {
        value 2;
      }
      enum "ADJ_RNH_V4" {
        value 3;
      }
      enum "LOCAL_V4" {
        value 4;
      }
      enum "GLEAN_V4" {
        value 5;
      }
      enum "CONNECTED_V6" {
        value 6;
      }
      enum "ADJ_RNH_V6" {
        value 7;
      }
      enum "LOCAL_V6" {
        value 8;
      }
      enum "GLEAN_V6" {
        value 9;
      }
      enum "DROP" {
        value 10;
      }
      enum "VXLAN_V4" {
        value 11;
      }
      enum "VXLAN_V6" {
        value 12;
     }
    }
  }

  typedef publish-path-type {
    type enumeration {
      enum PATH {
        value 1;
        description "Path";
      }
      enum ECMP {
        value 2;
        description "Equal cost multi paths";
      }
      enum RECURSIVE_PATH {
        value 3;
        description "Recursive path";
      }
      enum VXLAN_PATH {
        value 4;
        description "VxLAN path";
      }
      enum PROTECTED_PATH {
        value 5;
        description "Protected path";
      }
    }
  }

  typedef rnh-state-type {
    type enumeration {
      enum INVALID {
        value 0;
        description "RNH is invalid";
      }
      enum RESOLVED {
        value 1;
        description "RNH is resolved";
      }
      enum UNRESOLVED {
        value 2;
        description "RNH is not-resolved";
      }
      enum REJECT {
        value 3;
        description "RNH is not-resolved";
      }
      enum ENQUEUE {
        value 4;
        description "RNH is enqueued";
      }
      enum PLACEHOLDER {
        value 5;
        description "RNH is a place-holder";
      }
    }
  }

  typedef nexthop-value-type {
    type union {
      type inet:ip-address-no-zone;
      type inet:ip-prefix;
      type uint32;
    }
    description
      "Type for the nexthop ID";
  }

  typedef base-flags-type {
    type bits {
      bit DELETE_PENDING {
        position 0;
      }
      bit STALE {
        position 1;
      }
      bit ON_PUBLISH_LIST {
        position 2;
      }
      bit ACK_REQUIRED {
        position 3;
      }
      bit STATUS_VALID {
        position 4;
      }
      bit FORCE_PUBLISH {
        position 5;
      }
    }
  }

  typedef prefix-flags-type {
    type bits {
      bit UNRESOLVED {
        position 0;
      }
      bit DEFAULT {
        position 1;
      }
      bit LOCAL {
        position 2;
      }
    }
  }

  typedef nexthop-flags-type {
    type bits {
      bit UNRESOLVED {
        position 0;
      }
      bit RECURSIVE {
        position 1;
      }
      bit LOCAL {
        position 2;
      }
      bit IP_REACH {
        position 3;
      }
      bit MPLS_REACH {
        position 4;
      }
      bit MIXED_REACH {
        position 5;
      }
      bit PLACEHOLDER {
        position 6;
      }
      bit HAS_BACKUP {
        position 7;
      }
    }
  }

  typedef nexthop-type {
    type enumeration {
      enum "IPV4" {
        value 1;
        description "IPv4 address as nexthop";
      }
      enum "IPV6" {
        value 2;
        description "IPv6 address as nexthop";
      }
      enum "SR-POLICY" {
        value 3;
        description "SR-Policy ID as nexthop";
      }
      enum "IGP" {
        value 4;
        description "IGP ID as next-hop";
      }
    }
  }

  grouping v4-next-hop-info {
    container paths {
      list ipv4-path {
        key "path-id";
        leaf path-id {
          type uint32;
          description
            "ID of the Path";
        }
        leaf path-type {
          type fib-path-type;
          description
            "Type of the Path";
        }
        leaf nh-type {
          type nexthop-type;
          description
            "Nexthop type";
        }
        leaf next-hop {
          type nexthop-value-type;
          description
            "IP address or nexthop ID of the Path";
        }
        leaf-list push-label {
          type oc-mplst:mpls-label;
          description
            "The MPLS label stack imposed when forwarding packets
             to the next-hop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "Remote tunnel-endpoint MAC address for a vxlan tunnel next-hop";
        }
        leaf interface {
          type string;
          description
            "Name of the interface for the connected nexthop type";
        }
        leaf overlay-ifindex {
          type uint32;
          description
            "Interface index an overlay recursive route is learned over";
        }
        leaf network-instance {
          type string;
          description
            "Network Instance name";
        }
        leaf num-coll-paths {
          type uint32;
          description
            "Number of collapsed paths downloaded to hardware.
             Applicable only if this path is a recursive path";
        }
        leaf-list igp-path-id {
          type uint32;
          description
            "List of underlying igp path ids. Applicable only
             if the path is a a recursive path";
        }
        leaf igp-path-type {
          type uint32;
          description
            "IGP path type pointed by this path.
             Applicable only if this path is a recursive labelled path";
        }
        leaf backup {
          type boolean;
          description
            "Path is backup";
        }
      }
    }
  }

  grouping v6-next-hop-info {
    container paths {
      list ipv6-path {
        key "path-id";
        leaf path-id {
          type uint32;
          description
            "ID of the Path";
        }
        leaf path-type {
          type fib-path-type;
          description
            "Type of the Path";
        }
        leaf nh-type {
          type nexthop-type;
          description
            "Nexthop type";
        }
        leaf next-hop {
          type nexthop-value-type;
          description
            "IP address or nexthop ID of the Path";
        }
        leaf-list push-label {
          type oc-mplst:mpls-label;
          description
            "The MPLS label stack imposed when forwarding packets
             to the next-hop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "remote tunnel-endpoint MAC address for a vxlan tunnel next-hop";
        }
        leaf interface {
          type string;
          description
            "Name of the interface for the connected nexthop type";
        }
        leaf overlay-ifindex {
          type uint32;
          description
            "Interface index an overlay recursive route is learned over";
        }
        leaf network-instance {
          type string;
          description
            "Network Instance name";
        }
        leaf num-coll-paths {
          type uint32;
          description
            "Number of collapsed paths downloaded to hardware.
             Applicable only if this path is a recursive path";
        }
        leaf-list coll-path-id {
          type uint32;
          description
            "List of collapsed Path ids downloaded to hardware";
        }
        leaf-list igp-path-id {
          type uint32;
          description
            "List of underlying igp path ids. Applicable only
             if the path is a a recursive path";
        }
        leaf igp-path-type {
          type uint32;
          description
            "IGP path type pointed by this path.
             Applicable only if this path is a recursive labelled path";
        }
        leaf backup {
          type boolean;
          description
            "Path is backup";
        }
      }
    }
  }

  grouping v6-adj-info {
    container adjs {
      list ipv6-adj-entry {
        key "ipaddr";
        leaf ipaddr {
          type inet:ip-address-no-zone;
          description
            "Layer 3 ip address";
        }
        leaf hwaddr {
          type oc-yang:mac-address;
          description
            "Layer 2 address";
        }
        leaf l2ifindex {
          type uint64;
          description
            "Layer 2 ifindex";
        }
      }
    }
  }

  grouping v6-nht-info {
    container nhts {
      list ipv6-nht-entry {
        key "nht-ip";
        leaf nht-ip {
          type inet:ipv6-address-no-zone;
          description
            "Layer 3 ip address";
        }
        leaf path-id {
          type uint32;
          description
            "The Path id corresponding to the tracked ip and interface ";
        }
      }
    }
  }

  grouping v4-adj-info {
    container adjs {
      list ipv4-adj-entry {
        key "ipaddr";
        leaf ipaddr {
          type inet:ip-address-no-zone;
          description
            "Layer 3 ip address";
        }
        leaf hwaddr {
          type oc-yang:mac-address;
          description
            "Layer 2 address";
        }
        leaf l2ifindex {
          type uint64;
          description
            "Layer 2 ifindex";
        }
      }
    }
  }

  grouping v4-nht-info {
    container nhts {
      list ipv4-nht-entry {
        key "nht-ip";
        leaf nht-ip {
          type inet:ip-address-no-zone;
          description
            "Layer 3 ip address";
        }
        leaf path-id {
          type uint32;
          description
            "The Path id corresponding to the tracked ip and interface ";
        }
      }
    }
  }

  grouping ipv4-next-hops {
    container ipv4-next-hops {
      config false;
      list ipv4-nexthop-entry {
        description
          "List of Nexthops in  the IPV4 fib table";
        key "index";
        leaf index {
          type uint32;
          description
            "Id of the nexthop (NHID)";
        }
        leaf eos0-nexthop-index {
          type uint32;
          description
            "Id of the eos0 nexthop (NHID)";
        }
        leaf source-nexthop-index {
          type uint32;
          description
            "Id of the source nexthop (NHID)";
        }
        leaf level {
          type uint32;
          description
            "Level of the nexthop";
        }
        leaf published-level {
          type uint32;
          description
            "Level of the nexthop that is published to DPAL";
        }
        leaf flags {
          type nexthop-flags-type;
          description
            "Nexthop flags";
        }
        leaf protection-tracker-id {
          type uint64;
          description
            "Protection tracker pointed by this path";
        }
        uses v4-next-hop-info;
      }
    }
  }

  grouping ipv6-next-hops {
    container ipv6-next-hops {
      config false;
      list ipv6-nexthop-entry {
        description
          "List of Nexthops in  the IPV6 fib table";
        key "index";
        leaf index {
          type uint32;
          description
            "Id of the nexthop (NHID)";
        }
        leaf eos0-nexthop-index {
          type uint32;
          description
            "Id of the eos0 nexthop (NHID)";
        }
        leaf source-nexthop-index {
          type uint32;
          description
            "Id of the source nexthop (NHID)";
        }
        leaf level {
          type uint32;
          description
            "Level of the nexthop";
        }
        leaf published-level {
          type uint32;
          description
            "Level of the nexthop that is published to DPAL";
        }
        leaf flags {
          type nexthop-flags-type;
          description
            "Nexthop flags";
        }
        leaf protection-tracker-id {
          type uint64;
          description
            "Protection tracker pointed by this path";
        }
        uses v6-next-hop-info;
      }
    }
  }

  grouping ipv4-adj {
    container ipv4-adj {
      config false;
      list ipv4-adjacency {
        description
          "IPV4 adjacency information, IP to MAC binding";
        key "if-index";
        leaf if-index {
          type uint64;
          description
            "Interface Index";
        }
        leaf interface {
          type string;
          description
            "Interface Name";
        }
        leaf link-status {
          type string;
          description
            "Interface status";
        }
        leaf vrf-id {
          type uint32;
          description
            "VRF id which the interface belongs to";
        }
        uses v4-adj-info;
        uses v4-nht-info;
      }
    }
  }

  grouping ipv6-adj {
    container ipv6-adj {
      config false;
      list ipv6-adjacency {
        description
          "IPV6 adjacency information, IP to MAC binding";
        key "if-index";
        leaf if-index {
          type uint64;
          description
            "Interface Index";
        }
        leaf interface {
          type string;
          description
            "Interface Name";
        }
        leaf link-status {
          type string;
          description
            "Interface status";
        }
        leaf vrf-id {
          type uint32;
          description
            "VRF id which the interface belongs to";
        }
        uses v6-adj-info;
        uses v6-nht-info;
      }
    }
  }

  grouping pub-info {
    leaf next-hop-id {
      type uint32;
    }
    leaf publish-id {
      type uint32;
      description
        "Path/Nexthop ID published to  forwarding layer";
    }
  }

  grouping nh-reach-info {
    leaf next-hop-id {
      type uint32;
    }
    leaf publish-type {
      type publish-path-type;
      description
        "Publish ID type";
    }
    leaf publish-id {
      type uint32;
      description
        "Path/Nexthop ID published to forwarding layer";
    }
  }

  grouping prefix-entry-attributes {
    leaf base-flags {
      type base-flags-type;
    }
    leaf flags {
      type prefix-flags-type;
    }
    leaf forwarding-status {
      type uint32;
      description
        "Last reported forwarding status";
    }
    leaf cookie {
      type uint64;
      description
        "Last received opaque cookie for this route";
    }
    leaf qos-class-id {
      type uint32;
      description
        "QoS class id";
    }
    leaf locator-args {
      type inet:ip-prefix;
      description
        "The mobile gateway locator address";
    }

    leaf last-updated {
      type yang:date-and-time;
      description
        "Last update time";
    }

    uses nh-reach-info;
  }

  grouping ipv4-entries {
    container ipv4-entries {
      list ipv4-prefix-entry {
        description
          "List of IPV4 prefix entries in the fib table";
        key "prefix";
        leaf prefix {
          type inet:ipv4-prefix;
          description
            "The IPv4 prefix corresponding to the route";
        }

        uses prefix-entry-attributes;
      }
    }
  }

  grouping rnh-info {
    leaf rnh-res-state {
      type rnh-state-type;
      description
        "RNH resolution state";
    }
    leaf recur-level{
      type uint32;
      description
        "Recursion level if RNH is resolved";
    }
    leaf next-hop-id {
      type uint32;
      description
        "Nexthop ID corresponding to rnh prefix given by rib";
    }
    leaf num-ip-igp-paths {
      type uint32;
      description
        "Number of underlay IP IGP paths";
    }
    leaf-list ip-igp-path-id {
      type uint32;
      description
        "List  of IP IGP path IDs";
    }
    leaf mpls-igp-type {
      type publish-path-type;
      description
        "Underlay  MPLS ID type";
    }
    leaf mpls-igp-id {
      type uint32;
      description
        "Underlay  MPLS ID";
    }
    leaf srv6-igp-type {
      type publish-path-type;
      description
        "Underlay SRV6 ID type";
    }
    leaf srv6-igp-id {
      type uint32;
      description
        "Underlay SRV6 ID";
    }
  }

  grouping ipv4-rnh-entries {
    container ipv4-rnh-entries {
      list ipv4-rnh-entry {
        description
          "List of IPV4 rnh entries";
        key "type next-hop";
        leaf type {
          type nexthop-type;
          description
            "Type of recursive next-hop";
        }

        leaf next-hop {
          type nexthop-value-type;
          description
            "The IP address corresponding to the rnh";
        }
        uses rnh-info;
      }
    }
  }

  grouping ipv4-nht-entries {
    container ipv4-nht-entries {
      list ipv4-nht-entry {
        description
          "List of Nexthop tracking requests in IPV4 fib table";
        key "nht";
        leaf nht {
          type inet:ip-address-no-zone;
          description
            "IPV4 address of the tracked Nexthop ";
        }
        leaf res-route {
          type inet:ipv4-prefix;
          description
            "The IPv4 prefix corresponding to the tracked nexthop ";
        }
        leaf mpls-reachable {
          type boolean;
          description
            "Whether this prefix is reachable via labeled path";
        }
        leaf-list clients {
          type string;
          description
            "List of clients tracking nexthop";
        }
      }
    }
  }

  grouping ipv4-label-entries {
    container ipv4-label-entries {
      list ipv4-label-entry {
        description
          "Label entries in the IPV4 fib table";
        key "local-label";
        leaf local-label {
          type uint32;
          description
            "The FEC Label entry (ILM) associated with the IPV4 fib table";
        }
        leaf  vpn-table-id {
          type uint32;
          description
            "VPN table id associated with the label";
        }
        leaf ifindex {
          type uint64;
          description
            "Interface index associated with the label";
        }
        leaf control-word {
          type boolean;
          description
            "True if the control word is enabled";
        }
        leaf flow-label {
          type boolean;
          description
            "True if the flow label is enabled";
        }
        leaf domain-name {
          type string;
          description
            "Indicates the domain of the label entry.";
        }
        uses pub-info;
      }
    }
  }

  grouping ipv6-entries {
    container ipv6-entries {
      list ipv6-prefix-entry {
        description
          "List of IPV6 prefix entries in the fib table";
        key "prefix";
        leaf prefix {
          type inet:ipv6-prefix;
          description
            "The IPv6 prefix corresponding to the route";
        }

        uses prefix-entry-attributes;
      }
    }
  }

  grouping ipv6-rnh-entries {
    container ipv6-rnh-entries {
      list ipv6-rnh-entry {
        description
          "List of IPV6 RNH entries";
        key "type next-hop";
        leaf type {
          type nexthop-type;
          description
            "Type of recursive next-hop";
        }
        leaf next-hop {
          type nexthop-value-type;
          description
            "The IP address or nexthop ID corresponding to the RNH";
        }
        uses rnh-info;
      }
    }
  }

  grouping ipv6-nht-entries {
    container ipv6-nht-entries {
      list ipv6-nht-entry {
        description
          "List of Nexthop tracking requests in IPV6 fib table";
        key "nht";
        leaf nht {
          type union {
            type uint32;
            type inet:ipv6-address-no-zone;
          }
          description
            "IPV6 address or RNH ID of the Tracked Nexthop ";
        }
        leaf resolved {
          type boolean;
          description
            "Whether this RNH is resolved";
        }
        leaf res-route {
          type inet:ipv6-prefix;
          description
            "The IPv6 prefix corresponding to the tracked nexthop ";
        }
     	leaf mpls-reachable {
          type boolean;
          description
            "Whether this RNH is reachable via labeled path";
        }
        leaf-list clients {
          type string;
          description
            "List of clients tracking nexthop";
        }
      }
    }
  }

  grouping ipv6-label-entries {
    container ipv6-label-entries {
      list ipv6-label-entry {
        description
          "Label entries in the IPV6 fib table";
        key "local-label";
        leaf local-label {
          type uint32;
          description
            "The FEC Label entry (ILM) associated with the ipv6 prefix";
        }
        leaf  vpn-table-id {
          type uint32;
          description
            "VPN table id associated with the label";
        }
        leaf control-word {
          type boolean;
          description
            "True if the control word is enabled";
        }
        leaf flow-label {
          type boolean;
          description
            "True if the flow label is enabled";
        }
        leaf domain-name {
          type string;
          description
            "Indicates the domain of the label entry.";
        }
        uses pub-info;
      }
    }
  }

  grouping ipv6-sid-entries {
    container ipv6-sid-entries {
      list ipv6-sid-entry {
        description
          "SID entries in the fib table";
        key "sid";
        leaf sid {
          type inet:ipv6-prefix;
          description
            "The sid value ";
        }
        leaf micro-segment-behaviour-unode {
          type  boolean;
          description
            "This designates sid as usid";
        }
        leaf function {
          type arc-srv6-types:srv6-endpoint-behavior-type;
        }

        leaf locator-name {
          type string ;
          description
            "locator name";
        }
        leaf sid-table-id {
          type uint32;
          description
            "Table id corresponding END.T or END.DT variants";
        }
        leaf network-instance {
          type string;
          description
            "Network Instance name";
        }
        uses pub-info;
      }
    }
  }

  grouping tunnel-termination-entry-forward {
    leaf next-hop {
      type nexthop-value-type;
      description
        "Next-hop information for terminating gateway";
    }

    leaf next-hop-network-instance {
      type string;
      description
        "Network-instance at which the next-hop is reachable";
    }

    uses pub-info;
  }

  grouping tunnel-termination-entry-state {
    leaf srv6-sid {
      type inet:ipv6-address;
      description
        "DT4/DT6 SID";
    }

    leaf endpoint-function {
      type arc-srv6-types:srv6-endpoint-behavior-type;
      description
        "Endpoint behaviour";
    }

    leaf inner-network-instance {
      type string;
      description
        "Network Instance name";
    }

    leaf inner-vrf-id {
      type uint32 ;
      description
        "Inner vrf id corresponding END.T or END.DT variants";
    }

    leaf fallback-network-instance {
      type string;
      description
        "Network instance name for fallback of GTP-U message";
    }

    leaf fallback-vrf-id {
      type uint32;
      description
        "Fallback vrf id for GTP-U message";
    }

    leaf binding-sid {
      type inet:ipv6-prefix;
      description
        "Nexthop binding sid";
    }
  }

  grouping tunnel-termination-entry-common {
    leaf address-family {
      type identityref {
        base oc-types:ADDRESS_FAMILY;
      }
      description
        "Address-family of the destination";
    }

    leaf gtp-source-prefix {
      type inet:ipv6-prefix;
      description
        "GTP source prefix in case of GTP4.D function";
    }
  }

  grouping ipv6-tunnel-termination-entries {
    container ipv6-tunnel-termination-entries {
      list ipv6-tunnel-termination-entry {
        description
          "Tunnel termination entries in the fib table";
        key "ip teid";

        leaf ip {
          type inet:ipv6-prefix;
          description
            "Tunnel termination IP";
        }

        leaf teid {
          type inet:ipv4-prefix;
          description
            "Tunnel temrination TE-ID";
        }

        container state {
          uses tunnel-termination-entry-common;
          uses tunnel-termination-entry-state;
          uses tunnel-termination-entry-forward;
        }
      }
    }
  }

  grouping total-stats {
    container all-stats {
      leaf total-count {
        type yang:counter64;
        description
          "Total number of objects present in the fib table";
      }
      leaf total-creates {
        type yang:counter64;
        description
          "Total number of creates received  for the object";
      }
      leaf total-updates {
        type yang:counter64;
        description
          "Total number of updates  received for the object";
      }
      leaf total-deletes {
        type yang:counter64;
        description
          "Total number of deletes  received for the object";
      }
      leaf total-drop-suppress {
        type yang:counter64;
      }
      leaf total-duplicate-updates {
        type yang:counter64;
        description
          "Total number of duplicate updates  received for the object";
      }
      leaf total-skip-publish {
        type yang:counter64;
      }
    }
  }

  grouping curr-ids {
    container all-ids {
      leaf id-count {
        type yang:counter32;
        description
          "Total number of container IDs in use";
      }
    }
  }

  grouping txl-stats {
    container txlist-stats {
      leaf retry-count {
        type yang:counter64;
        description
          "Total number of ipc retries";
      }
    }
  }

  grouping publish-stats {
    container publish-stats {
      leaf total-published {
        type yang:counter64;
        description "Current number of objects in use (published to DPAL)";
      }
      leaf high-water-mark {
        type yang:counter64;
        description "High-water mark of objects in use (peak concurrent published)";
      }
      leaf high-water-mark-time {
        type yang:date-and-time;
        description
          "Time when the current high-water mark was recorded";
      }
    }
  }

  grouping restart-stats {
    container all-stats {
      leaf stale-marks {
        type yang:counter64;
        description
          "Total number of objects marked stale";
      }
      leaf stale-refreshes {
        type yang:counter64;
        description
          "Total number of objects refreshed";
      }
      leaf stale-sweeps {
        type yang:counter64;
        description
          "Total number of objects swept";
      }
      leaf last-stale-marks {
        type yang:counter64;
      }
      leaf last-stale-refreshes {
        type yang:counter64;
      }
      leaf last-stale-sweeps {
        type yang:counter64;
      }
    }
  }

  grouping stats {
    description
      "Table specific counters";

    container routes {
      description
        "Number of Routes";
      uses total-stats;
    }
    container rnhs {
      description
        "Number of RNHs";
      uses total-stats;
    }
    container cross-af-rnhs {
      description
        "Number of Cross AF RNHs";
      uses total-stats;
    }
    container labels {
      description
        "Number of Labels";
      uses total-stats;
    }
    container sids {
      description
        "Number of Sids";
      uses total-stats;
    }
    container adj-routes {
      description
        "Number of adj Routes";
      uses total-stats;
    }
    container nexthops {
      description
        "Number of Nexthops (nhids)";
      uses total-stats;
    }
    container paths {
      description
        "Number of Paths (path-ctx)";
      uses total-stats;
    }
    container tables {
      description
        "Number of Tables ";
      uses total-stats;
    }
    container ids {
      description
        "Current Number of Containers Ids allocated ";
      uses curr-ids;
    }
    container eos0-nh-ids {
      description
        "Current Number of EOS0_NH Containers Ids allocated ";
      uses curr-ids;
    }
    container txlist {
      description
        "Txlist statistics";
      uses txl-stats;
    }
    container nht-req-stats {
      description
        "NHT request statistics";
      uses total-stats;
    }
    container nht-resp-stats {
      description
        "NHT response statistics";
       uses total-stats;
     }
  }

  grouping rib-restart-stats {
    description
      "RIB restartability Table specific counters";

    container routes {
      description
        "Number of Routes";
      uses restart-stats;
    }
    container rnhs {
      description
        "Number of RNHs";
      uses restart-stats;
    }
    container labels {
      description
        "Number of Labels";
      uses restart-stats;
    }
    container sids {
      description
        "Number of Sids";
      uses restart-stats;
    }
    container nexthops-recursive {
      description
        "Number of Recursive Nexthops (nhids)";
      uses restart-stats;
    }
    container nexthops-non-recursive {
      description
        "Number of Non-Recursive Nexthops (nhids)";
      uses restart-stats;
    }
  }

  grouping dpal-publish-stats {
    description
      "counters specific to publish stats from FIB.";

    container nexthop {
        description "single nexthop";
        uses publish-stats;
    }
    container nexthop-group {
        description "ecmp nexthop";
        uses publish-stats;
    }
    container protected-nexthop {
        description "protected nexthop";
        uses publish-stats;
    }
  }

  grouping stats-entries {
    description
      "grouping for FIB statistics";

    container stats-entries {
      config false;
      description
        "container for FIB stats";
      uses stats;
    }
    container rib-restart-stats {
      config false;
      description
        "FIB Counters related to RIB restartability ";
      uses rib-restart-stats;
    }
    container dpal-publish-stats {
      config false;
      description
        "FIB Counters related to publishing to DPAL";
      uses dpal-publish-stats;
    }
  }

  grouping path-ctx-cmn {
    description
      "Path information";

    leaf path-type {
      type fib-path-type;
      description
        " Indicates Path type ";
    }
    leaf network-instance {
      type string;
      description
        "Network Instance name";
    }
    leaf nh-tableid {
      type uint32;
      description
        "Nexthop Table ID";
    }
    leaf nh-type {
      type nexthop-type;
      description
        "Nexthop Type";
    }
    leaf next-hop {
      type nexthop-value-type;
      description
        "The next-hop that is to be used for the  route
        - this may be specified as an IP address, an interface
        or a pre-defined next-hop type - for instance, DROP.";
    }
    leaf interface {
      type string;
      description
        "Name of the interface the nexthop could be reached";
    }
    leaf ifindex {
      type uint64;
    }
    leaf overlay-ifindex {
      type uint32;
      description
        "Interface index an overlay recursive route is learned over";
    }
    leaf tunnel-id {
      type uint32;
      description
        "Next-hop Tunnel ID";
    }
    leaf-list mpls-label-stack {
      type uint32;
      description
        "MPLS label stack pushed by this path";
    }
    leaf flags {
      type bits {
        bit ADJ_UNRESOLVED {
          position 0;
        }
        bit RNH_UNRESOLVED {
          position 1;
        }
        bit IMPLICIT_NULL {
          position 2;
        }
        bit MPLS {
          position 3;
        }
        bit MPLS_UNRESOLVED {
          position 4;
        }
        bit SRV6 {
          position 5;
        }
        bit SRV6_UNRESOLVED {
          position 6;
        }
        bit BACKUP {
          position 7;
        }
        bit SAME_GATEWAY {
          position 8;
        }
        bit UNNUMBERED {
          position 9;
        }
        bit SR {
          position 10;
        }
      }
      description "Path Flags";
    }
    leaf backup {
      type boolean;
      description
        "Path is backup";
    }
    leaf refcount {
      type uint32;
      description
        "Indicates number of nexthops using this path";
    }
    leaf level {
      type uint32;
      description
        "level of the path";
    }
  }

  grouping ipv4-path-ctx {
    container ipv4-path-ctx {
      config false;
      list ipv4-path {
        description
          "List of Paths present in IPV4 fib table";
        key "path-id";
        leaf path-id {
          type uint32;
          description
            "Indicates the ID of the path";
        }
        uses path-ctx-cmn;
      }
    }
  }

  grouping ipv6-path-ctx {
    container ipv6-path-ctx {
      config false;
      list ipv6-path {
        description
          "List of Paths present in IPV6 fib table";
        key "path-id";
        leaf path-id {
          type uint32;
          description
            "Indicates the ID of the path";
        }
        uses path-ctx-cmn;
      }
    }
  }

  grouping ids-cmn {
    description
      "Container ID information";

    leaf id-type {
      type string;
      description
        "Specifies if the ID allocated is for path or NH ";
    }
    leaf refcount {
      type uint32;
      description
        "Refcount for  the ID";
    }
    leaf path-type {
      type fib-path-type;
      description
        "Indicates Path type  if the ID corresponds to a path";
    }
    leaf-list pathids {
      type uint32;
    }
    leaf nh-addr {
      type inet:ip-address-no-zone;
      description
        "Specifies the NH address corresponding to the path
         if applicable";
    }
  }

  grouping ipv4-ids {
    container ipv4-id-list {
      config false;
      list ipv4-container-id {
        description
          "Container ID Information  for IPV4 FIB table";
        key "id";
        leaf id {
          type uint32;
          description
            "Container ID allocated by FIB";
        }
        uses ids-cmn;
      }
    }
  }

  grouping ipv6-ids {
    container ipv6-id-list {
      config false;
      list ipv6-container-id {
        description
          "Container ID Information  for IPV6 FIB table";
        key "id";
        leaf id {
          type uint32;
          description
            "Container ID allocated by FIB";
        }
        uses ids-cmn;
      }
    }
  }

  grouping ipv4-eos0-nh-ids {
    container ipv4-eos0-nh-id-list {
      config false;
      list ipv4-eos0-nh-container-id {
        description
          "Container ID Information for IPV4 EOS0 NHID table";
        key "id";
        leaf id {
          type uint32;
          description
            "EOS0 NH Container ID allocated by FIB";
        }
        uses ids-cmn;
      }
    }
  }

  grouping ipv6-eos0-nh-ids {
    container ipv6-eos0-nh-id-list {
      config false;
      list ipv6-eos0-nh-container-id {
        description
          "Container ID Information for IPV6 EOS0 NHID table";
        key "id";
        leaf id {
          type uint32;
          description
            "EOS0 NH Container ID allocated by FIB";
        }
        uses ids-cmn;
      }
    }
  }

  grouping fib-lpm-top {
    container fib-lpm {
      description
        "Perform a Longest Prefix Match lookup in the FIB";

      action v4-route {
        input {
          leaf address {
            type inet:ipv4-address;
            mandatory true;
            description
              "The IPv4 address to be looked from FIB";
          }
        }
        output {
          leaf prefix {
            type inet:ipv4-prefix;
            description
              "The IPv4 prefix corresponding to the route";
          }
          uses pub-info;
        }
      }

      action v6-route {
        input {
          leaf address {
            type inet:ipv6-address;
            mandatory true;
            description
              "The IPv6 address to be looked from FIB";
          }
        }
        output {
          leaf prefix {
            type inet:ipv6-prefix;
            description
              "The IPv6 prefix corresponding to the route";
          }
          uses pub-info;
        }
      }
    }
  }

  grouping ipv4-tunnels {
    description
      "Grouping for tunnel entries by lookup keys";

    container ipv4-tunnels {
      config false;
      list entry {
        key "tunnel-id";
        description
          "tunnel-id used for lookup";
        leaf tunnel-id {
          type uint32;
          description
            "tunnel-ID associated with this tunnel";
        }
        leaf ltep-ip {
          type inet:ipv4-address-no-zone;
          description
            "local tunnel-endpoint ipv4 address";
        }
        leaf rtep-ip {
          type inet:ipv4-address-no-zone;
          description
            "remote tunnel-endpoint ipv4 address";
        }
        leaf tunnel-table-id {
          type uint32;
          description
            "underlay table-id for this tunnel";
        }
        leaf l4-src-port {
          type uint16;
          description
            "UDP source port for this tunnel";
        }
        leaf l4-dst-port {
          type uint16;
          description
            "UDP destination port for this tunnel";
        }
        leaf flood-and-learn {
          type boolean;
          description
            "If set to true for the tunnel, mac-learning happens through flooding and not via EVPN.";
        }
        leaf tunnel-encap {
          type enumeration {
            enum "VXLAN" {
              description
                "VXLAN tunnel encapsulation";
            }
            enum "LI" {
              description
                "Lawful Intercept tunnel encapsulation";
            }
          }
          description
            "tunnel encapsulation";
        }
        leaf domain-name {
          type string;
          description
            "Indicates the domain of the ipv4 (VXLAN) tunnel entry.";
        }
        leaf session-id {
          type uint32;
          description
            "Lawful Intercept tunnel jmirror Session ID";
        }
        leaf intercept-id {
          type uint32;
          description
            "Lawful Intercept tunnel jmirror Intercept ID";
        }
        leaf jmirror-header {
          type boolean;
          description
            "Lawful Intercept tunnel jmirror header status";
        }
        uses pub-info;
      }
    }
  }

  grouping ipv6-tunnels {
    description
      "Grouping for tunnel entries by lookup keys";

    container ipv6-tunnels {
      config false;
      list entry {
        key "tunnel-id";
        description
          "tunnel-id used for lookup";
        leaf tunnel-id {
          type uint32;
          description
            "tunnel-ID associated with this tunnel";
        }
        leaf ltep-ip {
          type inet:ipv6-address-no-zone;
          description
            "local tunnel-endpoint ipv6 address";
        }
        leaf rtep-ip {
          type inet:ipv6-address-no-zone;
          description
            "remote tunnel-endpoint ipv6 address";
        }
        leaf tunnel-table-id {
          type uint32;
          description
            "underlay table-id for this tunnel";
        }
        leaf tunnel-encap {
          type enumeration {
            enum "SRV6" {
              description
                "SRV6 tunnel encapsulation";
            }
          }
          description
            "tunnel encapsulation";
        }
        leaf function {
          type arc-srv6-types:srv6-endpoint-behavior-type;
        }
        leaf-list sid-list {
          type inet:ipv6-address-no-zone;
          description
            "The list of SIDs added to SRv6 tunnel header";
        }
        leaf locator-args {
          type inet:ipv6-prefix;
          description
            "The mobile gateway locator address";
        }
        uses pub-info;
      }
    }
  }

  grouping protectiontrackers {
    description
      "Parameters for protection tracking in FIB";
    leaf interface {
      type string;
      description
        "Name of the interface";
    }
    leaf next-hop {
      type inet:ip-address-no-zone;
      description
        "Next-hop address";
    }
    leaf network-instance {
      type string;
      description
        "Next hop network instance";
    }
    leaf bfd-source {
      type inet:ip-address-no-zone;
      description
        "BFD source address";
    }
    leaf bfd-destination {
      type inet:ip-address-no-zone;
      description
        "BFD destination address";
    }
    leaf bfd-session-id {
      type uint64;
      description
        "BFD session ID";
    }
    leaf backup-in-use {
      type boolean;
      description
        "Backup is in use";
    }
  }
  grouping ipv4-protection-trackers {
    description
      "Grouping for protection tracker entries";
    container ipv4-protection-trackers {
      list entry {
        key "tracker-id";
        description
          "Protection tracker ID";
        leaf tracker-id {
          type uint64;
          description
            "Protection tracker ID";
        }
        uses protectiontrackers;
      }
    }
  }

  grouping ipv6-protection-trackers {
    description
      "Grouping for protection tracker entries";
    container ipv6-protection-trackers {
      list entry {
        key "tracker-id";
        description
          "Protection tracker ID";
        leaf tracker-id {
          type uint64;
          description
            "Protection tracker ID";
        }
        uses protectiontrackers;
      }
    }
  }

  grouping fib-top {
    description
      "Top level grouping for fib control plane routes";

    list fib {
      key "address-family";
      config false;
      description
        "The Control plane Forwarding table associated with an address family.";

      leaf address-family {
        type identityref {
          base oc-types:ADDRESS_FAMILY;
        }
        mandatory true;
        config false;
      }
      uses ipv4-entries {
        when "address-family = 'oc-types:IPV4'";
      }
      uses ipv4-rnh-entries {
        when "address-family = 'oc-types:IPV4'";
      }
      uses ipv4-nht-entries {
        when "address-family = 'oc-types:IPV4'";
      }
      uses ipv4-next-hops {
        when "address-family = 'oc-types:IPV4'";
      }
      uses ipv4-label-entries {
        when "address-family = 'oc-types:IPV4'";
      }
      uses ipv4-adj {
        when "address-family = 'oc-types:IPV4'";
      }
      uses ipv4-path-ctx {
        when "address-family = 'oc-types:IPV4'";
      }
      uses ipv4-ids {
        when "address-family = 'oc-types:IPV4'";
      }
      uses ipv4-eos0-nh-ids {
        when "address-family = 'oc-types:IPV4'";
      }
      uses ipv4-tunnels {
        when "address-family = 'oc-types:IPV4'";
      }
      uses ipv4-protection-trackers {
        when "address-family = 'oc-types:IPV4'";
      }
      uses ipv6-entries {
        when "address-family = 'oc-types:IPV6'";
      }
      uses ipv6-rnh-entries {
        when "address-family = 'oc-types:IPV6'";
      }
      uses ipv6-nht-entries {
        when "address-family = 'oc-types:IPV6'";
      }
      uses ipv6-next-hops {
        when "address-family = 'oc-types:IPV6'";
      }
      uses ipv6-label-entries {
        when "address-family = 'oc-types:IPV6'";
      }
      uses ipv6-adj {
        when "address-family = 'oc-types:IPV6'";
      }
      uses ipv6-path-ctx {
        when "address-family = 'oc-types:IPV6'";
      }
      uses ipv6-ids {
        when "address-family = 'oc-types:IPV6'";
      }
      uses ipv6-eos0-nh-ids {
        when "address-family = 'oc-types:IPV6'";
      }
      uses ipv6-sid-entries {
        when "address-family = 'oc-types:IPV6'";
      }
      uses ipv6-tunnel-termination-entries {
        when "address-family = 'oc-types:IPV6'";
      }
      uses ipv6-tunnels {
        when "address-family = 'oc-types:IPV6'";
      }
      uses ipv6-protection-trackers {
        when "address-family = 'oc-types:IPV6'";
      }
      uses stats-entries;
    }
  }

  augment "/oc-netinst:network-instances/oc-netinst:network-instance" {
    uses fib-top {
      when "./oc-netinst:config/oc-netinst:type = 'oc-ni-types:L3VRF' and " +
           "/arc-platform:platform/arc-platform:deployment-type != 'arc-platform:DISTRIBUTED'";
    }
    uses fib-lpm-top {
      when "./oc-netinst:config/oc-netinst:type = 'oc-ni-types:L3VRF' and " +
           "/arc-platform:platform/arc-platform:deployment-type != 'arc-platform:DISTRIBUTED'";
    }
  }
}
