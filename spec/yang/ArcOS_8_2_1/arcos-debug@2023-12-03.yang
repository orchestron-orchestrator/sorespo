module arcos-debug {
  yang-version 1.1;
  namespace "http://yang.arrcus.com/arcos/debug";
  prefix arc-dbg;

  import ietf-inet-types {
    prefix inet;
  }

  import openconfig-policy-types {
    prefix oc-pol-types;
  }

  import openconfig-isis-types {
    prefix oc-isis-types;
  }

  organization
    "Arrcus, Inc.";

  contact
    "Arrcus, Inc.
     2077 Gateway Place
     Suite 400
     San Jose, CA 95110

     E-mail: yang-support@arrcus.com";

  description
    "This module contains definitions for the native 
     ArcOS debug domain.

     Copyright (c) 2016-2023, by Arrcus, Inc.
     All rights reserved.";
  
  revision 2023-12-03 {
    description
      "Add model for debug state";
  } 

  grouping default-actions {
    /*
    action enable {
      description
        "Enable debug";

      input {
        leaf item {
          type leafref {
	          path "../../enable-items/item";
          }
	        default "all";
        }
      }
      output {
        leaf response {
          type string;
          mandatory true;
        }
      }
    }

    action disable {
      description
        "Disable debug";

      input {
        leaf item {
          type leafref {
            path "../../disable-items/item";
          }
	        default "all";
        }
      }
      output {
        leaf response {
          type string;
          mandatory true;
        }
      }
    }
    */

    list enable-items {
      key "item";
      leaf item {
        type string;
      }
    }

    list disable-items {
      key "item";
      leaf item {
        type string;
      }
    }

    leaf debug-enabled {
      description
        "State of debug. Enabled or Disabled";
      type boolean;
    }
  }

  grouping debug-enable-action {
    action enable {
      description
        "Enable the specific debug filter";

      input {
        leaf item {
          type boolean;
	        default true;
        }
      }
      output {
        leaf response {
          type string;
          mandatory true;
        }
      }
    }
  }

  grouping debug-disable-action {
    action disable {
      description
        "Disable the specific debug filter";

      input {
        leaf item {
          type boolean;
	        default true;
        }
      }
      output {
        leaf response {
          type string;
          mandatory true;
        }
      }
    }
  }

  grouping debug-default-actions {
    uses arc-dbg:debug-enable-action;
    uses arc-dbg:debug-disable-action;
  }

  grouping debug-component-top {
    list component-debug-items {
      key "item-name";

      leaf item-name {
        type string;
      }

      leaf enabled {
        type boolean;
        default false;
      }

      uses arc-dbg:debug-default-actions;
    }
  }

  grouping ip-address-match-filter {
    leaf-list ip-address-matches {
      description
        "Filter with one or more IP addresses to match";
      config false;
      type inet:ip-address;
    }

    action ip-address-match {
      description
        "One or more IP addresses to match";

      input {
        leaf-list addresses {
          type inet:ip-address;
        }
      }
      output {
        leaf response {
          type string;
          mandatory true;
        }
      }
    }
  }

  grouping sysid-match-filter {
    leaf-list system-id-matches {
      description
        "Filter with one or more System-Ids to match";
      config false;
      type oc-isis-types:system-id;
    }

    action system-id-match {
      description
        "One or more System-Ids to match";

      input {
        leaf-list system-ids {
          type oc-isis-types:system-id;
        }
      }
      output {
        leaf response {
          type string;
          mandatory true;
        }
      }
    }
  }

  grouping ip-prefix-match-filter {
    leaf-list ip-prefix-matches {
      description
        "Filter with one or more IP Prefixes to match";
      config false;
      type inet:ip-prefix;
    }

    action ip-prefix-match {
      description
        "One or more IP Prefixes to match";

      input {
        leaf-list prefixes {
          type inet:ip-prefix;
        }
      }
      output {
        leaf response {
          type string;
          mandatory true;
        }
      }
    }
  }

  grouping intf-match-filter {
    leaf-list interface-matches {
      description
        "Filter with one or more interfaces to match";
      config false;
      type string;
    }

    action interface-match {
      description
        "One or more interfaces to match";

      input {
        leaf-list interfaces {
          type string;
        }
      }
      output {
        leaf response {
          type string;
          mandatory true;
        }
      }
    }
  }

  grouping arrcus-debug-protocols-top {
    container protocols {
      description
        "The routing protocols that are enabled for this
        network-instance.";
      config false;

      list protocol {
        key "identifier name";
        config false;

        description
          "A process (instance) of a routing protocol. Some
          systems may not support more than one instance of
          a particular routing protocol";

        leaf identifier {
          description
            "The protocol identifier for the instance";

          type identityref {
            base "oc-pol-types:INSTALL_PROTOCOL_TYPE";
          }
        }

        leaf name {
          type string;
          description
            "A unique name for the protocol instance";
        }
      }
    }
  }

  grouping debug-ni-attach-top {
    list debug-attach-points {
      key "component";

      leaf component {
        type string;
      }
    }
  }

  grouping arrcus-debug-network-instances-top {
    description
      "Top-level grouping containing a list of network instances.";

    container network-instances {
      description
        "The L3 forwarding instances that are configured on the local system";
      config false;

      list network-instance {
        key "name";
        min-elements 2;
        max-elements 512;
        config false;

        description
          "Network instances configured on the local system";

        leaf name {
          type string;
          description
            "A unique name identifying the network instance";
        }

        uses debug-ni-attach-top;
        uses arrcus-debug-protocols-top;
      }
    }
  }

  grouping debug-global-attach-top {
    list debug-attach-points {
      key "component";

      leaf component {
        type string;
      }
    }
  }

  grouping arrcus-debug-top {
    container debug {
      description
        "Debug logging control";
      config false;

      list components {
        description
          "Debug the named component";

        key "component";
        leaf component {
          type string;
        }

        uses default-actions;
      }

      uses debug-global-attach-top;
      uses arrcus-debug-network-instances-top;

    }
  }

  uses arrcus-debug-top;
}
