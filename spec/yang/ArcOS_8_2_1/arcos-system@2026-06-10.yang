module arcos-system {
  yang-version 1.1;
  namespace "http://yang.arrcus.com/arcos/system";
  prefix arc-sys;

  import ietf-inet-types {
    prefix inet;
  }

  import openconfig-interfaces {
    prefix oc-if;
  }

  import ietf-yang-types {
    prefix yang;
  }

  import arcos-platform {
    prefix arc-platform;
  }

  organization
    "Arrcus, Inc.";

  contact
    "Arrcus, Inc.
     2077 Gateway Place
     Suite 400
     San Jose, CA 95110

     E-mail: yang-support@arrcus.com";

  description
    "This module contains definitions for the
     native ArcOS system domain.

     Copyright (c) 2016-2019 by Arrcus, Inc.
     All rights reserved.";
  revision 2026-06-10 {
    description
      "Add request-system-rollback RPC (hotfix-only revert) and
       enforce onl/firmware vs hotfix mutual-exclusion.";
  }
  revision 2025-07-30 {
    description
      "Addding choise statement to install rpc.";
  }
  revision 2025-07-17 {
    description
      "changed date and time format to the new cli.";
  }
  revision 2025-07-02 {
    description
      "redesign install cli and allowing support for simultaneous upgrade of arcos and firmware.";
  }

  revision 2025-05-14 {
    description
      "Changing the date and time format to accept time at minute level.";
  }

  revision 2025-05-12 {
    description
      "Support onie install mode from cli";
  }

  revision 2024-10-04 {
    description
      "Support scheduling reboot and install at specified time";
  }

  revision 2022-06-29 {
    description
      "Support difference between Candidate and Running Datastores";
  }

  revision 2019-10-01 {
    description "Initial version";
  }

  typedef status-code {
    type enumeration {
      enum SUCCESS {
        description
          "Operation succeeded";
      }

      enum FAILURE {
        description
          "Operation failed";
      }
    }
  }

  typedef date-and-time-no-seconds {
    type string {
      pattern '\d{4}-[0-1][0-9]-[0-3][0-9]T[0-2][0-9]:[0-5][0-9](Z|[\+\-][0-1][0-9]:[0-5][0-9])?';
    }
    description
    "date and time without seconds, with range validation.
     Examples: 2025-05-13T22:24Z, 2025-05-13T09:30+05:30";
}


  rpc request-configuration-factory-default-reboot {
    description
      "Reset config back to factory default and reboot device.
       NOTE: This command cannot be used for ArcRR (container) images";

    output {
      leaf status {
        type status-code;
          description
            "Result of the operation";
      }

      leaf message {
        type string;
          description
            "Description of the result of the operation";
      }
    }
  }

  rpc request-system-ztp-stop {
    description
       "Stop ZTP process.
       NOTE: This command cannot be used on container images";
  }

  rpc request-system-stateful-restart {
    description
       "Stop ZTP process.
       NOTE: This command cannot be used on container images";
  }

  rpc load-configuration {
    description
      "Request to load a configuration to the candidate datastore
       and either commit the configuration to the running datastore
       or provide a diff back to the client in the native CLI text
       format.

       If the commit presence container is omitted from the request
       then the request is a dry-run which will return a diff of the
       candidate and running datastores back to the client in CLI text
       format. For a diff to be returned, the encoding must be set to
       CLI.";

    input {
      leaf operation {
        mandatory true;
        type enumeration {
          enum MERGE {
            description
              "Merge the configuration specified in the config leaf
               into the candidate datastore.";
          }
          enum OVERRIDE {
            description
              "Override the complete configuration specified in the
               config leaf into the candidate datastore";
          }
          enum REPLACE {
            description
              "Replace the configuration specified in the config leaf
               into the candidate datastore. All other configuration
               remains as-is.";
          }
        }
        description
          "The load operation for the configuration specified within
           the config leaf.";
      }

      leaf encoding {
        type enumeration {
          enum CLI {
            description
              "Native text based (CLI) configuration format encoding.";
          }
          enum JSON {
            description
              "JSON configuration format encoding.";
          }
        }
        default CLI;
        description
          "The encoding format of the configuration specified within
           the config leaf.";
      }

      leaf config {
        mandatory true;
        type string;
        description
          "The configuration in the encoding format specified from the
           encoding leaf.";
      }

      container commit {
        presence "Commit the candidate configuration";
        description
          "Commit the candidate configuration to the running datastore.
           If this option is omitted then the server will attempt to
           load the configuration specified in the config leaf and
           return a diff (in CLI text based format) to the caller
           within the output data node.  If the commit is successful,
           an rpc-reply with an <ok/> is returned to the caller.";

        leaf comment {
          type string;
          description
            "Optional comment to be recorded for the commit
             transaction.";
        }
      }
    }

    output {
      leaf data {
        type string;
        description
          "This leaf is returned if the commit node is omitted from the
           request.  When this occurs, a dry-run takes effect and a
           diff between the candidate and running datastore is returned
           to the the client.  This is only returned if the request
           encoding is set to 'CLI'. For all other encodings, an
           rpc-error is returned to the client.";
      }
    }
  }

  rpc get-configuration {
    description
      "Request to retrieve a configuration from the running datastore
       in the encoding format specified by the client.";

    input {
      leaf encoding {
        type enumeration {
          enum CLI {
            description
              "Native text based (CLI) configuration format encoding.";
          }
          enum JSON {
            description
              "JSON configuration format encoding.";
          }
        }
        default CLI;
        description
          "The encoding format of the configuration to be returned
           from the running datastore.";
      }
    }

    output {
      leaf data {
        type string;
        description
          "Contains the full configuration of the running datastore in
           the encoding format specified in the request.";
      }
    }
  }

  rpc get-diff {
    description
      "Request to retrieve a configuration diff between the candidate and the
       running datastore in the encoding format specified by the client.";

    input {
      leaf encoding {
        type enumeration {
          enum CLI {
            description
              "Native text based (CLI) configuration format encoding.";
          }
          enum JSON {
            description
              "JSON configuration format encoding.";
          }
          enum XML {
            description
              "XML configuration format encoding.";
          }
        }
        default XML;
        description
          "The encoding format of the configuration to be returned.";
      }
    }

    output {
      leaf data {
        type string;
        description
          "Contains the configuration diff between the candidate datastore in
           the current session and the running datastore in the encoding format
           specified in the request.";
      }
    }
  }

  rpc request-system-reboot {
    description
      "Initiate a reboot to the system.  If no input options are given,
       then a check is done to see if any outstanding exclusive locks
       are held on the candidate database.  If so then an rpc-error is
       returned to the caller.  To override this check, the force
       option must be given in the RPC call.";

    input {
      leaf wait-time {
        type uint8 {
          range 1..120;
        }
        units minutes;
        description
          "Optional node to specify the wait time in minutes (up to 2hr)
           before rebooting the system.";
      }

      leaf cancel {
        type empty;
        description
          "Cancel a previous request for reboot.";
      }

      leaf force {
        type empty;
        description
          "Force the reboot and do not check if any exclusive locks
           exist.";
      }

      container schedule {
        when "not(../cancel)";

        choice option {
          description "Choose between scheduling by time or duration";

          case schedule-at {
            leaf schedule-at {
              type date-and-time-no-seconds;
              description 
                "Takes a date and time to schedule the reboot.
                Use the format YYYY-MM-DDTHH:MM (e.g., 2024-10-07T13:00Z or 2024-10-07T13:00+05:00).
                Use 'Z' for UTC or specify an offset (e.g., +05:00 for 5 hours ahead of UTC).
                If no time zone is provided, local time is assumed.";
            }
          }

          case schedule-after {
            leaf schedule-after {
              type uint16 {
                range "5..max";
              }
              description "Schedule the reboot after a specified number
                           of minutes from the current system time.";
            }
          }
        }
      }
    }
  }

  rpc request-software-load {
    description
      "Initiate the load of a software package";

    input {
      leaf package-name {
        mandatory true;
        type inet:uri {
          length 1..max;
        }
        description
          "A valid ArcOS installation executable either represented
           as a valid URI scheme (e.g. scp://, sftp://, http://) or
           a filesystem absolute path.";
      }

      leaf tag {
        mandatory true;
        type string {
          length 1..128;
        }
        description
          "Upgrade Bundle Tag";
      }
    }
  }

  // DEPRECATED: Use 'request-system-install' for both NOS and firmware upgrades.
  // This RPC will be removed in a future release. See FS ANPN-21823.
  rpc request-software-install {
    status deprecated;
    description
      "[DEPRECATED] Initiate the installation (and optional download) of a
       software package and configuration file to apply post installation.\n\nWARNING: This command is deprecated and will be removed in a future release.\nUse 'request system install <package-type> <package-name> schedule-at/after <timestamp>' instead.";

    input {
      leaf package-name {
        type inet:uri {
          length 1..max;
        }
        description
          "A valid ArcOS installation executable either represented
           as a valid URI scheme (e.g. scp://, sftp://, http://) or
           a filesystem absolute path.";
      }

      leaf upgrade-bundle-tag {
        type inet:uri {
          length 1..max;
        }
        description
          "Upgrade Bundle Tag";

        when "(/arc-platform:platform/arc-platform:deployment-type = 'arc-platform:DISTRIBUTED') and not(../cancel)";
      }

      leaf force {
        type empty;
        description
          "Skip any safety checks and force installation process to continue.
           Use with caution, may lead to traffic disruptions.";
        when "not(../cancel)";
      }

      leaf hitless {
        type empty;
        description
          "Perform a hitless ugprade";

        when "((/arc-platform:platform/arc-platform:type = 'arc-platform:IX8A') or " +
            "(/arc-platform:platform/arc-platform:type = 'arc-platform:AS7712')) and not(../cancel)";
      }

      leaf onie {
        type empty;
        description
          "Perform a onie ugprade";
      }

      leaf config-filename {
        type inet:uri {
          length 1..max;
        }
        description
          "A valid ArcOS configuration to be applied post-installation/
           reboot. The configuration file must be compatible with the
           destination software version and is either represented as a
           valid URI scheme (e.g. scp://, sftp://, http://) or a
           filesystem absolute path.";
        when "not(../hitless) and not(../cancel)";
      }

      leaf source-interface {
        type oc-if:base-interface-ref;
        description
          "Network-instance name to source any external requests from
           for retrieval of package-name or config-filename from remote
           destinations based off the URI scheme.";
        when "not(../cancel)";
      }

      leaf factory-default {
        type empty;
        description
          "Reset the running configuration to factory-default post the
           installation process.  If a config-filename is also passed
           in, the factory-default option takes precedence.";
        when "not(../hitless) and not(../cancel)";
      }

      leaf cancel {
        type empty;
        description "cancel the installation.";
        when "not(../package-name)" {
          description "cancel can only be used when 'package-name' is not set.";
        }
      }

      container schedule {
        when "(../package-name) and not(../cancel)";

        choice option {
          description "Choose between scheduling by time or duration";

          case schedule-at {
            leaf schedule-at {
              type date-and-time-no-seconds;
              description 
                "Takes a date and time to schedule the installation, up to minute precision. 
                Use the format YYYY-MM-DDTHH:MM (e.g., 2024-10-07T13:00Z or 2024-10-07T13:00+05:00).
                Use 'Z' for UTC or specify an offset (e.g., +05:00 for 5 hours ahead of UTC).
                If no time zone is provided, local time is assumed.";
            }
          }

          case schedule-after {
            leaf schedule-after {
              type uint16 {
                range "5..max";
              }
              description "Schedule the installation after a specified
                           number of minutes from the current system time.";
            }
          }
        }
      }

    }
  }
rpc request-system-install {
    description
      "Initiate an installation of a system component.
       This RPC supports both ArcOS NOS and firmware upgrade paths.
       The previous 'request-system-software-install' RPC is now deprecated and
       will be removed in future releases.";

    input {
      choice install-operation {
        mandatory true;
        case run-install {
          // onl/firmware vs hotfix mutual-exclusion is enforced STRUCTURALLY by
          // this choice (selecting hotfix excludes onl/firmware and vice versa),
          // NOT by a `when` on each leaf. This is deliberate: the `schedule`
          // container's `when` below references these leaves, and confd drops an
          // action-input node from the params delivered to the callback when its
          // `when` transitively depends on sibling leaves that themselves carry a
          // `when`. Keeping these leaves `when`-less lets `schedule` reference them
          // and still be delivered. choice/case nodes are schema-only and never
          // appear in the CLI — the operator only ever sees onl/firmware/hotfix.
          choice install-target {
            mandatory true;
            case nos-install {
              leaf onl {
                type inet:uri {
                  length 1..max;
                }
                description
                  "The ArcOS ONL image to install, represented as a URI
                  (e.g., scp://, sftp://, http://) or an absolute filesystem path.
                  The ArcOS ONL image is validated with its metadata.";
              }

              leaf firmware {
                type inet:uri {
                  length 1..max;
                }
                description
                  "The hardware firmware package to install, represented as a URI
                  (e.g., scp://, sftp://, http://) or an absolute filesystem path.
                  Firmware is validated with the vendor-provided API.";
              }
            }
            case hotfix-install {
              leaf hotfix {
                type inet:uri {
                  length 1..max;
                }
                description
                  "The ArcOS hotfix image to install, represented as a URI
                  (e.g., scp://, sftp://, http://) or an absolute filesystem path.
                  The ArcOS hotfix image is validated with its metadata.";
              }
            }
          }

          leaf force {
            type empty;
            description
              "Force the installation and bypass safety checks.
              Use with caution as it may cause service disruption.
              Not applicable to hotfix installation.";
            when "not(../hotfix)";
          }

          leaf hitless {
            type empty;
            description "Perform a hitless upgrade.";
            when "((/arc-platform:platform/arc-platform:type = 'arc-platform:IX8A') or " +
              "(/arc-platform:platform/arc-platform:type = 'arc-platform:AS7712')) and " +
              "(../onl)";
          }

          leaf config-filename {
            type inet:uri {
              length 1..max;
            }
            description
              "An ArcOS configuration to be applied post-installation/reboot.
              Must be compatible with the destination software version.";
            when "not(../hitless) and (../onl)";
          }

          leaf source-interface {
            type oc-if:base-interface-ref;
            description
              "Network-instance name for sourcing remote package or config downloads.";
            
          }

          leaf factory-default {
            type empty;
            description
              "Reset the running configuration to factory-default post-install.
              Not allowed for firmware upgrades.";
            when "(../onl) and not(../hitless)";
          }

          container schedule {
            when "((../onl) or (../firmware) or (../hotfix)) and " +
              "(/arc-platform:platform/arc-platform:deployment-type != 'arc-platform:DISTRIBUTED')";
            description "Schedule installation at a specific time or after a delay.";

            choice option {
              description "Choose between scheduling by timestamp or delay duration.";

              case schedule-at {
                leaf schedule-at {
                  type date-and-time-no-seconds;
                  description
                    "Takes a date and time to schedule the installation, up to minute precision.
                    Use the format YYYY-MM-DDTHH:MM (e.g., 2024-10-07T13:00Z or 2024-10-07T13:00+05:00).
                    Use 'Z' for UTC or specify an offset (e.g., +05:00 for 5 hours ahead of UTC).
                    If no time zone is provided, local time is assumed.";
                }
              }

              case schedule-after {
                leaf schedule-after {
                  type uint16 {
                    range "5..max";
                  }
                  description
                    "Schedule the installation after this number of minutes
                    from the current system time.";
                }
              }
            }
          }
        }
        case cancel-install {
          leaf cancel {
            type empty;
            description "Cancel a previously scheduled installation request.";
          }
        }
      }
    }
  }

  // DEPRECATED: Use 'request-system-rollback' instead.
  // This RPC will be removed in a future release.
  rpc request-software-rollback {
    status deprecated;
    description
      "[DEPRECATED] Initiate rollback of the last installed ArcOS image.
       Use 'request system rollback' instead.";
  }

  rpc request-system-rollback {
    description
      "Rollback the system to a previous state.

       With no arguments, performs an ONL rollback: reverts both system
       software and configuration to the state immediately prior to the
       last software upgrade.

       With the 'hotfix' argument, reverts only the currently-applied
       hotfix and restores the underlying ArcOS image; the base software
       and configuration are otherwise left untouched.";

    input {
      leaf hotfix {
        type empty;
        description
          "Revert only the currently-applied hotfix.  The base ArcOS
           image and running configuration are not changed.  Fails if
           no hotfix is currently applied or if the hotfix backup is
           missing.";
      }
    }
  }

  rpc debug-process-smd {
    description
      "Control debugging for the System Management Daemon (smd)
       process.  An RPC request with no input nodes indicates to
       enable debugging for the entire process.";

    input {
      leaf disable {
        type empty;
        description
          "Disable process debugging.";
      }
    }
  }
}
