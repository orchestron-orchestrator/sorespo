/*
 * Copyright (c) 2026 Juniper Networks, Inc.
 * All rights reserved.
 */
 module junos-conf-root {
   namespace "http://yang.juniper.net/junos/conf/root";

   prefix jc;

   import junos-common-types {
     prefix jt;
     revision-date 2024-01-01;
   }

   organization "Juniper Networks, Inc.";

   contact "yang-support@juniper.net";

   description "Junos YANG module for configuration hierarchies.";

   revision 2024-01-01 {
     description "Junos: 20241218.202301_builder.r1463698";
   }

   container configuration {
     config true;
     uses juniper-config;
     list groups {
       key name;
       ordered-by user;
       description "Configuration groups";
       uses juniper-group;
     }
   }
   grouping juniper-config {
     leaf rcsid {
       description "Revision control system identifier";
       type string;
     }
     leaf version {
       description "Software version information";
       type string;
     }
     leaf-list apply-groups {
       ordered-by user;
       description "Groups from which to inherit configuration data";
       type string;
     }
     list apply-macro {
       key name;
       ordered-by user;
       description "Macro and parameters for commit script expansion";
       uses apply-macro-type;
     }
     container system {
       description "System parameters";
       uses juniper-system;
     }
     container services {
       description "System services";
       uses apply-advanced;
       container rpm {
         presence "enable rpm";
         description "Real-time performance monitoring";
         uses apply-advanced;
         container traceoptions {
           description "RMOPD trace options";
           uses rmopd-traceoptions;
         }
         leaf probe-limit {
           description "Maximum number of concurrent probes allowed";
           default "100";
           type union {
             type string {
               pattern "<.*>|$.*";
             }
             type uint32 {
               range "1 .. 2000";
             }
           }
         }
         container twamp {
           description "Two-way Active Measurement Protocol configuration";
           uses apply-advanced;
           container client {
             description "TWAMP client configuration";
             uses apply-advanced;
             list control-connection {
               key name;
               ordered-by user;
               description "TWAMP control session configuration";
               leaf name {
                 description "Client name";
                 type string {
                   length "1 .. 32";
                 }
               }
               uses apply-advanced;
               container authentication-mode {
                 description "Authentication modes";
                 uses apply-advanced;
                 leaf none {
                   description "No authentication or encryption";
                   type empty;
                 }
               }
               leaf destination-interface {
                 description "Name of output interface for all test sessions";
                 type union {
                   type jt:interface-name;
                   type string {
                     pattern "<.*>|$.*";
                   }
                 }
               }
               leaf persistent-results {
                 description "Displays the old results along with present. Default disable";
                 type empty;
               }
               leaf control-type {
                 description "TWAMP control connection type";
                 default "managed";
                 type enumeration {
                   enum "light" {
                     description "No control connection to manage test sessions";
                   }
                   enum "managed" {
                     description "Control connection will negotiate test sessions";
                   }
                 }
               }
               leaf tcp-keepidle {
                 description "Time to start TCP KEEPALIVEs on control connection (default 120)";
                 default "120";
                 units "seconds";
                 type union {
                   type string {
                     pattern "<.*>|$.*";
                   }
                   type uint32 {
                     range "1 .. 600";
                   }
                 }
               }
               leaf tcp-keepintvl {
                 description "Delay between succesive TCP KEEPALIVEs (default 5)";
                 default "5";
                 units "seconds";
                 type union {
                   type string {
                     pattern "<.*>|$.*";
                   }
                   type uint32 {
                     range "1 .. 600";
                   }
                 }
               }
               leaf tcp-keepcnt {
                 description "Number of TCP KEEPALIVEs sent (default 6)";
                 default "6";
                 type union {
                   type string {
                     pattern "<.*>|$.*";
                   }
                   type uint32 {
                     range "1 .. 50";
                   }
                 }
               }
               leaf destination-port {
                 description "TCP TWAMP client listening port for the test sessions. Default 862";
                 default "862";
                 type union {
                   type string {
                     pattern "<.*>|$.*";
                   }
                   type uint16 {
                     range "862 .. 65535";
                   }
                 }
               }
               leaf history-size {
                 description "Number of stored history entries";
                 default "50";
                 type union {
                   type string {
                     pattern "<.*>|$.*";
                   }
                   type uint32 {
                     range "0 .. 512";
                   }
                 }
               }
               leaf moving-average-size {
                 description "Number of samples used for moving average";
                 default "0";
                 type union {
                   type string {
                     pattern "<.*>|$.*";
                   }
                   type uint32 {
                     range "0 .. 512";
                   }
                 }
               }
               leaf routing-instance {
                 description "Routing instance used by the test sessions";
                 type string {
                 }
               }
               leaf source-address {
                 description "Source address of TWAMP Control client";
                 type jt:ipv4addr;
               }
               leaf target-address {
                 description "Destination IPv4 address of TWAMP responder";
                 type jt:ipv4addr;
               }
               leaf test-count {
                 description "Total number of test session iterations";
                 default "0";
                 type union {
                   type string {
                     pattern "<.*>|$.*";
                   }
                   type uint32 {
                     range "0 .. 4294967290";
                   }
                 }
               }
               leaf test-interval {
                 description "Delay between test session iterations";
                 default "1";
                 units "seconds";
                 type union {
                   type string {
                     pattern "<.*>|$.*";
                   }
                   type uint16 {
                     range "1 .. 255";
                   }
                 }
               }
               container traps {
                 description "Trap to send if threshold is met or exceeded";
                 uses apply-advanced;
                 leaf test-iteration-done {
                   description "All test sessions configured under the control connection have completed an iteration";
                   type empty;
                 }
                 leaf control-connection-closed {
                   description "Control connection closed";
                   type empty;
                 }
               }
               list test-session {
                 key name;
                 ordered-by user;
                 description "Test session details";
                 leaf name {
                   description "Test session name";
                   type string {
                     length "1 .. 32";
                   }
                 }
                 uses apply-advanced;
                 leaf source-address {
                   description "Source address of TWAMP Probes";
                   type jt:ipaddr;
                 }
                 container target-address {
                   presence "enable target-address";
                   description "Destination IPv4 or IPv6 address of TWAMP responder";
                   leaf address {
                     description "Address of TWAMP session reflector";
                     type jt:ipaddr;
                     mandatory true;
                   }
                   leaf local-link {
                     description "Link scope for IPv6 link-local address";
                     type union {
                       type jt:interface-name;
                       type string {
                         pattern "<.*>|$.*";
                       }
                     }
                   }
                 }
                 leaf destination-port {
                   description "Target port number for test";
                   default "862";
                   type union {
                     type string {
                       pattern "<.*>|$.*";
                     }
                     type uint16 {
                       range "862 .. 65535";
                     }
                   }
                 }
                 leaf data-fill-with-zeros {
                   description "Fill contents of test packet with zeros";
                   type empty;
                 }
                 leaf data-size {
                   description "Size of the data portion of the probes";
                   default "60";
                   type union {
                     type string {
                       pattern "<.*>|$.*";
                     }
                     type uint16 {
                       range "60 .. 1400";
                     }
                   }
                 }
                 leaf dscp-code-points {
                   description "Differentiated Services code point bits or alias used for TCP control and UDP TWAMP test packets";
                   default "000000";
                   type string {
                   }
                 }
                 leaf ttl {
                   description "Time to Live (hop-limit) value for an RPM IPv4(IPv6) packet";
                   default "64";
                   type union {
                     type string {
                       pattern "<.*>|$.*";
                     }
                     type uint32 {
                       range "1 .. 254";
                     }
                   }
                 }
                 leaf probe-count {
                   description "Total number of probes per test";
                   default "1";
                   type union {
                     type string {
                       pattern "<.*>|$.*";
                     }
                     type uint32 {
                       range "1 .. 4294967290";
                     }
                   }
                 }
                 leaf probe-interval {
                   description "Delay between two consecutive probes";
                   default "1";
                   units "seconds";
                   type union {
                     type string {
                       pattern "<.*>|$.*";
                     }
                     type uint32 {
                       range "1 .. 255";
                     }
                   }
                 }
                 container thresholds {
                   presence "enable thresholds";
                   description "TWAMP test threshold values. Set 0 to disable respective threshold";
                   uses apply-advanced;
                   leaf successive-loss {
                     description "Successive probe loss count indicating probe failure";
                     default "1";
                     type union {
                       type string {
                         pattern "<.*>|$.*";
                       }
                       type uint32 {
                         range "0 .. 15";
                       }
                     }
                   }
                   leaf total-loss {
                     description "Total probe loss count indicating test failure";
                     default "1";
                     type union {
                       type string {
                         pattern "<.*>|$.*";
                       }
                       type uint32 {
                         range "0 .. 4294967290";
                       }
                     }
                   }
                   leaf rtt {
                     description "Maximum round trip time per probe";
                     default "0";
                     units "microseconds";
                     type union {
                       type string {
                         pattern "<.*>|$.*";
                       }
                       type uint32 {
                         range "0 .. 60000000";
                       }
                     }
                   }
                   leaf max-rtt {
                     description "Maximum round trip time per test";
                     status deprecated;
                     default "0";
                     units "microseconds";
                     type union {
                       type string {
                         pattern "<.*>|$.*";
                       }
                       type uint32 {
                         range "0 .. 60000000";
                       }
                     }
                   }
                   leaf jitter-rtt {
                     description "Maximum jitter per test";
                     default "0";
                     units "microseconds";
                     type union {
                       type string {
                         pattern "<.*>|$.*";
                       }
                       type uint32 {
                         range "0 .. 60000000";
                       }
                     }
                   }
                   leaf std-dev-rtt {
                     description "Maximum standard deviation per test";
                     default "0";
                     units "microseconds";
                     type union {
                       type string {
                         pattern "<.*>|$.*";
                       }
                       type uint32 {
                         range "0 .. 60000000";
                       }
                     }
                   }
                   leaf egress-time {
                     description "Maximum source to destination time per probe";
                     default "0";
                     units "microseconds";
                     type union {
                       type string {
                         pattern "<.*>|$.*";
                       }
                       type uint32 {
                         range "0 .. 60000000";
                       }
                     }
                   }
                   leaf ingress-time {
                     description "Maximum destination to source time per probe";
                     default "0";
                     units "microseconds";
                     type union {
                       type string {
                         pattern "<.*>|$.*";
                       }
                       type uint32 {
                         range "0 .. 60000000";
                       }
                     }
                   }
                   leaf jitter-ingress {
                     description "Maximum destination to source jitter per test";
                     default "0";
                     units "microseconds";
                     type union {
                       type string {
                         pattern "<.*>|$.*";
                       }
                       type uint32 {
                         range "0 .. 60000000";
                       }
                     }
                   }
                   leaf jitter-egress {
                     description "Maximum source to destination jitter per test";
                     default "0";
                     units "microseconds";
                     type union {
                       type string {
                         pattern "<.*>|$.*";
                       }
                       type uint32 {
                         range "0 .. 60000000";
                       }
                     }
                   }
                   leaf std-dev-ingress {
                     description "Maximum destination to source standard deviation per test";
                     default "0";
                     units "microseconds";
                     type union {
                       type string {
                         pattern "<.*>|$.*";
                       }
                       type uint32 {
                         range "0 .. 60000000";
                       }
                     }
                   }
                   leaf std-dev-egress {
                     description "Maximum source to destination standard deviation per test";
                     default "0";
                     units "microseconds";
                     type union {
                       type string {
                         pattern "<.*>|$.*";
                       }
                       type uint32 {
                         range "0 .. 60000000";
                       }
                     }
                   }
                 }
                 container traps {
                   description "Trap to send if threshold is met or exceeded";
                   uses apply-advanced;
                   leaf probe-failure {
                     description "Successive probe loss threshold reached";
                     type empty;
                   }
                   leaf test-failure {
                     description "Total probe loss threshold reached";
                     type empty;
                   }
                   leaf test-completion {
                     description "Test completed";
                     type empty;
                   }
                   leaf rtt-exceeded {
                     description "Exceeded maximum round trip time threshold";
                     type empty;
                   }
                   leaf max-rtt-exceeded {
                     description "Exceeded maximum round trip time threshold at the end of per test";
                     type empty;
                   }
                   leaf std-dev-exceeded {
                     description "Exceeded round trip time standard deviation threshold";
                     type empty;
                   }
                   leaf jitter-exceeded {
                     description "Exceeded jitter in round trip time threshold";
                     type empty;
                   }
                   leaf ingress-time-exceeded {
                     description "Exceeded maximum ingress time threshold";
                     type empty;
                   }
                   leaf ingress-std-dev-exceeded {
                     description "Exceeded ingress time standard deviation threshold";
                     type empty;
                   }
                   leaf ingress-jitter-exceeded {
                     description "Exceeded jitter in ingress time threshold";
                     type empty;
                   }
                   leaf egress-time-exceeded {
                     description "Exceeded maximum egress time threshold";
                     type empty;
                   }
                   leaf egress-std-dev-exceeded {
                     description "Exceeded egress time standard deviation threshold";
                     type empty;
                   }
                   leaf egress-jitter-exceeded {
                     description "Exceeded jitter in egress time threshold";
                     type empty;
                   }
                 }
               }
             }
           }
           container server {
             description "TWAMP server configuration";
             uses apply-advanced;
             leaf tcp-keepidle {
               description "Time to start TCP KEEPALIVEs on control connection (default 120)";
               default "120";
               units "seconds";
               type union {
                 type string {
                   pattern "<.*>|$.*";
                 }
                 type uint32 {
                   range "1 .. 600";
                 }
               }
             }
             leaf tcp-keepintvl {
               description "Delay between succesive TCP KEEPALIVEs (default 5)";
               default "5";
               units "seconds";
               type union {
                 type string {
                   pattern "<.*>|$.*";
                 }
                 type uint32 {
                   range "1 .. 600";
                 }
               }
             }
             leaf tcp-keepcnt {
               description "Number of TCP KEEPALIVEs sent (default 6)";
               default "6";
               type union {
                 type string {
                   pattern "<.*>|$.*";
                 }
                 type uint32 {
                   range "1 .. 50";
                 }
               }
             }
             list routing-instance-list {
               key name;
               ordered-by user;
               description "List of allowed routing instances,not more than 100, along with ports";
               leaf name {
                 description "Name of the routing instance";
                 type string {
                 }
               }
               uses apply-advanced;
               leaf port {
                 description "Port to be used by the routing instance";
                 type union {
                   type string {
                     pattern "<.*>|$.*";
                   }
                   type uint32 {
                     range "1 .. 65535";
                   }
                 }
                 mandatory true;
               }
             }
             container authentication-mode {
               description "Authentication modes";
               uses apply-advanced;
               leaf none {
                 description "No authentication or encryption";
                 type empty;
               }
               container authenticated {
                 presence "enable authenticated";
                 description "Authenticated mode";
                 leaf control-only {
                   description "Authentication mode only for TWAMP control protocol";
                   status deprecated;
                   type empty;
                 }
               }
               container encrypted {
                 presence "enable encrypted";
                 description "Encrypted mode";
                 leaf control-only {
                   description "Encryption mode only for TWAMP control protocol";
                   status deprecated;
                   type empty;
                 }
               }
               leaf control-only-encrypted {
                 description "Encrypted control and unauthenticated data mode";
                 type empty;
               }
             }
             list authentication-key-chain {
               key name;
               ordered-by user;
               description "Authentication key chain configuration";
               uses twamp-authentication-key-chain;
             }
             leaf server-inactivity-timeout {
               description "Control packet idle timeout value in minutes, 0 to disable";
               default "15";
               units "minutes";
               type union {
                 type string {
                   pattern "<.*>|$.*";
                 }
                 type uint32 {
                   range "0 .. 30";
                 }
               }
             }
             leaf max-connection-duration {
               description "Maximum Connection duration in hours, 0 to disable";
               default "0";
               units "hours";
               type union {
                 type string {
                   pattern "<.*>|$.*";
                 }
                 type uint32 {
                   range "0 .. 120";
                 }
               }
             }
             leaf maximum-sessions {
               description "Maximum number of test sessions for the server";
               default "64";
               type union {
                 type string {
                   pattern "<.*>|$.*";
                 }
                 type uint32 {
                   range "1 .. 2048";
                 }
               }
             }
             leaf maximum-sessions-per-connection {
               description "Maximum number of test sessions per client connection";
               type union {
                 type string {
                   pattern "<.*>|$.*";
                 }
                 type uint32 {
                   range "1 .. 1024";
                 }
               }
             }
             leaf maximum-connections {
               description "Maximum number of connections for the server";
               default "64";
               type union {
                 type string {
                   pattern "<.*>|$.*";
                 }
                 type uint32 {
                   range "1 .. 1000";
                 }
               }
             }
             leaf maximum-connections-per-client {
               description "Maximum number of server connections per client";
               type union {
                 type string {
                   pattern "<.*>|$.*";
                 }
                 type uint32 {
                   range "1 .. 500";
                 }
               }
             }
             leaf port {
               description "TWAMP server listening port";
               default "862";
               type union {
                 type string {
                   pattern "<.*>|$.*";
                 }
                 type uint32 {
                   range "1 .. 65535";
                 }
               }
             }
             list client-list {
               key name;
               ordered-by user;
               description "List of allowed clients";
               leaf name {
                 description "Name of client list";
                 type string {
                   length "1 .. 127";
                 }
               }
               uses apply-advanced;
               list address {
                 key name;
                 ordered-by user;
                 description "IPv4 prefix of TWAMP client";
                 leaf name {
                   description "IPv4 prefix of TWAMP client";
                   type jt:ipv4prefix;
                 }
                 uses apply-advanced;
               }
             }
             container light {
               presence "enable light";
               description "Enable TWAMP server for light control on the default port";
               uses apply-advanced;
               leaf-list port {
                 ordered-by user;
                 description "UDP ports reflecting TWAMP light test packets";
                 type union {
                   type uint16;
                   type string {
                     pattern "<.*>|$.*";
                   }
                 }
                 max-elements 1000;
               }
             }
           }
         }
       }
       container analytics {
         presence "enable analytics";
         description "Traffic analytics configuration options";
         uses apply-advanced;
         container zero-suppression {
           description "Configure suppression of zeros for GRPC sensors";
           uses apply-advanced;
           leaf no-zero-suppression {
             description "Disable zero suppression";
             type empty;
             mandatory true;
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:host;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipaddr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-gnmi" {
                 description "Use gnmi format for gpb messages";
               }
               enum "json-gnmi" {
                 description "Use gnmi format for json messages";
               }
             }
           }
           leaf transport {
             description "Telemetry export transport protocol";
             type enumeration {
               enum "udp" {
                 description "Use UDP transport protocol";
               }
               enum "grpc" {
                 description "Use grpc transport";
               }
             }
           }
           leaf routing-instance {
             description "Routing instance to be used for grpc transport";
             type string;
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 1024";
             }
             mandatory true;
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
             max-elements 30;
           }
           leaf target-defined {
             description "Allow target to decide periodic, on-change or mix";
             type empty;
           }
           leaf life-time {
             description "Denotes sensor life-time";
             type enumeration {
               enum "long-lived" {
                 description "A long-lived subscription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                         enum "interface-queue-statistics" {
                           description "Interface Queue statistics";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "0 .. 86400";
                       }
                     }
                   }
                   leaf sensors {
                     description "Space separated list of sensor paths";
                     type string {
                       length "1 .. 2048";
                     }
                     mandatory true;
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
         container traceoptions {
           description "Traffic analytics trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
               mandatory true;
             }
             leaf low {
               description "Low queue depth threshold";
               units "bytes";
               type union {
                 type string {
                   pattern "<.*>|$.*";
                 }
                 type uint32 {
                   range "1 .. 1250000000";
                 }
               }
               mandatory true;
             }
           }
           container latency-threshold {
             description "Latency threshold configuration";
             leaf high {
               description "High latency threshold";
               units "nanoseconds";
               type union {
                 type string {
                   pattern "<.*>|$.*";
                 }
                 type uint32 {
                   range "1 .. 100000000";
                 }
               }
               mandatory true;
             }
             leaf low {
               description "Low latency threshold";
               units "nanoseconds";
               type union {
                 type string {
                   pattern "<.*>|$.*";
                 }
                 type uint32 {
                   range "1 .. 100000000";
                 }
               }
               mandatory true;
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
       }
     }
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           leaf key-generation-self-test {
             description "Raise alarm for key generation self test failures";
             type empty;
           }
           leaf non-cryptographic-self-test {
             description "Raise alarm for non-cryptographic self test failures";
             type empty;
           }
           container policy {
             description "Raise alarm for flow policy violations";
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
         }
       }
       container log {
         description "Configure auditable security logs";
         uses log-object;
       }
       container traceoptions {
         description "Trace options for IPSec key management";
         uses security-traceoptions;
       }
       container ipsec {
         description "IPSec configuration";
         uses security-ipsec-vpn;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
     }
     container interfaces {
       description "Interface configuration";
       uses apply-advanced;
       container traceoptions {
         description "Interface trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "all" {
                 description "Enable all configuration logging";
               }
               enum "kernel" {
                 description "Log configuration IPC messages to kernel";
               }
               enum "error" {
                 description "Log error events";
               }
               enum "warning" {
                 description "Log warning events";
               }
               enum "notice" {
                 description "Log notification events";
               }
               enum "info" {
                 description "Log informations";
               }
               enum "debugging" {
                 description "Log debug events";
               }
             }
           }
         }
       }
       list interface {
         key name;
         uses interfaces_type;
       }
     }
     container forwarding-options {
       description "Configure options to control packet forwarding";
       uses juniper-forwarding-options;
     }
     container event-options {
       description "Event processing configuration";
       uses apply-advanced;
       leaf max-policies {
         description "Number of policies that can be executed simultaneously";
         default "15";
         type union {
           type string {
             pattern "<.*>|$.*";
           }
           type uint32 {
             range "0 .. 20";
           }
         }
       }
       list generate-event {
         key name;
         ordered-by user;
         description "Generate an internal event";
         max-elements 10;
         leaf name {
           description "Name of the event to be generated";
           type string {
             length "1 .. 63";
           }
         }
         choice time_choice {
           case case_1 {
             leaf time-of-day {
               description "Time of day at which to generate event (hh:mm:ss)";
               type jt:time-of-day;
             }
           }
           case case_2 {
             leaf time-interval {
               description "Frequency for generating the event";
               units "seconds";
               type union {
                 type string {
                   pattern "<.*>|$.*";
                 }
                 type uint32 {
                   range "60 .. 2592000";
                 }
               }
             }
           }
         }
         leaf start-time {
           description "Start-time to generate event (yyyy-mm-dd.hh:mm)";
           type jt:time;
         }
         leaf no-drift {
           description "Avoid event generation delay propagating to next event";
           type empty;
         }
       }
       list policy {
         key name;
         ordered-by user;
         description "Event policy for event policy manager";
         leaf name {
           description "Name of policy";
           type string {
             length "1 .. 63";
           }
         }
         uses apply-advanced;
         leaf-list events {
           ordered-by user;
           description "List of events that trigger this policy";
           type string;
         }
         list within {
           key name;
           ordered-by user;
           description "List of events correlated with trigering events";
           leaf name {
             description "Time within which correlated events must occur (or not)";
             units "seconds";
             type union {
               type string {
                 pattern "<.*>|$.*";
               }
               type uint32 {
                 range "1 .. 604800";
               }
             }
           }
           uses apply-advanced;
           container trigger {
             description "Correlate events based on the number of occurrences";
             choice when {
               case case_1 {
                 leaf until {
                   description "Trigger when occurrences of triggering event < 'count'";
                   type empty;
                 }
               }
               case case_2 {
                 leaf on {
                   description "Trigger when occurrences of triggering event = 'count'";
                   type empty;
                 }
               }
               case case_3 {
                 leaf after {
                   description "Trigger when occurrences of triggering event > 'count'";
                   type empty;
                 }
               }
             }
             leaf count {
               description "Number of occurrences of triggering event";
               type union {
                 type uint32;
                 type string {
                   pattern "<.*>|$.*";
                 }
               }
               mandatory true;
             }
           }
           leaf-list events {
             ordered-by user;
             description "List of events that must occur within time interval";
             type string;
           }
           container not {
             description "Events must not occur within time interval";
             leaf-list events {
               ordered-by user;
               description "List of events that must not occur within time interval";
               type string;
             }
           }
         }
         list attributes-match {
           key "from-event-attribute condition to-event-attribute-value";
           ordered-by user;
           description "List of attributes to compare for two events";
           leaf from-event-attribute {
             description "First attribute to compare";
             type string {
             }
           }
           leaf condition {
             description "Relationship that must hold between attributes";
             type enumeration {
               enum "equals" {
                 description "Attributes match";
               }
               enum "starts-with" {
                 description "Second attribute starts with first attribute value";
               }
               enum "matches" {
                 description "Regular expression matching the first attribute value";
               }
             }
           }
           leaf to-event-attribute-value {
             description "Second attribute or value to compare";
             type string;
           }
         }
         container then {
           description "List of actions to perform when policy matches";
           uses apply-advanced;
           leaf ignore {
             description "Do not log event or perform any other action";
             type empty;
           }
           list upload {
             key "filename destination";
             ordered-by user;
             description "Upload file to specified destination";
             leaf filename {
               description "Name of file to upload";
               type string;
             }
             leaf destination {
               description "Location to which to output file";
               type string;
             }
             uses apply-advanced;
             leaf user-name {
               description "User under whose privileges upload action will execute";
               type string;
             }
             leaf transfer-delay {
               description "Delay before uploading file to the destination";
               units "seconds";
               type union {
                 type uint32;
                 type string {
                   pattern "<.*>|$.*";
                 }
               }
             }
             container retry-count {
               description "Upload output-filename retry attempt count";
               leaf retry {
                 description "Number of retry attempts";
                 type union {
                   type string {
                     pattern "<.*>|$.*";
                   }
                   type uint8 {
                     range "0 .. 10";
                   }
                 }
                 mandatory true;
               }
               leaf retry-interval {
                 description "Time interval between each retry";
                 units "seconds";
                 type union {
                   type uint32;
                   type string {
                     pattern "<.*>|$.*";
                   }
                 }
                 mandatory true;
               }
             }
           }
           container change-configuration {
             description "Change configuration";
             uses apply-advanced;
             container retry {
               description "Change configuration retry attempt count";
               leaf count {
                 description "Number of retry attempts";
                 type union {
                   type string {
                     pattern "<.*>|$.*";
                   }
                   type uint8 {
                     range "0 .. 10";
                   }
                 }
                 mandatory true;
               }
               leaf interval {
                 description "Time interval between each retry";
                 units "seconds";
                 type union {
                   type uint32;
                   type string {
                     pattern "<.*>|$.*";
                   }
                 }
                 mandatory true;
               }
             }
             list commands {
               key name;
               ordered-by user;
               description "List of configuration commands";
               leaf name {
                 description "Configuration command to issue";
                 type string;
               }
               uses apply-advanced;
             }
             leaf user-name {
               description "User under whose privileges configuration should be changed";
               type string;
             }
             container commit-options {
               description "List of commit options";
               uses apply-advanced;
               container check {
                 presence "enable check";
                 description "Check correctness of syntax; do not apply changes";
                 uses apply-advanced;
                 leaf synchronize {
                   description "Synchronize commit on both Routing Engines";
                   type empty;
                 }
               }
               leaf synchronize {
                 description "Synchronize commit on both Routing Engines";
                 type empty;
               }
               leaf force {
                 description "Force commit on other Routing Engine (ignore warnings)";
                 type empty;
               }
               leaf log {
                 description "Message to write to commit log";
                 type string {
                   length "1 .. 512";
                 }
               }
             }
           }
           container execute-commands {
             description "Issue one or more CLI commands";
             uses apply-advanced;
             list commands {
               key name;
               ordered-by user;
               description "List of CLI commands to issue";
               leaf name {
                 description "CLI command to issue";
                 type string;
               }
               uses apply-advanced;
             }
             leaf user-name {
               description "User under whose privileges command will execute";
               type string;
             }
             leaf output-filename {
               description "Name of file in which to write command output";
               type string {
               }
             }
             list destination {
               key name;
               ordered-by user;
               description "Location to which to upload command output";
               max-elements 1;
               leaf name {
                 description "Location to which to upload command output";
                 type string;
               }
               uses apply-advanced;
               leaf transfer-delay {
                 description "Delay before uploading file to the destination";
                 units "seconds";
                 type union {
                   type uint32;
                   type string {
                     pattern "<.*>|$.*";
                   }
                 }
               }
               container retry-count {
                 description "Upload output-filename retry attempt count";
                 leaf retry {
                   description "Number of retry attempts";
                   type union {
                     type string {
                       pattern "<.*>|$.*";
                     }
                     type uint8 {
                       range "0 .. 10";
                     }
                   }
                   mandatory true;
                 }
                 leaf retry-interval {
                   description "Time interval between each retry";
                   units "seconds";
                   type union {
                     type uint32;
                     type string {
                       pattern "<.*>|$.*";
                     }
                   }
                   mandatory true;
                 }
               }
             }
             leaf output-format {
               description "Format of output from CLI commands";
               default "xml";
               type enumeration {
                 enum "text" {
                   description "Formatted ASCII text";
                 }
                 enum "xml" {
                   description "JUNOS XML tags";
                 }
               }
             }
           }
           list event-script {
             key name;
             ordered-by user;
             description "Invoke event scripts";
             leaf name {
               description "Local filename of the script file";
               type string {
                 length "1 .. 254";
               }
             }
             uses apply-advanced;
             list arguments {
               key name;
               ordered-by user;
               description "Command line argument to the script";
               leaf name {
                 description "Name of the argument";
                 type string {
                   length "1 .. 254";
                 }
               }
               leaf value {
                 description "Value of the argument";
                 type string;
                 mandatory true;
               }
             }
             leaf user-name {
               description "User under whose privileges event script will execute";
               type string;
             }
             leaf output-filename {
               description "Name of file in which to write event script output";
               type string {
               }
             }
             list destination {
               key name;
               ordered-by user;
               description "Location to which to upload event script output";
               max-elements 1;
               leaf name {
                 description "Location to which to upload event script output";
                 type string;
               }
               uses apply-advanced;
               leaf transfer-delay {
                 description "Delay before uploading files";
                 units "seconds";
                 type union {
                   type uint32;
                   type string {
                     pattern "<.*>|$.*";
                   }
                 }
               }
               container retry-count {
                 description "Upload output-filename retry attempt count";
                 leaf retry {
                   description "Number of retry attempts";
                   type union {
                     type string {
                       pattern "<.*>|$.*";
                     }
                     type uint8 {
                       range "0 .. 10";
                     }
                   }
                   mandatory true;
                 }
                 leaf retry-interval {
                   description "Time interval between each retry";
                   units "seconds";
                   type union {
                     type uint32;
                     type string {
                       pattern "<.*>|$.*";
                     }
                   }
                   mandatory true;
                 }
               }
             }
             leaf output-format {
               description "Format of output from event-script";
               type enumeration {
                 enum "text" {
                   description "Formatted ASCII text";
                 }
                 enum "xml" {
                   description "JUNOS XML tags";
                 }
               }
             }
           }
         }
       }
       container event-script {
         description "Configure event-scripts";
         uses apply-advanced;
         leaf optional {
           description "Allow commit to succeed if the script is missing";
           type empty;
         }
         leaf max-datasize {
           description "Maximum data segment size for scripts execution";
           units "bytes";
           type string;
         }
         container dampen {
           presence "enable dampen";
           description "Run event scripts in dampen mode";
           uses apply-advanced;
           container dampen-options {
             description "Dampen options for event scripts";
             uses apply-advanced;
             leaf cpu-factor {
               description "CPU factor at which to pause";
               type union {
                 type string {
                   pattern "<.*>|$.*";
                 }
                 type uint32 {
                   range "1 .. 100";
                 }
               }
             }
             leaf line-interval {
               description "Line interval at which to pause";
               type union {
                 type string {
                   pattern "<.*>|$.*";
                 }
                 type uint32 {
                   range "1 .. 4294967295";
                 }
               }
             }
             leaf time-interval {
               description "Time to pause";
               units "microseconds";
               type union {
                 type string {
                   pattern "<.*>|$.*";
                 }
                 type uint32 {
                   range "1 .. 4294967295";
                 }
               }
             }
           }
         }
         container start {
           description "Start event scripts with start-criteria check";
           uses apply-advanced;
           container start-options {
             description "Start options for event scripts";
             uses apply-advanced;
             leaf mem-factor {
               description "Memory factor at which to start/stop";
               type union {
                 type string {
                   pattern "<.*>|$.*";
                 }
                 type uint32 {
                   range "1 .. 100";
                 }
               }
             }
           }
         }
         container traceoptions {
           description "Trace options for event scripts";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
           }
           list flag {
             key name;
             description "Tracing parameters";
             leaf name {
               type enumeration {
                 enum "events" {
                   description "Trace important events";
                 }
                 enum "input" {
                   description "Trace script input data";
                 }
                 enum "offline" {
                   description "Generate data for offline development";
                 }
                 enum "output" {
                   description "Trace script output data";
                 }
                 enum "rpc" {
                   description "Trace script RPCs";
                 }
                 enum "xslt" {
                   description "Trace the XSLT library";
                 }
                 enum "all" {
                   description "Trace all operations";
                 }
               }
             }
           }
         }
         list file {
           key name;
           ordered-by user;
           description "File name for event script";
           leaf name {
             description "Local filename of the script file";
             type string {
               length "1 .. 254";
             }
           }
           uses apply-advanced;
           leaf source {
             description "URL of source for this script";
             type string {
               length "1 .. 254";
             }
           }
           leaf cert-file {
             description "Specify the certificate file name";
             type string;
           }
           leaf python-script-user {
             description "Run the python event script with privileges of user";
             type string;
           }
           container dampen {
             presence "enable dampen";
             description "Run script in dampen mode";
             uses apply-advanced;
             container dampen-options {
               description "Dampen options for the script";
               uses apply-advanced;
               leaf cpu-factor {
                 description "CPU factor at which to pause";
                 type union {
                   type string {
                     pattern "<.*>|$.*";
                   }
                   type uint32 {
                     range "1 .. 100";
                   }
                 }
               }
               leaf line-interval {
                 description "Line interval at which to pause";
                 type union {
                   type string {
                     pattern "<.*>|$.*";
                   }
                   type uint32 {
                     range "1 .. 4294967295";
                   }
                 }
               }
               leaf time-interval {
                 description "Time to pause";
                 units "microseconds";
                 type union {
                   type string {
                     pattern "<.*>|$.*";
                   }
                   type uint32 {
                     range "1 .. 4294967295";
                   }
                 }
               }
             }
           }
           container start {
             description "Start script with start-criteria check";
             uses apply-advanced;
             container start-options {
               description "Start options for the event script";
               uses apply-advanced;
               leaf mem-factor {
                 description "Memory factor at which to start/stop";
                 type union {
                   type string {
                     pattern "<.*>|$.*";
                   }
                   type uint32 {
                     range "1 .. 100";
                   }
                 }
               }
             }
           }
           leaf routing-instance {
             description "Routing instance";
             type string {
             }
           }
           leaf refresh {
             description "Refresh all operation scripts from their source";
             type empty;
           }
           leaf refresh-from {
             description "Refresh all operation scripts from a given base URL";
             type string {
               length "1 .. 254";
             }
           }
           container checksum {
             description "Checksum of this script";
             uses apply-advanced;
             leaf sha-256 {
               description "SHA-256 checksum of this script";
               type string {
                 length "1 .. 254";
               }
             }
           }
           list remote-execution {
             key name;
             ordered-by user;
             description "Remote login username and password details for script";
             leaf name {
               description "Remote hostname";
               type string {
                 length "1 .. 255";
               }
             }
             uses apply-advanced;
             leaf username {
               description "SSH username for login into the remote host";
               type string {
               }
               mandatory true;
             }
             leaf passphrase {
               description "SSH passphrase for login into the remote host";
               type jt:unreadable;
               mandatory true;
             }
           }
         }
         leaf refresh {
           description "Refresh all operation scripts from their source";
           type empty;
         }
         leaf refresh-from {
           description "Refresh all operation scripts from a given base URL";
           type string {
             length "1 .. 254";
           }
         }
       }
       list destinations {
         key name;
         ordered-by user;
         description "List of destinations referred to in 'then' clause";
         leaf name {
           description "Destination name";
           type string;
         }
         uses apply-advanced;
         leaf transfer-delay {
           description "Delay before transferring files";
           default "0";
           units "seconds";
           type union {
             type uint32;
             type string {
               pattern "<.*>|$.*";
             }
           }
         }
         list archive-sites {
           key name;
           ordered-by user;
           description "List of archive destinations";
           leaf name {
             description "URL of destination for file";
             type string;
           }
           leaf password {
             description "Password for login into the archive site";
             type jt:unreadable;
           }
         }
       }
       container traceoptions {
         description "Trace options for the event processing daemon";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "List of event types to include in trace";
           leaf name {
             type enumeration {
               enum "server" {
                 description "Communication with processes that are generating events";
               }
               enum "configuration" {
                 description "Reading of configuration";
               }
               enum "events" {
                 description "Event processing";
               }
               enum "timer-events" {
                 description "Internally generated events";
               }
               enum "database" {
                 description "Events involving storage and retrieval in events database";
               }
               enum "policy" {
                 description "Policy processing";
               }
               enum "registration" {
                 description "Event registration";
               }
               enum "syslogd" {
                 description "Syslog related traces";
               }
               enum "all" {
                 description "Everything";
               }
             }
           }
         }
       }
     }
     container policy-options {
       description "Policy option configuration";
       uses juniper-policy-options;
     }
     container class-of-service {
       description "Class-of-service configuration";
       uses juniper-class-of-service-options;
     }
     container firewall {
       description "Define a Firewall configuration";
       uses juniper-firewall-options;
     }
     container routing-instances {
       description "Routing instance configuration";
       uses apply-advanced;
       list instance {
         key name;
         uses juniper-routing-instance;
       }
     }
     container routing-options {
       description "Protocol-independent routing option configuration";
       uses juniper-routing-options;
     }
     container protocols {
       description "Routing protocol configuration";
       uses juniper-protocols;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping certificate-object {
     leaf name {
       description "Simple name to identify this certificate";
       type string;
     }
     uses apply-advanced;
     leaf certificate {
       description "Certificate and private key string";
       type string;
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping interfaces_type {
     description "Physical interface";
     leaf name {
       type string;
     }
     uses apply-advanced;
     leaf description {
       description "Text description of interface";
       type string;
     }
     leaf mtu {
       description "Maximum transmit packet size";
       type union {
         type string {
           pattern "<.*>|$.*";
         }
         type uint32 {
           range "1 .. 16000";
         }
       }
     }
     leaf mac {
       description "Hardware MAC address";
       type jt:mac-unicast;
     }
     leaf native-vlan-id {
       description "Virtual LAN identifier for untagged frames";
       type union {
         type string {
           pattern "<.*>|$.*";
         }
         type uint32 {
           range "0 .. 4094";
         }
       }
     }
     list unit {
       key name;
       description "Logical interface";
       leaf name {
         type string;
       }
       uses apply-advanced;
       leaf alias {
         description "Interface alias";
         type string;
       }
       leaf description {
         description "Text description of interface";
         type string;
       }
       leaf-list security-group {
         ordered-by user;
         description "Security-group for the interface";
         type string;
       }
       choice vlan_choice {
         case case_1 {
           leaf vlan-id {
             description "Virtual LAN identifier value for 802.1q VLAN tags";
             type string;
           }
         }
       }
       leaf encapsulation {
         description "Logical link-layer encapsulation";
         type enumeration {
           enum "ethernet-ccc" {
             description "Ethernet for a cross-connect";
           }
           enum "ethernet-bridge" {
             description "Ethernet II bridging";
           }
           enum "vlan-ccc" {
             description "802.1q tagging for a cross-connect";
           }
           enum "vlan-bridge" {
             description "VLAN layer-2 bridging";
           }
         }
       }
       container family {
         description "Protocol family";
         container inet {
           presence "enable inet";
           description "IPv4 parameters";
           uses apply-advanced;
           container filter {
             description "Packet filtering";
             uses apply-advanced;
             container input {
               description "Filter to be applied to received packets";
               leaf filter-name {
                 description "Name of the filter";
                 type string;
                 //mandatory true;
               }
             }
           }
           list address {
             key name;
             ordered-by user;
             description "Interface address/destination prefix";
             leaf name {
               description "Interface address/destination prefix";
               type jt:ipv4prefix;
             }
             uses apply-advanced;
             list vrrp-group {
               key name;
               ordered-by user;
               description "VRRP group";
               uses vrrp-group;
             }
           }
         }
         container inet6 {
           presence "enable inet6";
           description "IPv6 protocol parameters";
           uses apply-advanced;
           container filter {
             description "Packet filtering";
             uses apply-advanced;
             container input {
               description "Filter to be applied to received packets";
               leaf filter-name {
                 description "Name of the filter";
                 type string;
                 //mandatory true;
               }
             }
           }
           list address {
             key name;
             ordered-by user;
             description "Interface address or destination prefix";
             leaf name {
               description "Interface address or destination prefix";
               type jt:ipv6prefix;
             }
             uses apply-advanced;
             list vrrp-inet6-group {
               key name;
               ordered-by user;
               description "VRRP group";
               uses vrrp-inet6-group;
             }
           }
         }
         container iso {
           presence "enable iso";
           description "OSI ISO protocol parameters";
           uses apply-advanced;
           list address {
             key name;
             ordered-by user;
             description "Interface address";
             leaf name {
               description "Interface address";
               type jt:isoaddr;
             }
             uses apply-advanced;
           }
         }
         container mpls {
           presence "enable mpls";
           uses apply-advanced;
           container filter {
             description "Packet filtering";
             uses apply-advanced;
             container input {
               description "Filter to be applied to received packets";
               leaf filter-name {
                 description "Name of the filter";
                 type string;
                 //mandatory true;
               }
             }
           }
         }
         container bridge {
           presence "enable bridge";
           description "Layer-2 bridging parameters";
           uses apply-advanced;
           leaf interface-mode {
             description "Interface mode (access or trunk)";
             type enumeration {
               enum "access" {
                 description "Interface mode is access";
               }
               enum "trunk" {
                 description "Interface mode is trunk";
               }
             }
           }
           choice vlan_list {
             case case_1 {
               leaf vlan-id {
                 description "Access mode and trunk mode VLAN membership";
                 type union {
                   type string {
                     pattern "<.*>|$.*";
                   }
                   type uint32 {
                     range "0 .. 4094";
                   }
                 }
               }
             }
             case case_2 {
               leaf-list vlan-id-list {
                 description "Trunk mode VLAN membership for this interface";
                 type jt:vlan-range;
               }
             }
           }
           choice bridge_intf_type {
             case case_1 {
               leaf ce-facing {
                 description "Interface is ce facing";
                 type empty;
               }
             }
             case case_2 {
               leaf core-facing {
                 description "Interface is core facing";
                 type empty;
               }
             }
           }
         }
       }
       leaf mtu {
         description "Maximum transmission unit packet size";
         type union {
           type string {
             pattern "<.*>|$.*";
           }
           type uint32 {
             range "1 .. 16000";
           }
         }
       }
       leaf mac {
         description "Configure logical interface MAC address";
         type jt:mac-unicast;
       }
     }
   }
   grouping juniper-class-of-service-options {
     uses apply-advanced;
     container classifiers {
       description "Classify incoming packets based on code point value";
       uses apply-advanced;
       list dscp {
         key name;
         ordered-by user;
         description "Differentiated Services code point classifier";
         max-elements 16;
         leaf name {
           description "Classifier name";
           type string {
             length "1 .. 64";
           }
         }
         uses apply-advanced;
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "medium-low" {
                   description "Code points to classify to loss priority medium-low";
                 }
                 enum "medium-high" {
                   description "Code points to classify to loss priority medium-high";
                 }
                 enum "high" {
                   description "Code points to classify to loss priority high";
                 }
               }
             }
             leaf-list code-points {
               ordered-by user;
               description "List of code point aliases and/or bit strings";
               type string;
             }
           }
         }
       }
       list dscp-ipv6 {
         key name;
         ordered-by user;
         description "Differentiated Services code point classifier IPv6";
         max-elements 16;
         leaf name {
           description "Classifier name";
           type string {
             length "1 .. 64";
           }
         }
         uses apply-advanced;
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "medium-low" {
                   description "Code points to classify to loss priority medium-low";
                 }
                 enum "medium-high" {
                   description "Code points to classify to loss priority medium-high";
                 }
                 enum "high" {
                   description "Code points to classify to loss priority high";
                 }
               }
             }
             leaf-list code-points {
               ordered-by user;
               description "List of code point aliases and/or bit strings";
               type string;
             }
           }
         }
       }
     }
     container rewrite-rules {
       description "Rewrite rules applied to outgoing packets";
       uses apply-advanced;
       list dscp {
         key name;
         ordered-by user;
         description "Differentiated Services code point rewrite rule";
         max-elements 8;
         leaf name {
           description "Rewrite rule name";
           type string {
             length "1 .. 64";
           }
         }
         uses apply-advanced;
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "medium-low" {
                   description "Marking when loss priority is medium-low";
                 }
                 enum "medium-high" {
                   description "Marking when loss priority is medium-high";
                 }
                 enum "high" {
                   description "Marking when loss priority is high";
                 }
               }
             }
             leaf code-point {
               description "Code point aliases or bit string";
               type string {
               }
               mandatory true;
             }
           }
         }
       }
       list dscp-ipv6 {
         key name;
         ordered-by user;
         description "Differentiated Services code point rewrite rule IPv6";
         max-elements 8;
         leaf name {
           description "Rewrite rule name";
           type string {
             length "1 .. 64";
           }
         }
         uses apply-advanced;
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "medium-low" {
                   description "Marking when loss priority is medium-low";
                 }
                 enum "medium-high" {
                   description "Marking when loss priority is medium-high";
                 }
                 enum "high" {
                   description "Marking when loss priority is high";
                 }
               }
             }
             leaf code-point {
               description "Code point aliases or bit string";
               type string {
               }
               mandatory true;
             }
           }
         }
       }
       list exp {
         key name;
         ordered-by user;
         description "MPLS EXP rewrite rule";
         max-elements 8;
         leaf name {
           description "Rewrite rule name";
           type string {
             length "1 .. 64";
           }
         }
         uses apply-advanced;
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "medium-low" {
                   description "Marking when loss priority is medium-low";
                 }
                 enum "medium-high" {
                   description "Marking when loss priority is medium-high";
                 }
                 enum "high" {
                   description "Marking when loss priority is high";
                 }
               }
             }
             leaf code-point {
               description "Code point aliases or bit string";
               type string {
               }
               mandatory true;
             }
           }
         }
       }
     }
     list schedulers {
       key name;
       description "Packet schedulers";
       max-elements 8;
       leaf name {
         description "Scheduler name";
         type string {
           length "1 .. 64";
         }
       }
       uses apply-advanced;
       leaf priority {
         description "Scheduling priority";
         type enumeration {
           enum "low" {
             description "Scheduling priority 7 (Least)";
           }
           enum "high" {
             description "Scheduling priority 1";
           }
           enum "medium-high" {
             description "Scheduling priority 2";
           }
           enum "medium-low" {
             description "Scheduling priority 3";
           }
           enum "strict-high" {
             description "Scheduling priority 0 (Highest)";
           }
           enum "low-latency" {
             description "Scheduling priority 4";
           }
           enum "low-medium" {
             description "Scheduling priority 6";
           }
           enum "low-high" {
             description "Scheduling priority 5";
           }
         }
       }
     }
     list scheduler-maps {
       key name;
       description "Mapping of forwarding classes to packet schedulers";
       max-elements 8;
       leaf name {
         description "Scheduler map name";
         type string {
           length "1 .. 64";
         }
       }
       uses apply-advanced;
       list forwarding-class {
         key name;
         description "Forwarding class name to map to scheduler";
         leaf name {
           description "Forwarding class name";
           type string {
             length "1 .. 64";
           }
         }
         leaf scheduler {
           description "Scheduler name";
           type string {
             length "1 .. 64";
           }
           mandatory true;
         }
       }
     }
     container interfaces {
       description "Apply class-of-service options to interfaces";
       uses apply-advanced;
       list interface {
         key name;
         uses cos_interfaces_type;
       }
     }
     container forwarding-classes {
       description "One or more mappings of forwarding class to queue number";
       uses apply-advanced;
       list class {
         key name;
         description "Forwarding class to map to queue number";
         max-elements 16;
         leaf name {
           description "Name of forwarding class";
           type string {
             length "1 .. 64";
           }
         }
         uses apply-advanced;
       }
     }
   }
   grouping cos_interfaces_type {
     description "Physical interface";
     leaf name {
       description "Interface name";
       type string;
     }
     uses apply-advanced;
     leaf scheduler-map {
       description "Output scheduler map";
       type string {
         length "1 .. 64";
       }
     }
     list unit {
       key name;
       description "Logical interface unit";
       leaf name {
         description "Logical unit number";
         type string;
       }
       uses apply-advanced;
       container classifiers {
         description "Classifiers applied to incoming packets";
         uses apply-advanced;
         container dscp {
           description "Differentiated Services code point classifier";
           leaf classifier-name {
             description "Name of classifier to be applied";
             type string {
               length "1 .. 64";
             }
             mandatory true;
           }
         }
         container dscp-ipv6 {
           description "Differentiated Services code point classifier IPv6";
           leaf classifier-name {
             description "Name of classifier to be applied";
             type string {
               length "1 .. 64";
             }
             mandatory true;
           }
         }
       }
       container rewrite-rules {
         description "Rewrite rules applied to outgoing packets";
         uses apply-advanced;
         container dscp {
           description "Differentiated Services code point rewrite rule";
           leaf rewrite-rule-name {
             description "Name of rewrite rule to be applied";
             type string {
               length "1 .. 64";
             }
             mandatory true;
           }
         }
         container dscp-ipv6 {
           description "Differentiated Services code point rewrite rule IPv6";
           leaf rewrite-rule-name {
             description "Name of rewrite rule to be applied";
             type string {
               length "1 .. 64";
             }
             mandatory true;
           }
         }
         container exp {
           description "MPLS exp rewrite rule";
           leaf rewrite-rule-name {
             description "Name of rewrite rule to be applied";
             type string {
               length "1 .. 64";
             }
             mandatory true;
           }
         }
       }
     }
   }
   grouping juniper-firewall-options {
     uses apply-advanced;
     list three-color-policer {
       key name;
       description "Three-color policer";
       max-elements 16;
       uses three-color-policer-type;
     }
     container family {
       description "Protocol Family";
       container bridge {
         description "Protocol family BRIDGE for firewall filter";
         uses apply-advanced;
         list filter {
           key name;
           description "Define a BRIDGE firewall filter";
           uses bridge_filter;
         }
       }
       container inet {
         description "Protocol family IPv4 for firewall filter";
         uses apply-advanced;
         list filter {
           key name;
           description "Define an IPv4 firewall filter";
           max-elements 16;
           uses inet_filter;
         }
       }
       container inet6 {
         description "Protocol family IPv6 for firewall filter";
         uses apply-advanced;
         list filter {
           key name;
           description "Define an IPv6 firewall filter";
           max-elements 16;
           uses inet6_filter;
         }
       }
       container mpls {
         description "Protocol family MPLS for firewall filter";
         uses apply-advanced;
         list filter {
           key name;
           description "Define a MPLS firewall filter";
           max-elements 16;
           uses mpls_filter;
         }
       }
     }
   }
   grouping bridge_filter {
     description "Define a BRIDGE firewall filter";
     leaf name {
       description "Filter name";
       type string {
         length "1 .. 64";
       }
     }
     uses apply-advanced;
     list term {
       key name;
       ordered-by user;
       description "Define a firewall term";
       max-elements 16;
       leaf name {
         description "Term name";
         type string {
           length "1 .. 4";
         }
       }
       uses apply-advanced;
       container from {
         description "Define match criteria";
         uses apply-advanced;
         leaf source-mac-address {
           description "Match source mac address";
           type jt:mac-addr-prefix;
         }
         leaf destination-mac-address {
           description "Match destination mac address";
           type jt:mac-addr-prefix;
         }
         leaf-list ether-type {
           ordered-by user;
           description "Match Ethernet type";
           type string;
           max-elements 1;
         }
       }
       container then {
         description "Action to take if the 'from' condition is matched";
         uses apply-advanced;
         choice designation {
           case case_1 {
             leaf discard {
               description "Discard the packet";
               type empty;
             }
           }
         }
       }
     }
   }
   grouping inet6_filter {
     description "Define an IPv6 firewall filter";
     leaf name {
       description "Filter name";
       type string {
         length "1 .. 127";
       }
     }
     uses apply-advanced;
     list term {
       key name;
       ordered-by user;
       description "Define a firewall term";
       max-elements 16;
       leaf name {
         description "Term name";
         type string {
           length "1 .. 127";
         }
       }
       uses apply-advanced;
       container from {
         description "Define match criteria";
         uses apply-advanced;
         list source-address {
           key name;
           ordered-by user;
           description "Match IP source address";
           max-elements 1;
           uses firewall_addr6_object;
         }
         list destination-address {
           key name;
           ordered-by user;
           description "Match IP destination address";
           max-elements 1;
           uses firewall_addr6_object;
         }
         leaf-list source-port {
           ordered-by user;
           type string;
         }
         leaf-list destination-port {
           ordered-by user;
           type string;
         }
         leaf-list icmp-type {
           ordered-by user;
           type string;
         }
         leaf-list tcp-flags {
           ordered-by user;
           type string;
         }
         leaf-list traffic-class {
           ordered-by user;
           type string;
         }
         leaf-list forwarding-class {
           ordered-by user;
           description "Match packet to forwarding class";
           type string;
           max-elements 1;
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
         }
         leaf count {
           description "Count the packet in the named counter";
           type string {
             length "1 .. 127";
           }
         }
         leaf routing-instance {
           description "Name of routing instance - Packets are directed to specified routing instance";
           type string;
         }
         leaf log {
           description "Log the packet";
           type empty;
         }
         leaf syslog {
           description "System log (syslog) information about the packet";
           type empty;
         }
         choice policer-choice {
           case case_1 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf two-rate {
                     description "Name of two-rate three-color policer to use to rate-limit traffic";
                     type string {
                     }
                   }
                 }
               }
             }
           }
         }
         leaf forwarding-class {
           description "Classify packet to forwarding class";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
       }
     }
   }
   grouping firewall_addr6_object {
     leaf name {
       description "Prefix to match";
       type jt:ipv6prefix;
     }
   }
   grouping inet_filter {
     description "Define an IPv4 firewall filter";
     leaf name {
       description "Filter name";
       type string {
         length "1 .. 127";
       }
     }
     uses apply-advanced;
     list term {
       key name;
       ordered-by user;
       description "Define a firewall term";
       max-elements 16;
       leaf name {
         description "Term name";
         type string {
           length "1 .. 127";
         }
       }
       uses apply-advanced;
       container from {
         description "Define match criteria";
         uses apply-advanced;
         list source-address {
           key name;
           ordered-by user;
           description "Match IP source address";
           max-elements 1;
           uses firewall_addr_object;
         }
         list destination-address {
           key name;
           ordered-by user;
           description "Match IP destination address";
           max-elements 1;
           uses firewall_addr_object;
         }
         leaf-list source-port {
           ordered-by user;
           type string;
         }
         leaf-list destination-port {
           ordered-by user;
           type string;
         }
         leaf-list icmp-type {
           ordered-by user;
           type string;
         }
         leaf-list tcp-flags {
           ordered-by user;
           type string;
         }
         leaf-list protocol {
           ordered-by user;
           type string;
         }
         leaf-list dscp {
           ordered-by user;
           type string;
         }
         leaf-list forwarding-class {
           ordered-by user;
           description "Match forwarding class";
           type string;
           max-elements 1;
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
         }
         leaf count {
           description "Count the packet in the named counter";
           type string {
             length "1 .. 127";
           }
         }
         leaf routing-instance {
           description "Name of routing instance - Packets are directed to specified routing instance";
           type string;
         }
         leaf log {
           description "Log the packet";
           type empty;
         }
         leaf syslog {
           description "System log (syslog) information about the packet";
           type empty;
         }
         choice policer-choice {
           case case_1 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf two-rate {
                     description "Name of two-rate three-color policer to use to rate-limit traffic";
                     type string {
                     }
                   }
                 }
               }
             }
           }
         }
         leaf forwarding-class {
           description "Classify packet to forwarding class";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
       }
     }
   }
   grouping firewall_addr_object {
     leaf name {
       description "Prefix to match";
       type jt:ipv4prefix;
     }
   }
   grouping juniper-forwarding-options {
     uses apply-advanced;
     container dhcp-relay {
       description "Dynamic Host Configuration Protocol relay configuration";
       uses jdhcp-relay-type;
     }
   }
   grouping jdhcp-relay-type {
     description "Dynamic Host Configuration Protocol relay configuration";
     uses apply-advanced;
     container traceoptions {
       description "DHCP relay trace options";
       status deprecated;
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container liveness-detection {
       description "DHCP client liveness detection processing";
       uses dhcp-liveness-detection-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses override-type;
     }
     container relay-option {
       description "DHCP option processing";
       presence "enable relay-option";
       uses dhcp-generic-v4-option;
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       uses relay-option-60-type-top;
     }
     container relay-option-82 {
       description "DHCP option-82 processing";
       presence "enable relay-option-82";
       uses relay-option-82-type;
     }
     container forward-only {
       description "Forward DHCP packets without creating binding";
       presence "enable forward-only";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       uses server-group-type;
     }
     container active-server-group {
       description "Name of DHCP server group";
       uses dhcpv4-gbl-active-sg-type;
     }
     container route-suppression {
       description "Suppress access-internal and/or destination route addition";
       uses dhcp-route-suppression-type;
     }
     list group {
       key name;
       description "Define a DHCP group";
       uses dhcp-group;
     }
     list dual-stack-group {
       key name;
       description "Define a DHCP dual stack group";
       uses dhcp-dual-stack-group;
     }
     leaf no-snoop {
       description "Do not snoop DHCP packets";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       uses relay-leasequery-type;
     }
     container bulk-leasequery {
       description "DHCP bulk leasequery configuration";
       presence "enable bulk-leasequery";
       uses relay-bulk-leasequery-v4-type;
     }
     container active-leasequery {
       description "DHCPv4 active leasequery configuration";
       presence "enable active-leasequery";
       uses active-leasequery-v4-type;
     }
     container remote-id-mismatch {
       description "DHCP client remote-id mismatch";
       presence "enable remote-id-mismatch";
       uses dhcp-remote-id-mismatch-type;
     }
   }
   grouping active-leasequery-v4-type {
     description "Configure active leasequery";
     uses apply-advanced;
     leaf topology-discover {
       description "Topology discovery";
       type empty;
     }
     list peer-address {
       key name;
       description "Server ip address";
       leaf name {
         description "Peer ip address";
         type jt:ipaddr;
       }
       uses apply-advanced;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping dhcp-dual-stack-group {
     description "DHCP dual stack groups";
     leaf name {
       description "Dual stack group name";
       type string {
         length "1 .. 64";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       uses dhcp-generic-v4-option-type;
     }
     container option-77 {
       description "Add option 77 processing";
       presence "enable option-77";
       uses dhcp-generic-v4-option-type;
     }
     list option-order {
       key name;
       ordered-by user;
       description "Options precedence order";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
       }
     }
     uses apply-advanced;
     container active-server-group {
       description "Name of DHCP server group";
       uses dhcpv4-gp-active-sg-type;
     }
     container liveness-detection {
       description "DHCP client liveness detection processing";
       uses dhcp-liveness-detection-type;
     }
     leaf service-profile {
       description "Dynamic profile to use for default service activation";
       type string {
         length "1 .. 128";
       }
     }
     leaf access-profile {
       description "Access profile to use for AAA services";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       uses dhcp-generic-v4-option;
     }
     container relay-option-60 {
       description "DHCP option-60 processing";
       presence "enable relay-option-60";
       status deprecated;
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interfae tag configuration";
       leaf name {
         description "Interface tag name";
         type string {
           length "1 .. 64";
         }
       }
       uses apply-advanced;
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     leaf inline-disable {
       description "Disable inline mode for this BFD session";
       type empty;
     }
     leaf pdu-size {
       description "BFD transport protocol payload size";
       default "24";
       type union {
         type string {
           pattern "<.*>|$.*";
         }
         type uint32 {
           range "24 .. 16000";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
       mandatory true;
     }
   }
   grouping dhcp-route-suppression-type {
     uses apply-advanced;
   }
   grouping dhcp-v4-option-default-action {
     description "Default action";
     uses apply-advanced;
     choice server-group-choice {
       case case_1 {
         leaf relay-server-group {
           description "Name of DHCP relay server group when match is made";
           type string {
             length "1 .. 64";
           }
         }
       }
       case case_2 {
         leaf local-server-group {
           description "Name of DHCP local server group when match is made";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       type string {
         length "1 .. 64";
       }
     }
     leaf allow-server-change {
       description "Accept DHCP-ACK from any server in this group";
       type empty;
     }
   }
   grouping dhcpv4-gp-active-sg-type {
     leaf active-server-group {
       description "Name of DHCP server group";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     leaf exclude-relay-agent-identifier {
       description "Exclude relay agent identifier from packets to server";
       type empty;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container route-suppression {
       description "Suppress access-internal and/or access route addition";
       uses dhcpv6-route-suppression-type;
     }
     list group {
       key name;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       type empty;
     }
     container leasequery {
       description "DHCPv6 leasequery configuration";
       presence "enable leasequery";
       uses relay-leasequery-type;
     }
     container bulk-leasequery {
       description "DHCPv6 bulk leasequery configuration";
       presence "enable bulk-leasequery";
       uses relay-bulk-leasequery-v6-type;
     }
     container active-leasequery {
       description "DHCPv6 active leasequery configuration";
       presence "enable active-leasequery";
       uses active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping active-leasequery-v6-type {
     description "Configure active leasequery";
     uses apply-advanced;
     leaf topology-discover {
       description "Topology discovery";
       type empty;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       description "Peer ipv6 address";
       leaf name {
         description "Peer ipv6 address";
         type jt:ipv6addr;
       }
       uses apply-advanced;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       uses dhcp-generic-v6-option-type;
     }
     container option-16 {
       description "Add option 16 processing";
       presence "enable option-16";
       uses dhcp-generic-v6-option-type;
     }
     list option-order {
       key name;
       ordered-by user;
       description "Options precedence order";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configurations";
       leaf name {
         description "Interface tag name";
         type string {
           length "1 .. 64";
         }
       }
       uses apply-advanced;
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       type string {
         length "1 .. 64";
       }
     }
   }
   grouping dhcpv6-route-suppression-type {
     description "Suppress access-internal and/or access route addition";
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       type string {
         length "1 .. 80";
       }
       //mandatory true;
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-traceoptions-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-group {
     description "Configuration groups";
     leaf name {
       description "Group name";
       type string {
         length "1 .. 254";
       }
     }
     container when {
       description "Specify additional conditions for groups";
       uses apply-advanced;
       container time {
         description "Time at which group should be effective";
         leaf start-time {
           description "Start time([yyyy-mm-dd.]hh:mm)";
           type string;
         }
         container to {
           description "End time";
           uses apply-advanced;
           leaf end-time {
             description "End time([yyyy-mm-dd.]hh:mm)";
             type string;
           }
         }
       }
       leaf-list peers {
         ordered-by user;
         description "Hosts on which this group should be effective";
         type string {
           length "1 .. 255";
         }
       }
       leaf chassis {
         description "Chassis id";
         type enumeration {
           enum "lcc0" {
             description "Chassis lcc0";
           }
           enum "lcc1" {
             description "Chassis lcc1";
           }
           enum "lcc2" {
             description "Chassis lcc2";
           }
           enum "lcc3" {
             description "Chassis lcc3";
           }
           enum "lcc4" {
             description "Chassis lcc4";
           }
           enum "lcc5" {
             description "Chassis lcc5";
           }
           enum "lcc6" {
             description "Chassis lcc6";
           }
           enum "lcc7" {
             description "Chassis lcc7";
           }
           enum "scc" {
             description "Chassis scc";
           }
           enum "sfc0" {
             description "Chassis sfc0";
           }
         }
       }
       leaf model {
         description "Model name";
         type string;
       }
       leaf routing-engine {
         description "Routing Engine";
         type enumeration {
           enum "re0" {
             description "RE0";
           }
           enum "re1" {
             description "RE1";
           }
         }
       }
       leaf member {
         description "Member of virtual chassis";
         type string;
       }
       leaf node {
         description "Node of cluster";
         type enumeration {
           enum "node0" {
             description "Node0";
           }
           enum "node1" {
             description "Node1";
           }
         }
       }
     }
     uses juniper-config;
   }
   grouping juniper-policy-options {
     uses apply-advanced;
     list as-list {
       key name;
       description "BGP as range list information";
       leaf name {
         description "Name to identify BGP as-list";
         type string;
       }
       uses apply-advanced;
       leaf-list members {
         ordered-by user;
         description "Single autonomous system number or range of autonomous system numbers in plain number";
         type string;
       }
     }
     list as-path {
       key name;
       ordered-by user;
       description "BGP autonomous system path regular expression";
       leaf name {
         description "Name to identify AS path regular expression";
         type string;
       }
       uses apply-advanced;
       leaf path {
         description "AS path regular expression";
         type string {
         }
       }
     }
     list as-path-group {
       key name;
       ordered-by user;
       description "Group a set of AS paths";
       leaf name {
         description "Name to identify AS path group";
         type string;
       }
       uses apply-advanced;
       list as-path {
         key name;
         ordered-by user;
         description "BGP autonomous system path regular expression";
         leaf name {
           description "Name to identify AS path regular expression";
           type string;
         }
         leaf path {
           description "AS path regular expression";
           type string {
           }
         }
       }
     }
     list community {
       key name;
       description "BGP community information";
       leaf name {
         description "Name to identify BGP community";
         type string;
       }
       uses apply-advanced;
       leaf invert-match {
         description "Invert the result of the community expression matching";
         type empty;
       }
       leaf-list members {
         ordered-by user;
         description "Community members";
         type string;
       }
     }
     list condition {
       key name;
       description "Define a route advertisement condition";
       leaf name {
         description "Name to identify Condition";
         type string;
       }
       uses apply-advanced;
       choice condition_type {
         case case_1 {
         }
         case case_2 {
           container if-route-exists {
             presence "enable if-route-exists";
             description "Route exists in a specific routing table";
             uses apply-advanced;
             container address-family {
               presence "enable address-family";
               description "Indicates the address family of the route to match on";
               uses apply-advanced;
               choice address-family {
                 case case_1 {
                   container inet {
                     presence "enable inet";
                     description "Route to match corresponds to an inet/inet6 prefix";
                     uses apply-advanced;
                     leaf address {
                       description "Exact address of the route";
                       type jt:ipprefix;
                       mandatory true;
                     }
                     leaf table {
                       description "Routing table in which route should exist";
                       type string;
                       mandatory true;
                     }
                   }
                 }
                 case case_2 {
                   container ccc {
                     presence "enable ccc";
                     description "Route to match corresponds to a ccc prefix";
                     uses apply-advanced;
                     leaf address {
                       description "Logical interface used to establish ccc route";
                       type union {
                         type jt:interface-name;
                         type string {
                           pattern "<.*>|$.*";
                         }
                       }
                       mandatory true;
                     }
                     leaf table {
                       description "Routing table in which route should exist";
                       type string;
                       mandatory true;
                     }
                     leaf standby {
                       description "Indicates if route must be in standby state to be considered a match";
                       type empty;
                     }
                     leaf peer-unit {
                       description "Associated LT ifl's peer-unit. Required for LT-based routes";
                       type union {
                         type string {
                           pattern "<.*>|$.*";
                         }
                         type uint32 {
                           range "0 .. 8192";
                         }
                       }
                     }
                   }
                 }
               }
             }
             leaf address {
               description "Exact address of the route";
               type jt:ipprefix;
             }
             leaf table {
               description "Routing table in which route should exist";
               type string;
             }
           }
         }
       }
     }
     list damping {
       key name;
       ordered-by user;
       description "BGP route flap damping properties";
       leaf name {
         description "Name to identify route flap damping parameters";
         type string;
       }
       uses apply-advanced;
       choice enable-disable {
         case case_1 {
           leaf disable {
             description "Disable damping";
             type empty;
           }
         }
       }
       leaf half-life {
         description "Decay half-life";
         units "minutes";
         type union {
           type string {
             pattern "<.*>|$.*";
           }
           type uint32 {
             range "1 .. 45";
           }
         }
       }
       leaf reuse {
         description "Reuse threshold (figure-of-merit value)";
         type union {
           type string {
             pattern "<.*>|$.*";
           }
           type uint32 {
             range "1 .. 20000";
           }
         }
       }
       leaf suppress {
         description "Cutoff threshold (figure-of-merit value)";
         type union {
           type string {
             pattern "<.*>|$.*";
           }
           type uint32 {
             range "1 .. 20000";
           }
         }
       }
       leaf max-suppress {
         description "Maximum hold-down time";
         units "minutes";
         type union {
           type string {
             pattern "<.*>|$.*";
           }
           type uint32 {
             range "1 .. 720";
           }
         }
       }
     }
     container defaults {
       description "Policy default behaviour";
       uses apply-advanced;
       container route-filter {
         description "Set route filter behaviour";
         leaf walkup {
           description "Route filter walk up enable";
           type empty;
           //mandatory true;
         }
       }
       container asregex-optimize {
         description "Set AS-PATH regular expression engine optimizer";
         choice scope-choice {
           case case_1 {
             leaf optimize {
               description "Enable AS-PATH regular expression optimizer";
               type empty;
             }
           }
           case case_2 {
             leaf no-optimize {
               description "Disable AS-PATH regular expression optimizer";
               type empty;
             }
           }
         }
       }
     }
     list policy-statement {
       key name;
       description "Routing policy";
       leaf name {
         description "Name to identify a policy filter";
         type string;
       }
       uses apply-advanced;
       container defaults {
         description "Policy default behaviour";
         uses apply-advanced;
         container route-filter {
           description "Set route filter behaviour";
           choice scope-choice {
             case case_1 {
               leaf no-walkup {
                 description "Route filter walk up disable";
                 type empty;
               }
             }
             case case_2 {
               leaf walkup {
                 description "Route filter walk up enable";
                 type empty;
               }
             }
           }
         }
       }
       list term {
         key name;
         ordered-by user;
         description "Policy term";
         leaf name {
           type string;
         }
         uses apply-advanced;
         container from {
           description "Conditions to match the source of a route";
           uses apply-advanced;
           leaf instance {
             description "Routing protocol instance";
             type string;
           }
           leaf instance-any {
             description "Any routing protocol instance";
             type empty;
           }
           leaf-list instance-list {
             description "A list of routing protocol instances";
             type string;
           }
           leaf-list igp-instance {
             description "IGP instance";
             type string;
           }
           leaf igp-instance-regex {
             description "IGP instance name regular expression";
             type jt:regular-expression;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
               enum "inet-srte" {
                 description "IPv4 srtte family";
               }
               enum "inet6-srte" {
                 description "IPv6 srte family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf bgp-srte-discriminator {
             description "Srte discriminator";
             type union {
               type uint32;
               type string {
                 pattern "<.*>|$.*";
               }
             }
           }
           leaf srte-color {
             description "Srte color";
             type union {
               type uint32;
               type string {
                 pattern "<.*>|$.*";
               }
             }
           }
           leaf programmed {
             description "API-programmed route";
             type empty;
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           container validation-database-instance {
             presence "enable validation-database-instance";
             description "Name to identify a validation-state with DB name";
             uses apply-advanced;
             leaf database-name {
               description "Route Validation Database name to be looked at";
               type string;
             }
             leaf state {
               description "Name to identify a validation-state";
               type enumeration {
                 enum "valid" {
                   description "Match for valid database validation-state";
                 }
                 enum "invalid" {
                   description "Match for invalid database validation-state";
                 }
                 enum "unknown" {
                   description "Match for unknown database validation-state";
                 }
               }
               mandatory true;
             }
           }
           list nexthop-weight {
             key "choice-ident choice-value weight";
             ordered-by user;
             description "Weight of the gateway";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf weight {
               description "Weight of the gateway";
               type union {
                 type string {
                   pattern "<.*>|$.*";
                 }
                 type uint32 {
                   range "1 .. 65535";
                 }
               }
             }
             uses apply-advanced;
             choice weight_type {
               case case_1 {
                 leaf all-nexthop {
                   description "All the gateway weight should be matched";
                   type empty;
                 }
               }
             }
           }
           list nexthop-ecmp {
             key "choice-ident choice-value ecmp";
             ordered-by user;
             description "Qualify nexthop equal cost multipath gateways";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf ecmp {
               description "Number of equal cost multipath gateways";
               type union {
                 type string {
                   pattern "<.*>|$.*";
                 }
                 type uint32 {
                   range "1 .. 512";
                 }
               }
             }
             uses apply-advanced;
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf-list tag2 {
             ordered-by user;
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
           choice lsp-name-type {
             case case_1 {
               leaf lsp {
                 description "Label switched path name";
                 type string {
                 }
               }
             }
             case case_2 {
               leaf lsp-regex {
                 description "Label switched path name regular expression";
                 type string {
                 }
               }
             }
           }
           container source-routing-path {
             presence "enable source-routing-path";
             description "Spring-te lsp policy attributes";
             leaf name-regex {
               description "Spring-te lsp name regex";
               type string {
               }
             }
             leaf dest {
               description "Spring-te lsp IPV4/IPV6 destination without color";
               type jt:ipaddr;
             }
             leaf origin {
               description "Spring-te lsp origin address";
               type jt:ipaddr;
             }
             leaf tunnel-source {
               description "Spring-te lsp source protocol";
               type enumeration {
                 enum "pcep" {
                   description "Spring-te lsp src pcep";
                 }
                 enum "bgp" {
                   description "Spring-te lsp src bgp";
                 }
               }
             }
             leaf route-distinguisher {
               description "Spring-te lsp route distinguisher";
               type union {
                 type uint32;
                 type string {
                   pattern "<.*>|$.*";
                 }
               }
             }
             leaf color {
               description "Spring-te lsp color";
               type union {
                 type uint32;
                 type string {
                   pattern "<.*>|$.*";
                 }
               }
             }
           }
           list route-filter {
             key "address choice-ident choice-value";
             ordered-by user;
             description "List of routes to match";
             uses control_route_filter_type;
           }
           list source-address-filter {
             key "address choice-ident choice-value";
             ordered-by user;
             description "List of source addresses to match";
             uses control_source_address_filter_type;
           }
           list prefix-list {
             key name;
             ordered-by user;
             description "List of prefix-lists of routes to match";
             uses control_prefix_list_type;
           }
           list rib-list {
             key name;
             ordered-by user;
             description "List of routing-tables";
             uses control_rib_list_type;
           }
           list as-path-neighbors {
             key "list-type list-name";
             ordered-by user;
             description "List of peer AS to match";
             uses control_as_list_type;
           }
           list as-path-origins {
             key "list-type list-name";
             ordered-by user;
             description "List of originating AS to match";
             uses control_as_list_type;
           }
           list as-path-transits {
             key "list-type list-name";
             ordered-by user;
             description "List of originating AS to match";
             uses control_as_list_type;
           }
           list prefix-list-filter {
             key "list_name choice-ident choice-value";
             ordered-by user;
             description "List of prefix-list-filters to match";
             uses control_prefix_list_filter_type;
           }
           list rtf-prefix-list {
             key name;
             ordered-by user;
             description "List of rtf-prefix-lists of routes to match";
             uses control_rtf_prefix_list_type;
           }
           list route-filter-list {
             key name;
             ordered-by user;
             description "List of route-filter-lists of routes to match";
             uses control_route_filter_list_type;
           }
           list source-address-filter-list {
             key name;
             ordered-by user;
             description "List of source-address-filter-lists of routes to match";
             uses control_source_address_filter_list_type;
           }
           container multicast-scope {
             description "Multicast scope to match";
             choice scope-choice {
               case case_1 {
                 leaf node-local {
                   description "Node-local scope";
                   type empty;
                 }
               }
               case case_2 {
                 leaf link-local {
                   description "Link-local scope";
                   type empty;
                 }
               }
               case case_3 {
                 leaf site-local {
                   description "Site-local scope";
                   type empty;
                 }
               }
               case case_4 {
                 leaf organization-local {
                   description "Organization-local scope";
                   type empty;
                 }
               }
               case case_5 {
                 leaf global {
                   description "Global scope";
                   type empty;
                 }
               }
               case case_6 {
                 leaf scope_value {
                   description "Scope value";
                   type union {
                     type string {
                       pattern "<.*>|$.*";
                     }
                     type uint32 {
                       range "0 .. 15";
                     }
                   }
                 }
               }
             }
             choice scope-operator {
               case case_1 {
                 leaf orhigher {
                   description "Match higher values";
                   type empty;
                 }
               }
               case case_2 {
                 leaf orlower {
                   description "Match lower values";
                   type empty;
                 }
               }
             }
           }
           leaf aggregate-contributor {
             description "Match more specifics of an aggregate";
             type empty;
           }
           leaf state {
             description "Route state";
             type enumeration {
               enum "active" {
                 description "Active route";
               }
               enum "inactive" {
                 description "Inactive route";
               }
             }
           }
           leaf-list tunnel-type {
             ordered-by user;
             description "Tunnel type";
             type enumeration {
               enum "gre" {
                 description "GRE tunnel";
               }
               enum "udp" {
                 description "UDP tunnel";
               }
               enum "ipip" {
                 description "IPIP tunnel";
               }
             }
           }
           leaf route-type {
             description "Route type";
             type enumeration {
               enum "internal" {
                 description "Internal route";
               }
               enum "external" {
                 description "External route";
               }
             }
           }
           leaf-list nlri-route-type {
             ordered-by user;
             description "Route type from NLRI";
             type union {
               type string {
                 pattern "<.*>|$.*";
               }
               type uint32 {
                 range "1 .. 10";
               }
             }
           }
           leaf-list evpn-tag {
             ordered-by user;
             description "Tag in EVPN Route";
             type union {
               type string {
                 pattern "<.*>|$.*";
               }
               type uint32 {
                 range "0 .. 4294967295";
               }
             }
           }
           leaf-list evpn-esi {
             ordered-by user;
             description "ESI in EVPN Route";
             type string;
           }
           list mac-filter-list {
             key name;
             ordered-by user;
             description "List of mac-filter-list macs to match";
             uses control_mac_address_filter_list_type;
           }
           leaf evpn-mac-route {
             description "EVPN Mac Route type";
             type enumeration {
               enum "mac-only" {
                 description "MAC route";
               }
               enum "mac-ipv4" {
                 description "MAC IPV4 route";
               }
               enum "mac-ipv6" {
                 description "MAC IPV6 route";
               }
             }
           }
           leaf-list bridge-domain-id {
             ordered-by user;
             description "Bridge Domain Identifier (Vlan or VNI)";
             type union {
               type string {
                 pattern "<.*>|$.*";
               }
               type uint32 {
                 range "0 .. 4294967295";
               }
             }
           }
           leaf next-hop-type {
             description "Next-hop type";
             type enumeration {
               enum "merged" {
                 description "Merged next hop";
               }
             }
           }
           leaf-list condition {
             ordered-by user;
             description "Condition to match on";
             type string;
           }
           list community-count {
             key name;
             ordered-by user;
             description "Number of BGP communities";
             uses community_count_type;
           }
           list large-community-count {
             key name;
             ordered-by user;
             description "Number of Large BGP communities";
             uses community_count_type;
           }
           list as-path-unique-count {
             key name;
             ordered-by user;
             description "Number of unique BGP ASes excluding confederations";
             uses as-path-unique-count-type;
           }
           list as-path-calc-length {
             key name;
             ordered-by user;
             description "Number of BGP ASes excluding confederations";
             uses as-path-calc-length-type;
           }
           container traffic-engineering {
             presence "enable traffic-engineering";
             description "Traffic-Engineering related parameters";
             uses apply-advanced;
             leaf-list protocol {
               ordered-by user;
               description "Protocol that originated the entry";
               type enumeration {
                 enum "direct" {
                   description "Directly originated";
                 }
                 enum "ospf" {
                   description "OSPF originated";
                 }
                 enum "isis-level-1" {
                   description "ISIS level-1 originated";
                 }
                 enum "isis-level-2" {
                   description "ISIS level-2 originated";
                 }
                 enum "spring-te" {
                   description "SPRING-TE originated";
                 }
                 enum "static" {
                   description "Statically originated";
                 }
                 enum "unknown" {
                   description "Originated by unknown sources";
                 }
               }
             }
             container node {
               presence "enable node";
               description "Node-related parameters";
               uses apply-advanced;
               leaf as {
                 description "AS number";
                 type string {
                 }
               }
               leaf node-type {
                 description "Real or pseudo-node";
                 type enumeration {
                   enum "router" {
                     description "Real node";
                   }
                   enum "pseudo-node" {
                     description "Pseudo-node";
                   }
                 }
               }
               leaf router-id {
                 description "IP prefix to match the router-id against";
                 type jt:ipprefix;
               }
               leaf sys-id {
                 description "ISO address of the node";
                 type jt:sysid;
               }
             }
             container ipv4-prefix {
               presence "enable ipv4-prefix";
               description "IPV4 prefix-related parameters";
               uses apply-advanced;
               leaf as {
                 description "AS number";
                 type string {
                 }
               }
               leaf router-id {
                 description "IP prefix to match the router-id against";
                 type jt:ipprefix;
               }
               leaf prefix {
                 description "IP prefix to match against";
                 type jt:ipprefix;
               }
               leaf sys-id {
                 description "ISO address of the node";
                 type jt:sysid;
               }
             }
             container ipv6-prefix {
               presence "enable ipv6-prefix";
               description "IPV6 prefix related parameters";
               uses apply-advanced;
               leaf as {
                 description "AS number";
                 type string {
                 }
               }
               leaf router-id {
                 description "IPv6 prefix to match the router-id against";
                 type jt:ipprefix;
               }
               leaf prefix {
                 description "IPv6 prefix to match against";
                 type jt:ipv6prefix;
               }
               leaf sys-id {
                 description "ISO address of the node";
                 type jt:sysid;
               }
             }
             container srv6-sid {
               presence "enable srv6-sid";
               description "SRV6 SID related parameters";
               uses apply-advanced;
               leaf as {
                 description "AS number";
                 type string {
                 }
               }
               leaf router-id {
                 description "SRv6 SID to match the router-id against";
                 type jt:ipprefix;
               }
               leaf sid {
                 description "SRv6 SID to match against";
                 type jt:ipv6addr;
               }
               leaf sys-id {
                 description "ISO address of the node";
                 type jt:sysid;
               }
             }
             container spring-te {
               presence "enable spring-te";
               description "SPRING-TE policy related parameters";
               uses apply-advanced;
               leaf node-as {
                 description "Node AS number";
                 type string {
                 }
               }
               leaf router-id {
                 description "IP prefix to match against the node for the SPRING TE policy";
                 type jt:ipprefix;
               }
               leaf color {
                 description "Color of the SPRING-TE policy candidate path";
                 type union {
                   type uint32;
                   type string {
                     pattern "<.*>|$.*";
                   }
                 }
               }
               leaf discriminator {
                 description "Discriminator of the SPRING-TE policy candidate path";
                 type union {
                   type uint32;
                   type string {
                     pattern "<.*>|$.*";
                   }
                 }
               }
               leaf endpoint {
                 description "Endpoint of the SPRING-TE policy candidate path";
                 type jt:ipaddr;
               }
               leaf protocol-origin {
                 description "Protocol originating the SPRING-TE policy candidate path";
                 type enumeration {
                   enum "bgp" {
                     description "SPRING-TE policy candidate path originated by BGP";
                   }
                   enum "cli" {
                     description "SPRING-TE policy candidate path originated by cli";
                   }
                   enum "pcep" {
                     description "SPRING-TE policy candidate path originated by PCEP";
                   }
                 }
               }
               leaf origin-as {
                 description "AS number of the node creating the SPRING-TE policy candidate path";
                 type string {
                 }
               }
               leaf origin-addr {
                 description "Address of the node originating the SPRING-TE policy candidate path";
                 type jt:ipaddr;
               }
             }
             container link {
               presence "enable link";
               description "Link-related parameters";
               uses apply-advanced;
               container from {
                 description "Specify parameter of the 'from' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
               container to {
                 description "Specify parameters of the 'to' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
             }
             leaf identifier {
               description "BGP-TE identifier";
               type union {
                 type string {
                   pattern "<.*>|$.*";
                 }
                 type uint64 {
                   range "2 .. 18446744073709551615";
                 }
               }
             }
           }
           leaf-list route-distinguisher {
             ordered-by user;
             description "Name of the route-distinguisher";
             type string;
           }
           leaf prefix-segment {
             description "Prefix segment present in route extended data";
             type empty;
           }
         }
         container to {
           description "Conditions to match the destination of a route";
           uses apply-advanced;
           leaf instance {
             description "Routing protocol instance";
             type string;
           }
           leaf instance-any {
             description "Any routing protocol instance";
             type empty;
           }
           leaf-list instance-list {
             description "A list of routing protocol instances";
             type string;
           }
           leaf-list igp-instance {
             description "IGP instance";
             type string;
           }
           leaf igp-instance-regex {
             description "IGP instance name regular expression";
             type jt:regular-expression;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
               enum "inet-srte" {
                 description "IPv4 srtte family";
               }
               enum "inet6-srte" {
                 description "IPv6 srte family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf bgp-srte-discriminator {
             description "Srte discriminator";
             type union {
               type uint32;
               type string {
                 pattern "<.*>|$.*";
               }
             }
           }
           leaf srte-color {
             description "Srte color";
             type union {
               type uint32;
               type string {
                 pattern "<.*>|$.*";
               }
             }
           }
           leaf programmed {
             description "API-programmed route";
             type empty;
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           container validation-database-instance {
             presence "enable validation-database-instance";
             description "Name to identify a validation-state with DB name";
             uses apply-advanced;
             leaf database-name {
               description "Route Validation Database name to be looked at";
               type string;
             }
             leaf state {
               description "Name to identify a validation-state";
               type enumeration {
                 enum "valid" {
                   description "Match for valid database validation-state";
                 }
                 enum "invalid" {
                   description "Match for invalid database validation-state";
                 }
                 enum "unknown" {
                   description "Match for unknown database validation-state";
                 }
               }
               mandatory true;
             }
           }
           list nexthop-weight {
             key "choice-ident choice-value weight";
             ordered-by user;
             description "Weight of the gateway";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf weight {
               description "Weight of the gateway";
               type union {
                 type string {
                   pattern "<.*>|$.*";
                 }
                 type uint32 {
                   range "1 .. 65535";
                 }
               }
             }
             uses apply-advanced;
             choice weight_type {
               case case_1 {
                 leaf all-nexthop {
                   description "All the gateway weight should be matched";
                   type empty;
                 }
               }
             }
           }
           list nexthop-ecmp {
             key "choice-ident choice-value ecmp";
             ordered-by user;
             description "Qualify nexthop equal cost multipath gateways";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf ecmp {
               description "Number of equal cost multipath gateways";
               type union {
                 type string {
                   pattern "<.*>|$.*";
                 }
                 type uint32 {
                   range "1 .. 512";
                 }
               }
             }
             uses apply-advanced;
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf-list tag2 {
             ordered-by user;
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
           choice lsp-name-type {
             case case_1 {
               leaf lsp {
                 description "Label switched path name";
                 type string {
                 }
               }
             }
             case case_2 {
               leaf lsp-regex {
                 description "Label switched path name regular expression";
                 type string {
                 }
               }
             }
           }
           container source-routing-path {
             presence "enable source-routing-path";
             description "Spring-te lsp policy attributes";
             leaf name-regex {
               description "Spring-te lsp name regex";
               type string {
               }
             }
             leaf dest {
               description "Spring-te lsp IPV4/IPV6 destination without color";
               type jt:ipaddr;
             }
             leaf origin {
               description "Spring-te lsp origin address";
               type jt:ipaddr;
             }
             leaf tunnel-source {
               description "Spring-te lsp source protocol";
               type enumeration {
                 enum "pcep" {
                   description "Spring-te lsp src pcep";
                 }
                 enum "bgp" {
                   description "Spring-te lsp src bgp";
                 }
               }
             }
             leaf route-distinguisher {
               description "Spring-te lsp route distinguisher";
               type union {
                 type uint32;
                 type string {
                   pattern "<.*>|$.*";
                 }
               }
             }
             leaf color {
               description "Spring-te lsp color";
               type union {
                 type uint32;
                 type string {
                   pattern "<.*>|$.*";
                 }
               }
             }
           }
         }
         container then {
           description "Actions to take if 'from' and 'to' conditions match";
           uses apply-advanced;
           container metric {
             description "Metric value";
             uses apply-advanced;
             choice metric_action {
               case case_1 {
                 leaf metric {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
               case case_4 {
                 container igp {
                   presence "enable igp";
                   description "Track the IGP metric (BGP only)";
                   leaf metric_offset {
                     description "Metric offset for MED";
                     type union {
                       type int32;
                       type string {
                         pattern "<.*>|$.*";
                       }
                     }
                   }
                 }
               }
               case case_5 {
                 container minimum-igp {
                   presence "enable minimum-igp";
                   description "Track the minimum IGP metric (BGP only)";
                   leaf metric_offset {
                     description "Metric offset for MED";
                     type union {
                       type int32;
                       type string {
                         pattern "<.*>|$.*";
                       }
                     }
                   }
                 }
               }
               case case_6 {
                 container expression {
                   description "Calculate value based on route metric and metric2";
                   uses metric_expression_type;
                 }
               }
               case case_7 {
                 leaf aigp {
                   description "Use aigp, if it exists, to set the IGP metric";
                   type empty;
                 }
               }
               case case_8 {
                 container effective-aigp {
                   presence "enable effective-aigp";
                   description "Track the effective AIGP metric (BGP only)";
                   leaf metric_offset {
                     description "Metric offset for MED";
                     type union {
                       type int32;
                       type string {
                         pattern "<.*>|$.*";
                       }
                     }
                   }
                 }
               }
               case case_9 {
                 container minimum-effective-aigp {
                   presence "enable minimum-effective-aigp";
                   description "Track the minimum effective AIGP metric (BGP only)";
                   leaf metric_offset {
                     description "Metric offset for MED";
                     type union {
                       type int32;
                       type string {
                         pattern "<.*>|$.*";
                       }
                     }
                   }
                 }
               }
             }
           }
           container metric2 {
             description "Metric value 2";
             uses apply-advanced;
             choice metric_action {
               case case_1 {
                 leaf metric2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric3 {
             description "Metric value 3";
             uses apply-advanced;
             choice metric_action {
               case case_1 {
                 leaf metric3 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric4 {
             description "Metric value 4";
             uses apply-advanced;
             choice metric_action {
               case case_1 {
                 leaf metric4 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag {
             description "Tag string";
             uses apply-advanced;
             choice metric_action {
               case case_1 {
                 leaf tag {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag2 {
             description "Tag string 2";
             uses apply-advanced;
             choice metric_action {
               case case_1 {
                 leaf tag2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference {
             description "Preference value";
             uses apply-advanced;
             choice metric_action {
               case case_1 {
                 leaf preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference2 {
             description "Preference value 2";
             uses apply-advanced;
             choice metric_action {
               case case_1 {
                 leaf preference2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color {
             description "Color (preference) value";
             uses apply-advanced;
             choice metric_action {
               case case_1 {
                 leaf color {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color2 {
             description "Color (preference) value 2";
             uses apply-advanced;
             choice metric_action {
               case case_1 {
                 leaf color2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container local-preference {
             description "Local preference associated with a route";
             uses apply-advanced;
             choice metric_action {
               case case_1 {
                 leaf local-preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container credibility {
             description "TED credibility value for entries from BGP-TE";
             uses apply-advanced;
             choice metric_action {
               case case_1 {
                 leaf credibility {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           leaf priority {
             description "Set priority for route installation";
             type enumeration {
               enum "high" {
                 description "Set priority to high";
               }
               enum "medium" {
                 description "Set priority to medium";
               }
               enum "low" {
                 description "Set priority to low";
               }
             }
           }
           container prefix-segment {
             description "Set prefix segment attributes";
             uses apply-advanced;
             list algorithm {
               key name;
               description "Set prefix segment attributes for strict/flex algorithm ";
               max-elements 15;
               leaf name {
                 description "Set prefix segment for strict/flex algorithm";
                 type union {
                   type string {
                     pattern "<.*>|$.*";
                   }
                   type uint32 {
                     range "1 .. 255";
                   }
                 }
                 mandatory true;
               }
               leaf index {
                 description "Set prefix segment index id";
                 type union {
                   type string {
                     pattern "<.*>|$.*";
                   }
                   type uint32 {
                     range "0 .. 1048575";
                   }
                 }
                 mandatory true;
               }
               leaf node-segment {
                 description "Set node segment flag for this prefix segment";
                 type empty;
               }
             }
             leaf index {
               description "Set prefix segment index id";
               type union {
                 type string {
                   pattern "<.*>|$.*";
                 }
                 type uint32 {
                   range "0 .. 1048575";
                 }
               }
             }
             leaf node-segment {
               description "Set node segment flag for default prefix segment";
               type empty;
             }
             leaf redistribute {
               description "Redistribute prefix-segment from route entry";
               type empty;
             }
           }
           leaf label-allocation {
             description "Set label allocation mode";
             type enumeration {
               enum "per-table" {
                 description "Set per-table label allocation mode";
               }
               enum "per-nexthop" {
                 description "Set per-nexthop label allocation mode";
               }
               enum "per-table-localize" {
                 description "Set per-table-localize label allocation mode";
               }
             }
           }
           container add-path {
             description "Set BGP add-path attributes";
             leaf send-count {
               description "Number of add-paths sent";
               type union {
                 type string {
                   pattern "<.*>|$.*";
                 }
                 type uint32 {
                   range "2 .. 64";
                 }
               }
             }
           }
           leaf fib-install-priority {
             description "Set Fib Instalation priority of a route";
             type enumeration {
               enum "high" {
                 description "Set Fib install priority  to high";
               }
               enum "medium" {
                 description "Set Fib install priority to medium ";
               }
             }
           }
           leaf validation-state {
             description "Set validation-state of a route";
             type enumeration {
               enum "valid" {
                 description "Set validaton-state to valid";
               }
               enum "invalid" {
                 description "Set validation-state to invalid";
               }
               enum "unknown" {
                 description "Set validation-state to unknown";
               }
             }
           }
           leaf origin {
             description "BGP path origin";
             type enumeration {
               enum "igp" {
                 description "Path originated in the local IGP";
               }
               enum "egp" {
                 description "Path originated in another AS";
               }
               enum "incomplete" {
                 description "Path was learned by some other means";
               }
             }
           }
           container srv6 {
             description "Configure SID with 128 bit address";
             leaf sid {
               description "IPv6 Address";
               type jt:ipv6addr;
             }
             leaf locator {
               description "Name of locator";
               type string;
             }
             choice locator_type {
               case case_1 {
                 leaf micro-dt4-sid {
                   description "Micro SID type dt4";
                   type empty;
                 }
               }
               case case_2 {
                 leaf micro-dt6-sid {
                   description "Micro SID type dt6";
                   type empty;
                 }
               }
               case case_3 {
                 leaf micro-dt46-sid {
                   description "Micro SID type dt46";
                   type empty;
                 }
               }
             }
           }
           container aigp-originate {
             presence "enable aigp-originate";
             description "Originate a BGP AIGP attribute";
             leaf distance {
               description "AIGP distance";
               type union {
                 type uint32;
                 type string {
                   pattern "<.*>|$.*";
                 }
               }
             }
           }
           container aigp-adjust {
             description "Adjust a BGP AIGP attribute";
             choice math-op {
               case case_1 {
                 leaf add {
                   type empty;
                 }
               }
               case case_2 {
                 leaf subtract {
                   type empty;
                 }
               }
               case case_3 {
                 leaf multiply {
                   type empty;
                 }
               }
               case case_4 {
                 leaf divide {
                   type empty;
                 }
               }
             }
             choice adjust-value {
               case case_1 {
                 leaf user-value {
                   description "Adjustment value";
                   type union {
                     type uint64;
                     type string {
                       pattern "<.*>|$.*";
                     }
                   }
                 }
               }
               case case_2 {
                 leaf distance-to-protocol-nexthop {
                   description "Metric2";
                   type empty;
                 }
               }
             }
           }
           list community {
             key "choice-ident choice-value community-name";
             ordered-by user;
             description "BGP community properties associated with a route";
             leaf choice-ident {
               type enumeration {
                 enum "equal-literal" {
                 }
                 enum "set" {
                 }
                 enum "plus-literal" {
                 }
                 enum "add" {
                 }
                 enum "minus-literal" {
                 }
                 enum "delete" {
                 }
               }
             }
             leaf choice-value {
               type string;
             }
             leaf community-name {
               description "Name to identify a BGP community";
               type string;
             }
           }
           list tunnel-attribute {
             key "choice-ident choice-value tunnel-attribute-name";
             ordered-by user;
             description "BGP tunnel attribute associated with a route";
             leaf choice-ident {
               type enumeration {
                 enum "set" {
                 }
                 enum "remove" {
                 }
               }
             }
             leaf choice-value {
               type string;
             }
             leaf tunnel-attribute-name {
               description "Name of a tunnel attribute , or 'all'";
               type string;
             }
           }
           container assisted-replication {
             presence "enable assisted-replication";
             description "Deterministic AR replicator knobs";
             uses apply-advanced;
             leaf-list replicator-ip {
               description "Set deterministic AR replicator ip for the flow";
               type jt:ipaddr;
               max-elements 1;
             }
             leaf strict {
               description "Do not use any other replicator";
               type empty;
             }
             leaf-list fallback-replicator-ip {
               description "Set Fallback replicator-ip";
               type jt:ipaddr;
               max-elements 1;
             }
           }
           leaf damping {
             description "Define BGP route flap damping parameters";
             type string;
           }
           container aggregate-bandwidth {
             presence "enable aggregate-bandwidth";
             description "Advertise aggregate outbound link bandwidth";
             uses apply-advanced;
             choice transitive-type {
               case case_1 {
                 leaf transitive {
                   description "Transitive flag for link bandwidth";
                   type empty;
                 }
               }
               case case_2 {
                 leaf non-transitive {
                   description "Non-Transitive flag for link bandwidth";
                   type empty;
                 }
               }
             }
             leaf divide-equal {
               description "Divide-equal";
               type empty;
             }
           }
           container auto-link-bandwidth {
             presence "enable auto-link-bandwidth";
             description "Auto sense and attach link bandwidth community";
             uses apply-advanced;
             choice transitive-type {
               case case_1 {
                 leaf transitive {
                   description "Transitive flag for link bandwidth";
                   type empty;
                 }
               }
               case case_2 {
                 leaf non-transitive {
                   description "Non-Transitive flag for link bandwidth";
                   type empty;
                 }
               }
             }
           }
           leaf limit-bandwidth {
             description "Limit advertised aggregate outbound link bandwidth";
             type union {
               type uint64;
               type string {
                 pattern "<.*>|$.*";
               }
             }
           }
           leaf no-entropy-label-capability {
             description "Don't advertise entropy label capability";
             type empty;
           }
           leaf as-path-prepend {
             description "Prepend AS numbers to an AS path (BGP only)";
             type string;
           }
           container as-path-expand {
             description "Prepend AS numbers prior to adding local-as (BGP only)";
             choice aspath_exp_value {
               case case_1 {
                 container last-as {
                   presence "enable last-as";
                   description "Prepend last AS";
                   leaf count {
                     description "Repeat count";
                     type union {
                       type string {
                         pattern "<.*>|$.*";
                       }
                       type uint32 {
                         range "1 .. 32";
                       }
                     }
                   }
                 }
               }
               case case_2 {
                 leaf aspath {
                   description "AS path string";
                   type string;
                 }
               }
             }
           }
           container next-hop {
             description "Set the address of the next-hop router";
             choice nexthop_value {
               case case_1 {
                 leaf self {
                   description "Use a local address as the next-hop address";
                   type empty;
                 }
               }
               case case_2 {
                 leaf peer-address {
                   description "Use the remote peer address as the next-hop address";
                   type empty;
                 }
               }
               case case_3 {
                 leaf address {
                   description "Next-hop address";
                   type jt:ipaddr;
                 }
               }
               case case_4 {
                 leaf reject {
                   description "Use a reject next hop";
                   type empty;
                 }
               }
               case case_5 {
                 leaf discard {
                   description "Use a discard next hop";
                   type empty;
                 }
               }
               case case_6 {
                 leaf next-table {
                   description "Perform a forwarding lookup in the specified table";
                   type string;
                 }
               }
             }
           }
           container install-nexthop {
             description "Choose the next hop to be used for forwarding";
             choice strict_type {
               case case_1 {
                 leaf strict {
                   description "Do not use any other available next hops";
                   type empty;
                 }
               }
               case case_2 {
                 leaf strict-named-lsp {
                   description "Do not use any other non-lsp next hops";
                   type empty;
                 }
               }
             }
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
             container except {
               description "Do not choose to install matching next hops";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
               }
               container fallback {
                 description "Backup option";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                 }
                 container except {
                   description "Do not choose to install matching next hops";
                   uses apply-advanced;
                   choice nexthop-value {
                     case case_1 {
                       leaf-list lsp {
                         ordered-by user;
                         description "Next-hop LSP name";
                         type string;
                       }
                     }
                     case case_2 {
                       leaf-list lsp-regex {
                         ordered-by user;
                         description "Next-hop LSP name regular expression";
                         type string;
                       }
                     }
                     case case_3 {
                       leaf-list static-lsp {
                         ordered-by user;
                         description "Next-hop static LSP name";
                         type string;
                       }
                     }
                     case case_4 {
                       leaf-list static-lsp-regex {
                         ordered-by user;
                         description "Next-hop static LSP name regular expression";
                         type string;
                       }
                     }
                     case case_5 {
                       leaf non-lsp-nexthop {
                         description "Next-hop with non-lsp";
                         type empty;
                       }
                     }
                     case case_6 {
                       leaf non-labelled-nexthop {
                         description "Next-hop without tag";
                         type empty;
                       }
                     }
                     case case_7 {
                       leaf overlay-vxlan-interfaces {
                         description "Next-hop for vxlan interfaces";
                         type empty;
                       }
                     }
                   }
                 }
               }
             }
             container fallback {
               description "Backup option ";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
               }
               container except {
                 description "Do not choose to install matching next hops";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                 }
               }
             }
           }
           leaf trace {
             description "Log matches to a trace file";
             type empty;
           }
           container external {
             presence "enable external";
             description "External route";
             uses apply-advanced;
             leaf type {
               description "OSPF external metric type";
               type union {
                 type string {
                   pattern "<.*>|$.*";
                 }
                 type int32 {
                   range "1 .. 2";
                 }
               }
             }
             leaf nssa-only {
               description "Clear P-bit on lsa type 7";
               type empty;
             }
           }
           container load-balance {
             description "Type of load balancing in forwarding table";
             choice load_balance_type {
               case case_1 {
                 leaf per-packet {
                   description "Load balance on a per-packet basis deprecated, use per-flow instead";
                   type empty;
                 }
               }
               case case_2 {
                 leaf per-flow {
                   description "Load balance on a per-flow basis";
                   type empty;
                 }
               }
               case case_3 {
               }
               case case_4 {
               }
               case case_5 {
               }
               case case_6 {
               }
               case case_7 {
               }
               case case_8 {
               }
               case case_9 {
               }
               case case_10 {
               }
               case case_11 {
               }
             }
           }
           container advertise-locator {
             presence "enable advertise-locator";
             description "Advertise SRv6 Locator";
             uses apply-advanced;
             leaf internal {
               description "Advertise locator as Interal route";
               type empty;
             }
           }
           leaf set-down-bit {
             description "Set down bit";
             type empty;
           }
           leaf analyze {
             description "Send to registered controllers for analysis";
             type empty;
           }
           leaf destination-class {
             description "Set destination class in forwarding table";
             type string;
           }
           leaf source-class {
             description "Set source class in forwarding table";
             type string;
           }
           leaf forwarding-class {
             description "Set source or destination class in forwarding table";
             type string;
           }
           container map-to-interface {
             description "Set output logical interface";
             choice map_to_interface_value {
               case case_1 {
                 leaf self {
                   description "Map the interface to itself";
                   type empty;
                 }
               }
               case case_2 {
                 leaf interface {
                   description "Output logical interface";
                   type union {
                     type jt:interface-name;
                     type string {
                       pattern "<.*>|$.*";
                     }
                   }
                 }
               }
             }
           }
           leaf-list ssm-source {
             ordered-by user;
             description "List of Sources for SSM mapping";
             type jt:ipaddr;
           }
           container p2mp-lsp-root {
             description "P2mp lsp root address";
             uses apply-advanced;
             leaf address {
               description "Ipv4 root address";
               type jt:ipv4addr;
             }
           }
           leaf dynamic-tunnel-attributes {
             description "Choose the dynamic tunnel attributes used for forwarding";
             type string;
           }
           leaf tunnel-end-point-address {
             description "Set tunnel end-point address of tunnel";
             type jt:ipaddr;
           }
           leaf selected-mldp-egress {
             description "This node should act as egress node for MLDP inband signalling";
             type empty;
           }
           leaf mhop-bfd-port {
             description "Use port number 4784 for MPLS-BFD as per RFC5884";
             type empty;
           }
           leaf no-backup {
             description "This prefix should not have backup";
             type empty;
           }
           leaf default-action {
             description "Set default policy action";
             type enumeration {
               enum "accept" {
                 description "Accept a route";
               }
               enum "reject" {
                 description "Reject a route";
               }
             }
           }
           leaf next {
             description "Skip to next policy or term";
             type enumeration {
               enum "policy" {
                 description "Skip to next policy filter";
               }
               enum "term" {
                 description "Skip to next term in a policy filter";
               }
             }
           }
           choice accept_reject {
             case case_1 {
               leaf accept {
                 description "Accept a route";
                 type empty;
               }
             }
             case case_2 {
               leaf reject {
                 description "Reject a route";
                 type empty;
               }
             }
           }
           container bgp-output-queue-priority {
             description "Set the BGP Update output queue priority.";
             choice class {
               case case_1 {
                 leaf priority {
                   description "Output queue priority; higher is better";
                   type union {
                     type string {
                       pattern "<.*>|$.*";
                     }
                     type uint32 {
                       range "1 .. 16";
                     }
                   }
                 }
               }
               case case_2 {
                 leaf expedited {
                   description "Expedited queue; highest priority";
                   type empty;
                 }
               }
             }
           }
           leaf multipath-resolve {
             description "Use all paths for resolution over this prefix";
             type empty;
           }
           leaf source-routing-path-template {
             description "Spring-te template to apply";
             type string {
             }
           }
           leaf label-allocation-fallback-reject {
             description "Suppress prefix export when label allocation fails";
             type empty;
           }
           leaf resolution-map {
             description "Set resolution map modes";
             type string;
           }
           leaf ignore-service-label {
             description "Ignore service labels";
             type empty;
           }
           container prefix-attribute-flags {
             presence "enable prefix-attribute-flags";
             description "Set ISIS prefix attribute flags sub TLV";
             uses apply-advanced;
             leaf node-segment-flag {
               description "Set node segment flag ";
               type empty;
             }
             leaf external-prefix-flag {
               description "Set external prefix flag ";
               type empty;
             }
             leaf anycast-flag {
               description "Set anycast flag ";
               type empty;
             }
             leaf entropy-label-capability-flag {
               description "Set entropy label capability flag ";
               type empty;
             }
           }
           container ipv4-source-router-id {
             presence "enable ipv4-source-router-id";
             description "Set IPv4 source router id in advertisement";
             uses apply-advanced;
             leaf router-id {
               description "Specify IPv4 address";
               type jt:ipaddr;
             }
           }
           container ipv6-source-router-id {
             presence "enable ipv6-source-router-id";
             description "Set IPv6 source router id in advertisement";
             uses apply-advanced;
             leaf router-id {
               description "Specify IPv6 address";
               type jt:ipv6addr;
             }
           }
           leaf request-long-lived-ack {
             description "Advertise route after forwarding is programmed";
             type empty;
           }
           leaf send-withdrawal-on-route-change {
             description "Withdraw route if change is not acked from forwarding";
             type empty;
           }
           container slice {
             description "Configure Policy Slice action";
             leaf slice-name {
               description "Slice Name";
               type string {
                 length "1 .. 64";
               }
             }
           }
           leaf filter {
             description "Set firewall-filter name";
             type string {
             }
           }
           leaf strip-as-path {
             description "Remove the incoming BGP as-path and replace with local AS";
             type empty;
           }
           container request-acknowledgements {
             description "Set request acknowledgement";
             leaf nexthop-ack {
               description "Set nexthop acknowledgement ";
               type empty;
             }
             leaf route-ack {
               description "Set route acknowledgement ";
               type empty;
             }
           }
         }
       }
       container from {
         description "Conditions to match the source of a route";
         uses apply-advanced;
         leaf instance {
           description "Routing protocol instance";
           type string;
         }
         leaf instance-any {
           description "Any routing protocol instance";
           type empty;
         }
         leaf-list instance-list {
           description "A list of routing protocol instances";
           type string;
         }
         leaf-list igp-instance {
           description "IGP instance";
           type string;
         }
         leaf igp-instance-regex {
           description "IGP instance name regular expression";
           type jt:regular-expression;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
             enum "inet-srte" {
               description "IPv4 srtte family";
             }
             enum "inet6-srte" {
               description "IPv6 srte family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "express-segments" {
               description "Express-segment routes";
             }
             enum "rift" {
               description "RIFT routes";
             }
             enum "l2-learned-host-routing" {
               description "Layer2-learned host routes";
             }
             enum "srv6-isis" {
               description "SRV6 ISIS";
             }
             enum "ari-ts" {
               description "ARI TS routes";
             }
             enum "srv6" {
               description "Segment Routing IPv6 local route";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf bgp-srte-discriminator {
           description "Srte discriminator";
           type union {
             type uint32;
             type string {
               pattern "<.*>|$.*";
             }
           }
         }
         leaf srte-color {
           description "Srte color";
           type union {
             type uint32;
             type string {
               pattern "<.*>|$.*";
             }
           }
         }
         leaf programmed {
           description "API-programmed route";
           type empty;
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         container validation-database-instance {
           presence "enable validation-database-instance";
           description "Name to identify a validation-state with DB name";
           uses apply-advanced;
           leaf database-name {
             description "Route Validation Database name to be looked at";
             type string;
           }
           leaf state {
             description "Name to identify a validation-state";
             type enumeration {
               enum "valid" {
                 description "Match for valid database validation-state";
               }
               enum "invalid" {
                 description "Match for invalid database validation-state";
               }
               enum "unknown" {
                 description "Match for unknown database validation-state";
               }
             }
             mandatory true;
           }
         }
         list nexthop-weight {
           key "choice-ident choice-value weight";
           ordered-by user;
           description "Weight of the gateway";
           leaf choice-ident {
             type enumeration {
               enum "equal" {
               }
               enum "greater-than" {
               }
               enum "less-than" {
               }
               enum "greater-than-equal" {
               }
               enum "less-than-equal" {
               }
             }
           }
           leaf choice-value {
             type string;
           }
           leaf weight {
             description "Weight of the gateway";
             type union {
               type string {
                 pattern "<.*>|$.*";
               }
               type uint32 {
                 range "1 .. 65535";
               }
             }
           }
           uses apply-advanced;
           choice weight_type {
             case case_1 {
               leaf all-nexthop {
                 description "All the gateway weight should be matched";
                 type empty;
               }
             }
           }
         }
         list nexthop-ecmp {
           key "choice-ident choice-value ecmp";
           ordered-by user;
           description "Qualify nexthop equal cost multipath gateways";
           leaf choice-ident {
             type enumeration {
               enum "equal" {
               }
               enum "greater-than" {
               }
               enum "less-than" {
               }
               enum "greater-than-equal" {
               }
               enum "less-than-equal" {
               }
             }
           }
           leaf choice-value {
             type string;
           }
           leaf ecmp {
             description "Number of equal cost multipath gateways";
             type union {
               type string {
                 pattern "<.*>|$.*";
               }
               type uint32 {
                 range "1 .. 512";
               }
             }
           }
           uses apply-advanced;
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf-list tag2 {
           ordered-by user;
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
         choice lsp-name-type {
           case case_1 {
             leaf lsp {
               description "Label switched path name";
               type string {
               }
             }
           }
           case case_2 {
             leaf lsp-regex {
               description "Label switched path name regular expression";
               type string {
               }
             }
           }
         }
         container source-routing-path {
           presence "enable source-routing-path";
           description "Spring-te lsp policy attributes";
           leaf name-regex {
             description "Spring-te lsp name regex";
             type string {
             }
           }
           leaf dest {
             description "Spring-te lsp IPV4/IPV6 destination without color";
             type jt:ipaddr;
           }
           leaf origin {
             description "Spring-te lsp origin address";
             type jt:ipaddr;
           }
           leaf tunnel-source {
             description "Spring-te lsp source protocol";
             type enumeration {
               enum "pcep" {
                 description "Spring-te lsp src pcep";
               }
               enum "bgp" {
                 description "Spring-te lsp src bgp";
               }
             }
           }
           leaf route-distinguisher {
             description "Spring-te lsp route distinguisher";
             type union {
               type uint32;
               type string {
                 pattern "<.*>|$.*";
               }
             }
           }
           leaf color {
             description "Spring-te lsp color";
             type union {
               type uint32;
               type string {
                 pattern "<.*>|$.*";
               }
             }
           }
         }
         list route-filter {
           key "address choice-ident choice-value";
           ordered-by user;
           description "List of routes to match";
           uses control_route_filter_type;
         }
         list source-address-filter {
           key "address choice-ident choice-value";
           ordered-by user;
           description "List of source addresses to match";
           uses control_source_address_filter_type;
         }
         list prefix-list {
           key name;
           ordered-by user;
           description "List of prefix-lists of routes to match";
           uses control_prefix_list_type;
         }
         list rib-list {
           key name;
           ordered-by user;
           description "List of routing-tables";
           uses control_rib_list_type;
         }
         list as-path-neighbors {
           key "list-type list-name";
           ordered-by user;
           description "List of peer AS to match";
           uses control_as_list_type;
         }
         list as-path-origins {
           key "list-type list-name";
           ordered-by user;
           description "List of originating AS to match";
           uses control_as_list_type;
         }
         list as-path-transits {
           key "list-type list-name";
           ordered-by user;
           description "List of originating AS to match";
           uses control_as_list_type;
         }
         list prefix-list-filter {
           key "list_name choice-ident choice-value";
           ordered-by user;
           description "List of prefix-list-filters to match";
           uses control_prefix_list_filter_type;
         }
         list rtf-prefix-list {
           key name;
           ordered-by user;
           description "List of rtf-prefix-lists of routes to match";
           uses control_rtf_prefix_list_type;
         }
         list route-filter-list {
           key name;
           ordered-by user;
           description "List of route-filter-lists of routes to match";
           uses control_route_filter_list_type;
         }
         list source-address-filter-list {
           key name;
           ordered-by user;
           description "List of source-address-filter-lists of routes to match";
           uses control_source_address_filter_list_type;
         }
         container multicast-scope {
           description "Multicast scope to match";
           choice scope-choice {
             case case_1 {
               leaf node-local {
                 description "Node-local scope";
                 type empty;
               }
             }
             case case_2 {
               leaf link-local {
                 description "Link-local scope";
                 type empty;
               }
             }
             case case_3 {
               leaf site-local {
                 description "Site-local scope";
                 type empty;
               }
             }
             case case_4 {
               leaf organization-local {
                 description "Organization-local scope";
                 type empty;
               }
             }
             case case_5 {
               leaf global {
                 description "Global scope";
                 type empty;
               }
             }
             case case_6 {
               leaf scope_value {
                 description "Scope value";
                 type union {
                   type string {
                     pattern "<.*>|$.*";
                   }
                   type uint32 {
                     range "0 .. 15";
                   }
                 }
               }
             }
           }
           choice scope-operator {
             case case_1 {
               leaf orhigher {
                 description "Match higher values";
                 type empty;
               }
             }
             case case_2 {
               leaf orlower {
                 description "Match lower values";
                 type empty;
               }
             }
           }
         }
         leaf aggregate-contributor {
           description "Match more specifics of an aggregate";
           type empty;
         }
         leaf state {
           description "Route state";
           type enumeration {
             enum "active" {
               description "Active route";
             }
             enum "inactive" {
               description "Inactive route";
             }
           }
         }
         leaf-list tunnel-type {
           ordered-by user;
           description "Tunnel type";
           type enumeration {
             enum "gre" {
               description "GRE tunnel";
             }
             enum "udp" {
               description "UDP tunnel";
             }
             enum "ipip" {
               description "IPIP tunnel";
             }
           }
         }
         leaf route-type {
           description "Route type";
           type enumeration {
             enum "internal" {
               description "Internal route";
             }
             enum "external" {
               description "External route";
             }
           }
         }
         leaf-list nlri-route-type {
           ordered-by user;
           description "Route type from NLRI";
           type union {
             type string {
               pattern "<.*>|$.*";
             }
             type uint32 {
               range "1 .. 10";
             }
           }
         }
         leaf-list evpn-tag {
           ordered-by user;
           description "Tag in EVPN Route";
           type union {
             type string {
               pattern "<.*>|$.*";
             }
             type uint32 {
               range "0 .. 4294967295";
             }
           }
         }
         leaf-list evpn-esi {
           ordered-by user;
           description "ESI in EVPN Route";
           type string;
         }
         list mac-filter-list {
           key name;
           ordered-by user;
           description "List of mac-filter-list macs to match";
           uses control_mac_address_filter_list_type;
         }
         leaf evpn-mac-route {
           description "EVPN Mac Route type";
           type enumeration {
             enum "mac-only" {
               description "MAC route";
             }
             enum "mac-ipv4" {
               description "MAC IPV4 route";
             }
             enum "mac-ipv6" {
               description "MAC IPV6 route";
             }
           }
         }
         leaf-list bridge-domain-id {
           ordered-by user;
           description "Bridge Domain Identifier (Vlan or VNI)";
           type union {
             type string {
               pattern "<.*>|$.*";
             }
             type uint32 {
               range "0 .. 4294967295";
             }
           }
         }
         leaf next-hop-type {
           description "Next-hop type";
           type enumeration {
             enum "merged" {
               description "Merged next hop";
             }
           }
         }
         leaf-list condition {
           ordered-by user;
           description "Condition to match on";
           type string;
         }
         list community-count {
           key name;
           ordered-by user;
           description "Number of BGP communities";
           uses community_count_type;
         }
         list large-community-count {
           key name;
           ordered-by user;
           description "Number of Large BGP communities";
           uses community_count_type;
         }
         list as-path-unique-count {
           key name;
           ordered-by user;
           description "Number of unique BGP ASes excluding confederations";
           uses as-path-unique-count-type;
         }
         list as-path-calc-length {
           key name;
           ordered-by user;
           description "Number of BGP ASes excluding confederations";
           uses as-path-calc-length-type;
         }
         container traffic-engineering {
           presence "enable traffic-engineering";
           description "Traffic-Engineering related parameters";
           uses apply-advanced;
           leaf-list protocol {
             ordered-by user;
             description "Protocol that originated the entry";
             type enumeration {
               enum "direct" {
                 description "Directly originated";
               }
               enum "ospf" {
                 description "OSPF originated";
               }
               enum "isis-level-1" {
                 description "ISIS level-1 originated";
               }
               enum "isis-level-2" {
                 description "ISIS level-2 originated";
               }
               enum "spring-te" {
                 description "SPRING-TE originated";
               }
               enum "static" {
                 description "Statically originated";
               }
               enum "unknown" {
                 description "Originated by unknown sources";
               }
             }
           }
           container node {
             presence "enable node";
             description "Node-related parameters";
             uses apply-advanced;
             leaf as {
               description "AS number";
               type string {
               }
             }
             leaf node-type {
               description "Real or pseudo-node";
               type enumeration {
                 enum "router" {
                   description "Real node";
                 }
                 enum "pseudo-node" {
                   description "Pseudo-node";
                 }
               }
             }
             leaf router-id {
               description "IP prefix to match the router-id against";
               type jt:ipprefix;
             }
             leaf sys-id {
               description "ISO address of the node";
               type jt:sysid;
             }
           }
           container ipv4-prefix {
             presence "enable ipv4-prefix";
             description "IPV4 prefix-related parameters";
             uses apply-advanced;
             leaf as {
               description "AS number";
               type string {
               }
             }
             leaf router-id {
               description "IP prefix to match the router-id against";
               type jt:ipprefix;
             }
             leaf prefix {
               description "IP prefix to match against";
               type jt:ipprefix;
             }
             leaf sys-id {
               description "ISO address of the node";
               type jt:sysid;
             }
           }
           container ipv6-prefix {
             presence "enable ipv6-prefix";
             description "IPV6 prefix related parameters";
             uses apply-advanced;
             leaf as {
               description "AS number";
               type string {
               }
             }
             leaf router-id {
               description "IPv6 prefix to match the router-id against";
               type jt:ipprefix;
             }
             leaf prefix {
               description "IPv6 prefix to match against";
               type jt:ipv6prefix;
             }
             leaf sys-id {
               description "ISO address of the node";
               type jt:sysid;
             }
           }
           container srv6-sid {
             presence "enable srv6-sid";
             description "SRV6 SID related parameters";
             uses apply-advanced;
             leaf as {
               description "AS number";
               type string {
               }
             }
             leaf router-id {
               description "SRv6 SID to match the router-id against";
               type jt:ipprefix;
             }
             leaf sid {
               description "SRv6 SID to match against";
               type jt:ipv6addr;
             }
             leaf sys-id {
               description "ISO address of the node";
               type jt:sysid;
             }
           }
           container spring-te {
             presence "enable spring-te";
             description "SPRING-TE policy related parameters";
             uses apply-advanced;
             leaf node-as {
               description "Node AS number";
               type string {
               }
             }
             leaf router-id {
               description "IP prefix to match against the node for the SPRING TE policy";
               type jt:ipprefix;
             }
             leaf color {
               description "Color of the SPRING-TE policy candidate path";
               type union {
                 type uint32;
                 type string {
                   pattern "<.*>|$.*";
                 }
               }
             }
             leaf discriminator {
               description "Discriminator of the SPRING-TE policy candidate path";
               type union {
                 type uint32;
                 type string {
                   pattern "<.*>|$.*";
                 }
               }
             }
             leaf endpoint {
               description "Endpoint of the SPRING-TE policy candidate path";
               type jt:ipaddr;
             }
             leaf protocol-origin {
               description "Protocol originating the SPRING-TE policy candidate path";
               type enumeration {
                 enum "bgp" {
                   description "SPRING-TE policy candidate path originated by BGP";
                 }
                 enum "cli" {
                   description "SPRING-TE policy candidate path originated by cli";
                 }
                 enum "pcep" {
                   description "SPRING-TE policy candidate path originated by PCEP";
                 }
               }
             }
             leaf origin-as {
               description "AS number of the node creating the SPRING-TE policy candidate path";
               type string {
               }
             }
             leaf origin-addr {
               description "Address of the node originating the SPRING-TE policy candidate path";
               type jt:ipaddr;
             }
           }
           container link {
             presence "enable link";
             description "Link-related parameters";
             uses apply-advanced;
             container from {
               description "Specify parameter of the 'from' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
             container to {
               description "Specify parameters of the 'to' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
           }
           leaf identifier {
             description "BGP-TE identifier";
             type union {
               type string {
                 pattern "<.*>|$.*";
               }
               type uint64 {
                 range "2 .. 18446744073709551615";
               }
             }
           }
         }
         leaf-list route-distinguisher {
           ordered-by user;
           description "Name of the route-distinguisher";
           type string;
         }
         leaf prefix-segment {
           description "Prefix segment present in route extended data";
           type empty;
         }
       }
       container to {
         description "Conditions to match the destination of a route";
         uses apply-advanced;
         leaf instance {
           description "Routing protocol instance";
           type string;
         }
         leaf instance-any {
           description "Any routing protocol instance";
           type empty;
         }
         leaf-list instance-list {
           description "A list of routing protocol instances";
           type string;
         }
         leaf-list igp-instance {
           description "IGP instance";
           type string;
         }
         leaf igp-instance-regex {
           description "IGP instance name regular expression";
           type jt:regular-expression;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
             enum "inet-srte" {
               description "IPv4 srtte family";
             }
             enum "inet6-srte" {
               description "IPv6 srte family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "express-segments" {
               description "Express-segment routes";
             }
             enum "rift" {
               description "RIFT routes";
             }
             enum "l2-learned-host-routing" {
               description "Layer2-learned host routes";
             }
             enum "srv6-isis" {
               description "SRV6 ISIS";
             }
             enum "ari-ts" {
               description "ARI TS routes";
             }
             enum "srv6" {
               description "Segment Routing IPv6 local route";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf bgp-srte-discriminator {
           description "Srte discriminator";
           type union {
             type uint32;
             type string {
               pattern "<.*>|$.*";
             }
           }
         }
         leaf srte-color {
           description "Srte color";
           type union {
             type uint32;
             type string {
               pattern "<.*>|$.*";
             }
           }
         }
         leaf programmed {
           description "API-programmed route";
           type empty;
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         container validation-database-instance {
           presence "enable validation-database-instance";
           description "Name to identify a validation-state with DB name";
           uses apply-advanced;
           leaf database-name {
             description "Route Validation Database name to be looked at";
             type string;
           }
           leaf state {
             description "Name to identify a validation-state";
             type enumeration {
               enum "valid" {
                 description "Match for valid database validation-state";
               }
               enum "invalid" {
                 description "Match for invalid database validation-state";
               }
               enum "unknown" {
                 description "Match for unknown database validation-state";
               }
             }
             mandatory true;
           }
         }
         list nexthop-weight {
           key "choice-ident choice-value weight";
           ordered-by user;
           description "Weight of the gateway";
           leaf choice-ident {
             type enumeration {
               enum "equal" {
               }
               enum "greater-than" {
               }
               enum "less-than" {
               }
               enum "greater-than-equal" {
               }
               enum "less-than-equal" {
               }
             }
           }
           leaf choice-value {
             type string;
           }
           leaf weight {
             description "Weight of the gateway";
             type union {
               type string {
                 pattern "<.*>|$.*";
               }
               type uint32 {
                 range "1 .. 65535";
               }
             }
           }
           uses apply-advanced;
           choice weight_type {
             case case_1 {
               leaf all-nexthop {
                 description "All the gateway weight should be matched";
                 type empty;
               }
             }
           }
         }
         list nexthop-ecmp {
           key "choice-ident choice-value ecmp";
           ordered-by user;
           description "Qualify nexthop equal cost multipath gateways";
           leaf choice-ident {
             type enumeration {
               enum "equal" {
               }
               enum "greater-than" {
               }
               enum "less-than" {
               }
               enum "greater-than-equal" {
               }
               enum "less-than-equal" {
               }
             }
           }
           leaf choice-value {
             type string;
           }
           leaf ecmp {
             description "Number of equal cost multipath gateways";
             type union {
               type string {
                 pattern "<.*>|$.*";
               }
               type uint32 {
                 range "1 .. 512";
               }
             }
           }
           uses apply-advanced;
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf-list tag2 {
           ordered-by user;
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
         choice lsp-name-type {
           case case_1 {
             leaf lsp {
               description "Label switched path name";
               type string {
               }
             }
           }
           case case_2 {
             leaf lsp-regex {
               description "Label switched path name regular expression";
               type string {
               }
             }
           }
         }
         container source-routing-path {
           presence "enable source-routing-path";
           description "Spring-te lsp policy attributes";
           leaf name-regex {
             description "Spring-te lsp name regex";
             type string {
             }
           }
           leaf dest {
             description "Spring-te lsp IPV4/IPV6 destination without color";
             type jt:ipaddr;
           }
           leaf origin {
             description "Spring-te lsp origin address";
             type jt:ipaddr;
           }
           leaf tunnel-source {
             description "Spring-te lsp source protocol";
             type enumeration {
               enum "pcep" {
                 description "Spring-te lsp src pcep";
               }
               enum "bgp" {
                 description "Spring-te lsp src bgp";
               }
             }
           }
           leaf route-distinguisher {
             description "Spring-te lsp route distinguisher";
             type union {
               type uint32;
               type string {
                 pattern "<.*>|$.*";
               }
             }
           }
           leaf color {
             description "Spring-te lsp color";
             type union {
               type uint32;
               type string {
                 pattern "<.*>|$.*";
               }
             }
           }
         }
       }
       container then {
         description "Actions to take if 'from' and 'to' conditions match";
         uses apply-advanced;
         container metric {
           description "Metric value";
           uses apply-advanced;
           choice metric_action {
             case case_1 {
               leaf metric {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
             case case_4 {
               container igp {
                 presence "enable igp";
                 description "Track the IGP metric (BGP only)";
                 leaf metric_offset {
                   description "Metric offset for MED";
                   type union {
                     type int32;
                     type string {
                       pattern "<.*>|$.*";
                     }
                   }
                 }
               }
             }
             case case_5 {
               container minimum-igp {
                 presence "enable minimum-igp";
                 description "Track the minimum IGP metric (BGP only)";
                 leaf metric_offset {
                   description "Metric offset for MED";
                   type union {
                     type int32;
                     type string {
                       pattern "<.*>|$.*";
                     }
                   }
                 }
               }
             }
             case case_6 {
               container expression {
                 description "Calculate value based on route metric and metric2";
                 uses metric_expression_type;
               }
             }
             case case_7 {
               leaf aigp {
                 description "Use aigp, if it exists, to set the IGP metric";
                 type empty;
               }
             }
             case case_8 {
               container effective-aigp {
                 presence "enable effective-aigp";
                 description "Track the effective AIGP metric (BGP only)";
                 leaf metric_offset {
                   description "Metric offset for MED";
                   type union {
                     type int32;
                     type string {
                       pattern "<.*>|$.*";
                     }
                   }
                 }
               }
             }
             case case_9 {
               container minimum-effective-aigp {
                 presence "enable minimum-effective-aigp";
                 description "Track the minimum effective AIGP metric (BGP only)";
                 leaf metric_offset {
                   description "Metric offset for MED";
                   type union {
                     type int32;
                     type string {
                       pattern "<.*>|$.*";
                     }
                   }
                 }
               }
             }
           }
         }
         container metric2 {
           description "Metric value 2";
           uses apply-advanced;
           choice metric_action {
             case case_1 {
               leaf metric2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric3 {
           description "Metric value 3";
           uses apply-advanced;
           choice metric_action {
             case case_1 {
               leaf metric3 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric4 {
           description "Metric value 4";
           uses apply-advanced;
           choice metric_action {
             case case_1 {
               leaf metric4 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag {
           description "Tag string";
           uses apply-advanced;
           choice metric_action {
             case case_1 {
               leaf tag {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag2 {
           description "Tag string 2";
           uses apply-advanced;
           choice metric_action {
             case case_1 {
               leaf tag2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference {
           description "Preference value";
           uses apply-advanced;
           choice metric_action {
             case case_1 {
               leaf preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference2 {
           description "Preference value 2";
           uses apply-advanced;
           choice metric_action {
             case case_1 {
               leaf preference2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color {
           description "Color (preference) value";
           uses apply-advanced;
           choice metric_action {
             case case_1 {
               leaf color {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color2 {
           description "Color (preference) value 2";
           uses apply-advanced;
           choice metric_action {
             case case_1 {
               leaf color2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container local-preference {
           description "Local preference associated with a route";
           uses apply-advanced;
           choice metric_action {
             case case_1 {
               leaf local-preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container credibility {
           description "TED credibility value for entries from BGP-TE";
           uses apply-advanced;
           choice metric_action {
             case case_1 {
               leaf credibility {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         leaf priority {
           description "Set priority for route installation";
           type enumeration {
             enum "high" {
               description "Set priority to high";
             }
             enum "medium" {
               description "Set priority to medium";
             }
             enum "low" {
               description "Set priority to low";
             }
           }
         }
         container prefix-segment {
           description "Set prefix segment attributes";
           uses apply-advanced;
           list algorithm {
             key name;
             description "Set prefix segment attributes for strict/flex algorithm ";
             max-elements 15;
             leaf name {
               description "Set prefix segment for strict/flex algorithm";
               type union {
                 type string {
                   pattern "<.*>|$.*";
                 }
                 type uint32 {
                   range "1 .. 255";
                 }
               }
               mandatory true;
             }
             leaf index {
               description "Set prefix segment index id";
               type union {
                 type string {
                   pattern "<.*>|$.*";
                 }
                 type uint32 {
                   range "0 .. 1048575";
                 }
               }
               mandatory true;
             }
             leaf node-segment {
               description "Set node segment flag for this prefix segment";
               type empty;
             }
           }
           leaf index {
             description "Set prefix segment index id";
             type union {
               type string {
                 pattern "<.*>|$.*";
               }
               type uint32 {
                 range "0 .. 1048575";
               }
             }
           }
           leaf node-segment {
             description "Set node segment flag for default prefix segment";
             type empty;
           }
           leaf redistribute {
             description "Redistribute prefix-segment from route entry";
             type empty;
           }
         }
         leaf label-allocation {
           description "Set label allocation mode";
           type enumeration {
             enum "per-table" {
               description "Set per-table label allocation mode";
             }
             enum "per-nexthop" {
               description "Set per-nexthop label allocation mode";
             }
             enum "per-table-localize" {
               description "Set per-table-localize label allocation mode";
             }
           }
         }
         container add-path {
           description "Set BGP add-path attributes";
           leaf send-count {
             description "Number of add-paths sent";
             type union {
               type string {
                 pattern "<.*>|$.*";
               }
               type uint32 {
                 range "2 .. 64";
               }
             }
           }
         }
         leaf fib-install-priority {
           description "Set Fib Instalation priority of a route";
           type enumeration {
             enum "high" {
               description "Set Fib install priority  to high";
             }
             enum "medium" {
               description "Set Fib install priority to medium ";
             }
           }
         }
         leaf validation-state {
           description "Set validation-state of a route";
           type enumeration {
             enum "valid" {
               description "Set validaton-state to valid";
             }
             enum "invalid" {
               description "Set validation-state to invalid";
             }
             enum "unknown" {
               description "Set validation-state to unknown";
             }
           }
         }
         leaf origin {
           description "BGP path origin";
           type enumeration {
             enum "igp" {
               description "Path originated in the local IGP";
             }
             enum "egp" {
               description "Path originated in another AS";
             }
             enum "incomplete" {
               description "Path was learned by some other means";
             }
           }
         }
         container srv6 {
           description "Configure SID with 128 bit address";
           leaf sid {
             description "IPv6 Address";
             type jt:ipv6addr;
           }
           leaf locator {
             description "Name of locator";
             type string;
           }
           choice locator_type {
             case case_1 {
               leaf micro-dt4-sid {
                 description "Micro SID type dt4";
                 type empty;
               }
             }
             case case_2 {
               leaf micro-dt6-sid {
                 description "Micro SID type dt6";
                 type empty;
               }
             }
             case case_3 {
               leaf micro-dt46-sid {
                 description "Micro SID type dt46";
                 type empty;
               }
             }
           }
         }
         container aigp-originate {
           presence "enable aigp-originate";
           description "Originate a BGP AIGP attribute";
           leaf distance {
             description "AIGP distance";
             type union {
               type uint32;
               type string {
                 pattern "<.*>|$.*";
               }
             }
           }
         }
         container aigp-adjust {
           description "Adjust a BGP AIGP attribute";
           choice math-op {
             case case_1 {
               leaf add {
                 type empty;
               }
             }
             case case_2 {
               leaf subtract {
                 type empty;
               }
             }
             case case_3 {
               leaf multiply {
                 type empty;
               }
             }
             case case_4 {
               leaf divide {
                 type empty;
               }
             }
           }
           choice adjust-value {
             case case_1 {
               leaf user-value {
                 description "Adjustment value";
                 type union {
                   type uint64;
                   type string {
                     pattern "<.*>|$.*";
                   }
                 }
               }
             }
             case case_2 {
               leaf distance-to-protocol-nexthop {
                 description "Metric2";
                 type empty;
               }
             }
           }
         }
         list community {
           key "choice-ident choice-value community-name";
           ordered-by user;
           description "BGP community properties associated with a route";
           leaf choice-ident {
             type enumeration {
               enum "equal-literal" {
               }
               enum "set" {
               }
               enum "plus-literal" {
               }
               enum "add" {
               }
               enum "minus-literal" {
               }
               enum "delete" {
               }
             }
           }
           leaf choice-value {
             type string;
           }
           leaf community-name {
             description "Name to identify a BGP community";
             type string;
           }
         }
         list tunnel-attribute {
           key "choice-ident choice-value tunnel-attribute-name";
           ordered-by user;
           description "BGP tunnel attribute associated with a route";
           leaf choice-ident {
             type enumeration {
               enum "set" {
               }
               enum "remove" {
               }
             }
           }
           leaf choice-value {
             type string;
           }
           leaf tunnel-attribute-name {
             description "Name of a tunnel attribute , or 'all'";
             type string;
           }
         }
         container assisted-replication {
           presence "enable assisted-replication";
           description "Deterministic AR replicator knobs";
           uses apply-advanced;
           leaf-list replicator-ip {
             description "Set deterministic AR replicator ip for the flow";
             type jt:ipaddr;
             max-elements 1;
           }
           leaf strict {
             description "Do not use any other replicator";
             type empty;
           }
           leaf-list fallback-replicator-ip {
             description "Set Fallback replicator-ip";
             type jt:ipaddr;
             max-elements 1;
           }
         }
         leaf damping {
           description "Define BGP route flap damping parameters";
           type string;
         }
         container aggregate-bandwidth {
           presence "enable aggregate-bandwidth";
           description "Advertise aggregate outbound link bandwidth";
           uses apply-advanced;
           choice transitive-type {
             case case_1 {
               leaf transitive {
                 description "Transitive flag for link bandwidth";
                 type empty;
               }
             }
             case case_2 {
               leaf non-transitive {
                 description "Non-Transitive flag for link bandwidth";
                 type empty;
               }
             }
           }
           leaf divide-equal {
             description "Divide-equal";
             type empty;
           }
         }
         container auto-link-bandwidth {
           presence "enable auto-link-bandwidth";
           description "Auto sense and attach link bandwidth community";
           uses apply-advanced;
           choice transitive-type {
             case case_1 {
               leaf transitive {
                 description "Transitive flag for link bandwidth";
                 type empty;
               }
             }
             case case_2 {
               leaf non-transitive {
                 description "Non-Transitive flag for link bandwidth";
                 type empty;
               }
             }
           }
         }
         leaf limit-bandwidth {
           description "Limit advertised aggregate outbound link bandwidth";
           type union {
             type uint64;
             type string {
               pattern "<.*>|$.*";
             }
           }
         }
         leaf no-entropy-label-capability {
           description "Don't advertise entropy label capability";
           type empty;
         }
         leaf as-path-prepend {
           description "Prepend AS numbers to an AS path (BGP only)";
           type string;
         }
         container as-path-expand {
           description "Prepend AS numbers prior to adding local-as (BGP only)";
           choice aspath_exp_value {
             case case_1 {
               container last-as {
                 presence "enable last-as";
                 description "Prepend last AS";
                 leaf count {
                   description "Repeat count";
                   type union {
                     type string {
                       pattern "<.*>|$.*";
                     }
                     type uint32 {
                       range "1 .. 32";
                     }
                   }
                 }
               }
             }
             case case_2 {
               leaf aspath {
                 description "AS path string";
                 type string;
               }
             }
           }
         }
         container next-hop {
           description "Set the address of the next-hop router";
           choice nexthop_value {
             case case_1 {
               leaf self {
                 description "Use a local address as the next-hop address";
                 type empty;
               }
             }
             case case_2 {
               leaf peer-address {
                 description "Use the remote peer address as the next-hop address";
                 type empty;
               }
             }
             case case_3 {
               leaf address {
                 description "Next-hop address";
                 type jt:ipaddr;
               }
             }
             case case_4 {
               leaf reject {
                 description "Use a reject next hop";
                 type empty;
               }
             }
             case case_5 {
               leaf discard {
                 description "Use a discard next hop";
                 type empty;
               }
             }
             case case_6 {
               leaf next-table {
                 description "Perform a forwarding lookup in the specified table";
                 type string;
               }
             }
           }
         }
         container install-nexthop {
           description "Choose the next hop to be used for forwarding";
           choice strict_type {
             case case_1 {
               leaf strict {
                 description "Do not use any other available next hops";
                 type empty;
               }
             }
             case case_2 {
               leaf strict-named-lsp {
                 description "Do not use any other non-lsp next hops";
                 type empty;
               }
             }
           }
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
             container fallback {
               description "Backup option";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
               }
               container except {
                 description "Do not choose to install matching next hops";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                 }
               }
             }
           }
           container fallback {
             description "Backup option ";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
             container except {
               description "Do not choose to install matching next hops";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
               }
             }
           }
         }
         leaf trace {
           description "Log matches to a trace file";
           type empty;
         }
         container external {
           presence "enable external";
           description "External route";
           uses apply-advanced;
           leaf type {
             description "OSPF external metric type";
             type union {
               type string {
                 pattern "<.*>|$.*";
               }
               type int32 {
                 range "1 .. 2";
               }
             }
           }
           leaf nssa-only {
             description "Clear P-bit on lsa type 7";
             type empty;
           }
         }
         container load-balance {
           description "Type of load balancing in forwarding table";
           choice load_balance_type {
             case case_1 {
               leaf per-packet {
                 description "Load balance on a per-packet basis deprecated, use per-flow instead";
                 type empty;
               }
             }
             case case_2 {
               leaf per-flow {
                 description "Load balance on a per-flow basis";
                 type empty;
               }
             }
             case case_3 {
             }
             case case_4 {
             }
             case case_5 {
             }
             case case_6 {
             }
             case case_7 {
             }
             case case_8 {
             }
             case case_9 {
             }
             case case_10 {
             }
             case case_11 {
             }
           }
         }
         container advertise-locator {
           presence "enable advertise-locator";
           description "Advertise SRv6 Locator";
           uses apply-advanced;
           leaf internal {
             description "Advertise locator as Interal route";
             type empty;
           }
         }
         leaf set-down-bit {
           description "Set down bit";
           type empty;
         }
         leaf analyze {
           description "Send to registered controllers for analysis";
           type empty;
         }
         leaf destination-class {
           description "Set destination class in forwarding table";
           type string;
         }
         leaf source-class {
           description "Set source class in forwarding table";
           type string;
         }
         leaf forwarding-class {
           description "Set source or destination class in forwarding table";
           type string;
         }
         container map-to-interface {
           description "Set output logical interface";
           choice map_to_interface_value {
             case case_1 {
               leaf self {
                 description "Map the interface to itself";
                 type empty;
               }
             }
             case case_2 {
               leaf interface {
                 description "Output logical interface";
                 type union {
                   type jt:interface-name;
                   type string {
                     pattern "<.*>|$.*";
                   }
                 }
               }
             }
           }
         }
         leaf-list ssm-source {
           ordered-by user;
           description "List of Sources for SSM mapping";
           type jt:ipaddr;
         }
         container p2mp-lsp-root {
           description "P2mp lsp root address";
           uses apply-advanced;
           leaf address {
             description "Ipv4 root address";
             type jt:ipv4addr;
           }
         }
         leaf dynamic-tunnel-attributes {
           description "Choose the dynamic tunnel attributes used for forwarding";
           type string;
         }
         leaf tunnel-end-point-address {
           description "Set tunnel end-point address of tunnel";
           type jt:ipaddr;
         }
         leaf selected-mldp-egress {
           description "This node should act as egress node for MLDP inband signalling";
           type empty;
         }
         leaf mhop-bfd-port {
           description "Use port number 4784 for MPLS-BFD as per RFC5884";
           type empty;
         }
         leaf no-backup {
           description "This prefix should not have backup";
           type empty;
         }
         leaf default-action {
           description "Set default policy action";
           type enumeration {
             enum "accept" {
               description "Accept a route";
             }
             enum "reject" {
               description "Reject a route";
             }
           }
         }
         leaf next {
           description "Skip to next policy or term";
           type enumeration {
             enum "policy" {
               description "Skip to next policy filter";
             }
             enum "term" {
               description "Skip to next term in a policy filter";
             }
           }
         }
         choice accept_reject {
           case case_1 {
             leaf accept {
               description "Accept a route";
               type empty;
             }
           }
           case case_2 {
             leaf reject {
               description "Reject a route";
               type empty;
             }
           }
         }
         container bgp-output-queue-priority {
           description "Set the BGP Update output queue priority.";
           choice class {
             case case_1 {
               leaf priority {
                 description "Output queue priority; higher is better";
                 type union {
                   type string {
                     pattern "<.*>|$.*";
                   }
                   type uint32 {
                     range "1 .. 16";
                   }
                 }
               }
             }
             case case_2 {
               leaf expedited {
                 description "Expedited queue; highest priority";
                 type empty;
               }
             }
           }
         }
         leaf multipath-resolve {
           description "Use all paths for resolution over this prefix";
           type empty;
         }
         leaf source-routing-path-template {
           description "Spring-te template to apply";
           type string {
           }
         }
         leaf label-allocation-fallback-reject {
           description "Suppress prefix export when label allocation fails";
           type empty;
         }
         leaf resolution-map {
           description "Set resolution map modes";
           type string;
         }
         leaf ignore-service-label {
           description "Ignore service labels";
           type empty;
         }
         container prefix-attribute-flags {
           presence "enable prefix-attribute-flags";
           description "Set ISIS prefix attribute flags sub TLV";
           uses apply-advanced;
           leaf node-segment-flag {
             description "Set node segment flag ";
             type empty;
           }
           leaf external-prefix-flag {
             description "Set external prefix flag ";
             type empty;
           }
           leaf anycast-flag {
             description "Set anycast flag ";
             type empty;
           }
           leaf entropy-label-capability-flag {
             description "Set entropy label capability flag ";
             type empty;
           }
         }
         container ipv4-source-router-id {
           presence "enable ipv4-source-router-id";
           description "Set IPv4 source router id in advertisement";
           uses apply-advanced;
           leaf router-id {
             description "Specify IPv4 address";
             type jt:ipaddr;
           }
         }
         container ipv6-source-router-id {
           presence "enable ipv6-source-router-id";
           description "Set IPv6 source router id in advertisement";
           uses apply-advanced;
           leaf router-id {
             description "Specify IPv6 address";
             type jt:ipv6addr;
           }
         }
         leaf request-long-lived-ack {
           description "Advertise route after forwarding is programmed";
           type empty;
         }
         leaf send-withdrawal-on-route-change {
           description "Withdraw route if change is not acked from forwarding";
           type empty;
         }
         container slice {
           description "Configure Policy Slice action";
           leaf slice-name {
             description "Slice Name";
             type string {
               length "1 .. 64";
             }
           }
         }
         leaf filter {
           description "Set firewall-filter name";
           type string {
           }
         }
         leaf strip-as-path {
           description "Remove the incoming BGP as-path and replace with local AS";
           type empty;
         }
         container request-acknowledgements {
           description "Set request acknowledgement";
           leaf nexthop-ack {
             description "Set nexthop acknowledgement ";
             type empty;
           }
           leaf route-ack {
             description "Set route acknowledgement ";
             type empty;
           }
         }
       }
     }
     list resolution-map {
       key name;
       ordered-by user;
       description "Define a set of PNH resolution modes";
       leaf name {
         description "Resolution Map name";
         type string;
       }
       uses apply-advanced;
       leaf-list mode {
         ordered-by user;
         description "List of resolution modes in order that defines fallback mechanism";
         type enumeration {
           enum "ip-color" {
             description "Colored-IP PNH Resolution Mode";
           }
           enum "color-only" {
             description "Color-only PNH Resolution Mode";
           }
         }
       }
     }
     list route-distinguisher {
       key name;
       description "Route-distinguisher information";
       leaf name {
         description "Name to identify route-distinguisher";
         type string;
       }
       uses apply-advanced;
       leaf-list members {
         ordered-by user;
         description "Route distinguisher string in ( *:X ) or ( Y:* ) or (X:Y) format";
         type string;
       }
     }
     list route-filter-list {
       key name;
       description "Define a named set of route-filter address prefixes";
       leaf name {
         description "Route filter list name";
         type string;
       }
       uses apply-advanced;
       list rf_list {
         key "address choice-ident choice-value";
         ordered-by user;
         uses route_filter_list_items;
       }
     }
     list rtf-prefix-list {
       key name;
       description "Define a named set of family route target prefixes";
       leaf name {
         description "RTF prefix list name";
         type string;
       }
       uses apply-advanced;
       list prefix-list {
         key name;
         uses rtf_prefix_list_items;
       }
     }
     list source-address-filter-list {
       key name;
       description "Define a named set of source address filter address prefixes";
       leaf name {
         description "Source address filter list name";
         type string;
       }
       uses apply-advanced;
       list saf_list {
         key "address choice-ident choice-value";
         ordered-by user;
         uses source_address_filter_list_items;
       }
     }
     list tunnel-attribute {
       key name;
       ordered-by user;
       description "BGP tunnel attributes definition";
       leaf name {
         description "Tunnel attribute name";
         type string {
         }
       }
       uses apply-advanced;
       leaf tunnel-type {
         description "Tunnel type";
         type enumeration {
           enum "ipip" {
             description "Tunnel type IP-IN-IP";
           }
           enum "udp" {
             description "Tunnel type X-IN-UDP";
           }
         }
         mandatory true;
       }
       leaf tunnel-color {
         description "Tunnel color";
         type union {
           type uint32;
           type string {
             pattern "<.*>|$.*";
           }
         }
       }
       leaf remote-end-point {
         description "Tunnel remote end point";
         type jt:ipaddr;
       }
     }
     list prefix-list {
       key name;
       description "Define a named set of address prefixes";
       leaf name {
         description "Prefix list name";
         type string;
       }
       uses apply-advanced;
       list prefix-list-item {
         key name;
         uses prefix_list_items;
       }
       leaf apply-path {
         description "Apply IP prefixes from a configuration statement";
         type string;
       }
     }
     list rib-list {
       key name;
       ordered-by user;
       description "Define a named set of RIB names or wildcards";
       leaf name {
         description "RIB list name";
         type string;
       }
       uses apply-advanced;
       list rib-list-item {
         key name;
         uses rib_list_items;
       }
     }
     list fast-lookup-tuple-list {
       key name;
       description "Define a named set of address prefixes";
       leaf name {
         description "Five tuple combination list name";
         type string;
       }
       uses apply-advanced;
       list fast_lookup_tuple_list_item {
         key name;
         uses fast_lookup_tuple_list_items;
       }
     }
     list as-list-group {
       key name;
       description "Group a set of as-list";
       leaf name {
         description "Name to identify AS list group";
         type string;
       }
       uses apply-advanced;
       list as-list {
         key name;
         description "BGP as range list information";
         leaf name {
           description "Name to identify BGP as-list";
           type string;
         }
         uses apply-advanced;
         leaf-list members {
           ordered-by user;
           description "Single autonomous system number or range of autonomous system numbers";
           type string;
         }
       }
     }
   }
   grouping as-path-calc-length-type {
     description "Calculated BGP AS_PATH length per BGP rules";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping as-path-unique-count-type {
     description "Number of unique BGP ASes excluding confederation ASes";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping community_count_type {
     description "Number of BGP communities";
     leaf name {
       description "Number of communities";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal	values";
           type empty;
         }
       }
       case case_3 {
         leaf orlower {
           description "Match lower or equal values";
           type empty;
         }
       }
     }
   }
   grouping control_as_list_type {
     leaf list-type {
       description "Type as-list or as-list-group";
       type enumeration {
         enum "as-list" {
           description " Type as-list";
         }
         enum "as-list-group" {
           description "Type as-list-group";
         }
       }
     }
     leaf list-name {
       description "Name of as-list or as-list-group";
       type string;
     }
     uses apply-advanced;
   }
   grouping control_mac_address_filter_list_type {
     leaf name {
       description "Name of mac-filter-list of macs to match";
       type string;
     }
     uses apply-advanced;
   }
   grouping control_prefix_list_filter_type {
     leaf list_name {
       description "Name of prefix-list of routes to match";
       type string;
     }
     leaf choice-ident {
       type enumeration {
         enum "exact" {
         }
         enum "longer" {
         }
         enum "orlonger" {
         }
       }
     }
     leaf choice-value {
       type string;
     }
     uses apply-advanced;
     leaf invert-match {
       description "Invert the result of the prefix-list-filter matching";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping control_prefix_list_type {
     leaf name {
       description "Name of prefix-list of routes to match";
       type string;
     }
     uses apply-advanced;
     leaf invert-match {
       description "Invert the result of the prefix-list matching";
       type empty;
     }
   }
   grouping control_rib_list_type {
     leaf name {
       description "Name of rib-list";
       type string;
     }
     uses apply-advanced;
   }
   grouping control_route_filter_list_type {
     leaf name {
       description "Name of route-filter-list of routes to match";
       type string;
     }
     uses apply-advanced;
     choice modifier {
       case case_1 {
         leaf exact {
           description "Exactly match the prefix length";
           type empty;
         }
       }
       case case_2 {
         leaf longer {
           description "Mask is greater than the prefix length";
           type empty;
         }
       }
       case case_3 {
         leaf orlonger {
           description "Mask is greater than or equal to the prefix length";
           type empty;
         }
       }
       case case_4 {
         leaf upto {
           description "Mask falls between two prefix lengths";
           type string {
           }
         }
       }
       case case_5 {
         leaf prefix-length-range {
           description "Mask falls between two prefix lengths";
           type string {
           }
         }
       }
     }
     leaf invert-match {
       description "Invert the result of the route-filter-list matching";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping control_route_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     leaf get-route-range {
       description "Get the range";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping control_rtf_prefix_list_type {
     description "RTF prefix list";
     leaf name {
       description "Name of rtf-prefix-list of routes to match";
       type string;
     }
     uses apply-advanced;
   }
   grouping control_source_address_filter_list_type {
     leaf name {
       description "Name of source-address-filter-list of routes to match";
       type string;
     }
     uses apply-advanced;
   }
   grouping control_source_address_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping fast_lookup_tuple_list_items {
     leaf name {
       description "As <destination-address>:<source-address>:<proto>:<src-port>:<dest-port>";
       type string {
       }
     }
     uses apply-advanced;
   }
   grouping juniper-protocols {
     uses apply-advanced;
     container bfd {
       description "Bidirectional Forwarding Detection (BFD) options";
       uses apply-advanced;
       container traceoptions {
         description "Trace options for BFD";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "adjacency" {
                 description "Trace adjacency messages";
               }
               enum "event" {
                 description "Trace all events";
               }
               enum "error" {
                 description "Trace all errors";
               }
               enum "rtsock" {
                 description "Trace all rtscok messages";
               }
               enum "packet" {
                 description "Trace all packets";
               }
               enum "ppm-packet" {
                 description "Trace packet activity by periodic packet management";
               }
               enum "pipe" {
                 description "Trace pipe messages";
               }
               enum "pipe-detail" {
                 description "Trace pipe messages in detail";
               }
               enum "state" {
                 description "Trace state transitions";
               }
               enum "timer" {
                 description "Trace timer processing";
               }
               enum "nsr-synchronization" {
                 description "Trace NSR synchronization events";
               }
               enum "nsr-packet" {
                 description "Trace packet activity of NSR";
               }
               enum "issu" {
                 description "Trace ISSU packet activity";
               }
               enum "slow-start" {
                 description "Trace slow-start activity";
               }
               enum "session" {
                 description "Per session activity";
               }
               enum "all" {
                 description "Trace everything";
               }
             }
           }
         }
       }
       leaf mhop-inline-disable {
         description "Disable Inline mode for Multi Hop BFD sessions";
         type empty;
       }
       leaf no-issu-timer-negotiation {
         description "Disable ISSU timer negotiation";
         type empty;
       }
       container sbfd {
         description "Seamless BFD parameters";
         uses apply-advanced;
         leaf-list pool {
           description "List of seamless BFD endpoints";
           type union {
             type uint32;
             type string {
               pattern "<.*>|$.*";
             }
           }
         }
         list local-discriminator {
           key name;
           ordered-by user;
           description "Local discriminator for seamless BFD responder";
           leaf name {
             description "Local discriminator for seamless BFD responder";
             type union {
               type string {
                 pattern "<.*>|$.*";
               }
               type uint32 {
                 range "1 .. 4294967295";
               }
             }
           }
           uses apply-advanced;
           leaf minimum-receive-interval {
             description "Minimum receive interval for seamless BFD responder";
             units "milliseconds";
             type union {
               type string {
                 pattern "<.*>|$.*";
               }
               type uint32 {
                 range "10 .. 255000";
               }
             }
           }
           leaf local-ip-address {
             description "IPv4 source address";
             type jt:ipv4addr;
           }
           leaf local-ipv6-address {
             description "IPv6 source address";
             type jt:ipv6addr;
           }
         }
         list local-discriminator-ip {
           key name;
           ordered-by user;
           description "Local discriminator IP address for sBFD responder";
           leaf name {
             description "Local discriminator IP address for sBFD responder";
             type jt:ipv4addr;
           }
           uses apply-advanced;
           leaf minimum-receive-interval {
             description "Minimum receive interval for seamless BFD responder";
             units "milliseconds";
             type union {
               type string {
                 pattern "<.*>|$.*";
               }
               type uint32 {
                 range "10 .. 255000";
               }
             }
           }
           leaf local-ip-address {
             description "IPv4 source address";
             type jt:ipv4addr;
           }
         }
       }
     }
     container bgp {
       description "BGP options";
       uses juniper-protocols-bgp;
     }
     container vrrp {
       description "VRRP options";
       uses apply-advanced;
       leaf version-3 {
         description "VRRPv3 conformance";
         type empty;
       }
     }
     container evpn {
       description "Configuration EVPN default routing instance";
       uses apply-advanced;
       container traceoptions {
         description "Trace options for Layer 2 VPNs";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 VPN, VPLS and EVPN topology changes";
               }
               enum "nlri" {
                 description "Trace Layer 2 VPN, VPLS and EVPN remote site advertisements";
               }
               enum "connections" {
                 description "Trace Layer 2 VPN and VPLS connections";
               }
               enum "automatic-site" {
                 description "Trace VPLS automatic site state";
               }
               enum "oam" {
                 description "Trace OAM messages";
               }
               enum "mac-database" {
                 description "Trace MAC route database in a EVPN instance";
               }
               enum "nsr" {
                 description "Trace NSR in a EVPN instance";
               }
               enum "egress-protection" {
                 description "Trace Edge Protection messages";
               }
               enum "instance" {
                 description "Evpn instance related messages";
               }
               enum "interface" {
                 description "Interface related messages";
               }
               enum "l2aldsync" {
                 description "Messages related to EVPN-L2ALD communication";
               }
               enum "p2mp" {
                 description "P2MP messages";
               }
               enum "esi" {
                 description "Evpn ethernet segment related messages";
               }
               enum "mcsn" {
                 description "Evpn multicast snooping related messages";
               }
               enum "vpws" {
                 description "VPWS messages";
               }
               enum "irb" {
                 description "Integrated routing bridging messages";
               }
               enum "ar" {
                 description "Assisted-replication messages";
               }
               enum "etree" {
                 description "Evpn etree messages";
               }
               enum "kernel" {
                 description "Messages related to rpd-kernel communication";
               }
               enum "bd" {
                 description "Evpn bridge domain messages";
               }
               enum "pbb" {
                 description "Evpn provider backbone bridging messages";
               }
               enum "infra" {
                 description "Messages related to infrastructure in evpn";
               }
               enum "pfxdb" {
                 description "Type-5 related messages";
               }
               enum "peg-df" {
                 description "PIM EVPN Gateway DF-Election related messages";
               }
               enum "gbptagdb" {
                 description "Trace message related to gbptagdb";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf mac-history {
         description "Number of history entries to be maitained per mac";
         type union {
           type string {
             pattern "<.*>|$.*";
           }
           type uint16 {
             range "0 .. 255";
           }
         }
       }
       leaf peg-df-election-history {
         description "Number of DF Election history entries to be maintained per PEG BD";
         type union {
           type string {
             pattern "<.*>|$.*";
           }
           type uint16 {
             range "0 .. 255";
           }
         }
       }
       leaf oism-core-route-history {
         description "Number of history entries to be maintained per OISM Core Route";
         type union {
           type string {
             pattern "<.*>|$.*";
           }
           type uint16 {
             range "0 .. 255";
           }
         }
       }
       leaf interface-history {
         description "Number of history entries to be maintained per EVPN interface";
         type union {
           type string {
             pattern "<.*>|$.*";
           }
           type uint16 {
             range "0 .. 255";
           }
         }
       }
       leaf core-isolation-delay-response {
         description "Delay core-isolation response (seconds)";
         type union {
           type string {
             pattern "<.*>|$.*";
           }
           type uint32 {
             range "0 .. 255";
           }
         }
       }
       leaf mac-ip-limit {
         description "Maximum number of IPs that can be learned on a MAC, default is 200";
         type union {
           type string {
             pattern "<.*>|$.*";
           }
           type uint32 {
             range "1 .. 5000";
           }
         }
       }
       list mac-list {
         key name;
         description "Configure MAC lists";
         leaf name {
           description "List name";
           type string {
             length "1 .. 128";
           }
         }
         uses apply-advanced;
         leaf-list mac-address {
           description "MAC address";
           type jt:mac-addr;
         }
       }
       container mac-mobility {
         description "MAC mobility settings";
         uses apply-advanced;
         leaf no-sequence-numbers {
           description "Don't use sequence numbers for MAC mobility";
           type empty;
         }
       }
       leaf no-core-isolation {
         description "Disable EVPN Core isolation";
         type empty;
       }
       leaf leave-sync-route-oldstyle {
         description "Originate leave sync route oldstyle";
         type empty;
       }
       leaf-list interconnect-multihoming-peer-gateways {
         description "Configure multihoming peer gateway VTEP IPv4 addresses";
         type jt:ipaddr;
         max-elements 64;
       }
       leaf-list interconnect-multihoming-peer-v6-gateways {
         description "Configure multihoming peer gateway VTEP IPv6 addresses";
         type jt:ipv6addr;
         max-elements 64;
       }
       leaf advertise-evpn-esi-routes {
         description "Advertise AD/ES routes considering instance ifl status";
         type empty;
       }
       leaf-list static-multihoming-peer {
         description "Configure static multihoming peer VTEP IPv4 addresses";
         type jt:ipaddr;
         max-elements 64;
       }
       leaf-list static-multihoming-peer-v6 {
         description "Configure static multihoming peer VTEP IPv6 addresses";
         type jt:ipv6addr;
         max-elements 64;
       }
       container node-detection {
         presence "enable node-detection";
         description "Node detection";
         uses apply-advanced;
         leaf next-hop {
           description "Next-hop identifier to which to map";
           type union {
             type jt:interface-unit;
             type string {
               pattern "<.*>|$.*";
             }
           }
         }
         leaf action {
           description "Isolation action";
           type enumeration {
             enum "laser-off" {
               description "Will trigger laser-off on core-isolation";
             }
             enum "trigger-node-isolation" {
               description "Will trigger link-down on core-isolation";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           leaf neighbor {
             description "BFD neighbor address";
             type jt:ipaddr;
           }
         }
       }
     }
     container router-advertisement {
       description "IPv6 router advertisement options";
       uses apply-advanced;
       container traceoptions {
         description "Trace options for router advertisement";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
         }
       }
       list interface {
         key name;
         ordered-by user;
         description "Interfaces on which to configure router advertisement";
         leaf name {
           type string;
         }
         uses apply-advanced;
       }
     }
     container router-discovery {
       description "ICMP router discovery options";
       uses juniper-protocols-router-discovery;
     }
     container isis {
       description "IS-IS options";
       uses juniper-protocols-isis;
     }
     list isis-instance {
       key name;
       ordered-by user;
       description "Multi-instance IS-IS configuration";
       leaf name {
         description "IS-IS instance name";
         type string;
       }
       leaf link-state-instance-id {
         description "Link State Instance Identifier";
         type union {
           type string {
             pattern "<.*>|$.*";
           }
           type uint64 {
             range "1 .. 65535";
           }
         }
       }
       uses apply-advanced;
       list interface {
         key name;
         description "Interface configuration";
         leaf name {
           description "Interface name";
           type union {
             type jt:interface-name;
             type string {
               pattern "<.*>|$.*";
             }
           }
         }
         uses apply-advanced;
         container ldp-synchronization {
           description "Advertise maximum metric until LDP is operational";
           presence "enable ldp-synchronization";
           uses ldp-sync-obj;
         }
         list level {
           key name;
           ordered-by user;
           description "Configure levels on this interface";
           leaf name {
             description "IS-IS level number";
             type union {
               type string {
                 pattern "<.*>|$.*";
               }
               type uint32 {
                 range "1 .. 2";
               }
             }
           }
           uses apply-advanced;
           leaf te-metric {
             description "Traffic engineering metric";
             type union {
               type string {
                 pattern "<.*>|$.*";
               }
               type uint32 {
                 range "0 .. 16777215";
               }
             }
           }
           leaf no-advertise-adjacency-segment {
             description "Do not advertise an adjacency segment for this level";
             type empty;
           }
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srv6-adjacency-segment {
             description "Configure srv6 adjacency segment";
             uses apply-advanced;
             container unprotected {
               presence "enable unprotected";
               description "SRv6 Adjacency segment is uneligible for protection";
               uses apply-advanced;
               list locator {
                 key name;
                 ordered-by user;
                 description "Locator to bind SRv6 adjacency segment";
                 leaf name {
                   description "Locator name";
                   type string;
                   mandatory true;
                 }
                 uses apply-advanced;
                 list end-x-sid {
                   key name;
                   ordered-by user;
                   description "Endpoint 128 bit address";
                   leaf name {
                     type jt:ipv6addr;
                   }
                   uses apply-advanced;
                 }
                 container micro-adjacency-sid {
                   presence "enable micro-adjacency-sid";
                   description "Micro-adjacency-SID";
                   uses apply-advanced;
                   leaf static-sid {
                     description "Static micro-adjacency-SID";
                     type union {
                       type uint32;
                       type string {
                         pattern "<.*>|$.*";
                       }
                     }
                   }
                 }
                 container dynamic-end-x-sid {
                   presence "enable dynamic-end-x-sid";
                   description "Allocate end-x-SID dynamically";
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
           list lan-neighbor {
             key name;
             ordered-by user;
             description "Configuration specific to a LAN neighbor";
             leaf name {
               description "Neighbor's sysid";
               type jt:sysid;
             }
             uses apply-advanced;
             container ipv4-adjacency-segment {
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container ipv6-adjacency-segment {
               description "Configure ipv6 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container srv6-adjacency-segment {
               description "Configure srv6 adjacency segment";
               uses apply-advanced;
               container unprotected {
                 presence "enable unprotected";
                 description "SRv6 Adjacency segment is uneligible for protection";
                 uses apply-advanced;
                 list locator {
                   key name;
                   ordered-by user;
                   description "Locator to bind SRv6 adjacency segment";
                   leaf name {
                     description "Locator name";
                     type string;
                     mandatory true;
                   }
                   uses apply-advanced;
                   list end-x-sid {
                     key name;
                     ordered-by user;
                     description "Endpoint 128 bit address";
                     leaf name {
                       type jt:ipv6addr;
                     }
                     uses apply-advanced;
                     container flavor {
                       presence "enable flavor";
                       description "Configure end-x-SID flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                   container micro-adjacency-sid {
                     presence "enable micro-adjacency-sid";
                     description "Micro-adjacency-SID";
                     uses apply-advanced;
                     leaf static-sid {
                       description "Static micro-adjacency-SID";
                       type union {
                         type uint32;
                         type string {
                           pattern "<.*>|$.*";
                         }
                       }
                     }
                   }
                   container dynamic-end-x-sid {
                     presence "enable dynamic-end-x-sid";
                     description "Allocate end-x-SID dynamically";
                     uses apply-advanced;
                     container flavor {
                       presence "enable flavor";
                       description "Configure end-x-SID flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                 }
               }
             }
           }
           container post-convergence-lfa {
             presence "enable post-convergence-lfa";
             description "Configure backup along post convergence on this interface";
             uses apply-advanced;
           }
           choice enable-disable {
             case case_1 {
               leaf disable {
                 description "Disable IS-IS for this level";
                 type empty;
               }
             }
           }
           leaf metric {
             description "Metric for this level";
             type union {
               type string {
                 pattern "<.*>|$.*";
               }
               type uint32 {
                 range "0 .. 16777215";
               }
             }
           }
           leaf ipv4-multicast-metric {
             description "IPv4 multicast metric for this level";
             type union {
               type string {
                 pattern "<.*>|$.*";
               }
               type uint32 {
                 range "0 .. 16777215";
               }
             }
           }
           leaf ipv6-unicast-metric {
             description "IPv6 unicast metric for this level";
             type union {
               type string {
                 pattern "<.*>|$.*";
               }
               type uint32 {
                 range "0 .. 16777215";
               }
             }
           }
           leaf ipv6-multicast-metric {
             description "IPv6 multicast metric for this level";
             type union {
               type string {
                 pattern "<.*>|$.*";
               }
               type uint32 {
                 range "0 .. 16777215";
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                   mandatory true;
                 }
               }
             }
           }
           leaf authentication-key {
             description "Authentication key (password)";
             status deprecated;
             type jt:unreadable;
           }
           leaf authentication-type {
             description "Authentication type";
             status deprecated;
             type enumeration {
               enum "md5" {
                 description "MD5 authentication";
                 status deprecated;
               }
               enum "simple" {
                 description "Simple password authentication";
                 status deprecated;
               }
             }
           }
           leaf hello-authentication-key {
             description "Authentication key (password) for hello packets";
             type jt:unreadable;
           }
           leaf hello-authentication-type {
             description "Authentication type for hello packets";
             type enumeration {
               enum "md5" {
                 description "MD5 authentication";
               }
               enum "simple" {
                 description "Simple password authentication";
               }
             }
           }
           leaf hello-authentication-key-chain {
             description "Key chain name";
             type string {
               length "1 .. 128";
             }
           }
           leaf hello-interval {
             description "Interval between hello packet transmissions";
             units "seconds";
             type union {
               type string {
                 pattern "<.*>|$.*";
               }
               type uint32 {
                 range "1 .. 21845";
               }
             }
           }
           leaf hold-time {
             description "Time after which neighbors think the interface is down";
             units "seconds";
             type union {
               type string {
                 pattern "<.*>|$.*";
               }
               type uint32 {
                 range "1 .. 65535";
               }
             }
           }
           leaf priority {
             description "Designated router election priority";
             type union {
               type string {
                 pattern "<.*>|$.*";
               }
               type uint32 {
                 range "0 .. 127";
               }
             }
           }
           container flood-reflector {
             presence "enable flood-reflector";
             description "Configure interface as flood-reflector";
             uses apply-advanced;
             leaf cluster-id {
               description "Cluster-ID";
               type union {
                 type string {
                   pattern "<.*>|$.*";
                 }
                 type uint32 {
                   range "1 .. 4294967295";
                 }
               }
             }
           }
           container passive {
             presence "enable passive";
             description "Do not run IS-IS at this level, but advertise it";
             uses apply-advanced;
             leaf remote-node-iso {
               description "ISO System-ID of the remote node";
               type jt:sysid;
             }
             leaf remote-node-id {
               description "Remote address of the link";
               type jt:ipv4addr;
             }
           }
           leaf strict-bfd-old {
             description "Enable strict bfd over this interface";
             type empty;
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container normalize {
             description "Normalize Measured Link Delay";
             leaf interval {
               description "The value of the normalized interval in microseconds.";
               units "microseconds";
               type union {
                 type string {
                   pattern "<.*>|$.*";
                 }
                 type uint32 {
                   range "1 .. 5000000";
                 }
               }
               mandatory true;
             }
             leaf offset {
               description "The value of the normalized offset in microseconds (Must be < normalized interval).";
               units "microseconds";
               type union {
                 type string {
                   pattern "<.*>|$.*";
                 }
                 type uint32 {
                   range "1 .. 5000000";
                 }
               }
               mandatory true;
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         leaf no-advertise-adjacency-segment {
           description "Do not advertise an adjacency segment for this interface";
           type empty;
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible for backup traffic from protected interfaces";
           type empty;
         }
         leaf no-eligible-remote-backup {
           description "Not eligible for Remote-LFA backup traffic from protected interfaces";
           type empty;
         }
         container link-degradation-threshold {
           presence "enable link-degradation-threshold";
           description "Link up and down thresholds (in %) for proactive link protection";
           leaf link-down {
             description "Signal degradation threshold above which link marked down";
             type union {
               type string {
                 pattern "<.*>|$.*";
               }
               type uint32 {
                 range "0 .. 100";
               }
             }
             mandatory true;
           }
           leaf link-up {
             description "Signal degradation threshold below which link is marked up.";
             type union {
               type string {
                 pattern "<.*>|$.*";
               }
               type uint32 {
                 range "0 .. 100";
               }
             }
             mandatory true;
           }
         }
         choice enable-disable {
           case case_1 {
             leaf disable {
               description "Disable IS-IS on this interface";
               type empty;
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf flood-group {
           description "ISO Area that this interface should send LSPs to";
           type string {
           }
         }
         leaf hello-authentication-key {
           description "Authentication key (password) for hello packets";
           status deprecated;
           type jt:unreadable;
         }
         leaf hello-authentication-type {
           description "Authentication type for hello packets";
           status deprecated;
           type enumeration {
             enum "md5" {
               description "MD5 authentication";
               status deprecated;
             }
             enum "simple" {
               description "Simple password authentication";
               status deprecated;
             }
           }
         }
         leaf hello-padding-type {
           description "Type of padding for hello packets";
           default "loose";
           type enumeration {
             enum "strict" {
               description "Padding for all adjacency states";
             }
             enum "adaptive" {
               description "Padding until state of neighbor adjacency is 'up'";
             }
             enum "loose" {
               description "Padding until state of adjacency is 'initializing'";
             }
             enum "disable" {
               description "Do not add any padding for hello packets";
             }
           }
         }
         leaf interface-group-holddown-delay {
           description "Time to wait before including in BBM calculation";
           units "seconds";
           type union {
             type string {
               pattern "<.*>|$.*";
             }
             type uint32 {
               range "0 .. 60";
             }
           }
         }
         leaf max-hello-size {
           description "Maximum size allowed for ISIS Hello PDUs";
           type union {
             type string {
               pattern "<.*>|$.*";
             }
             type uint32 {
               range "512 .. 16000";
             }
           }
         }
         leaf lsp-interval {
           description "Interval between LSP transmissions";
           default "100";
           units "milliseconds";
           type union {
             type string {
               pattern "<.*>|$.*";
             }
             type uint32 {
               range "1 .. 1000";
             }
           }
         }
         container csnp-interval {
           description "Rate of CSN packets (for LAN interfaces only)";
           choice csnp_interval_option {
             case case_1 {
               leaf csnp-interval-number {
                 description "Interval between CSN packets";
                 units "seconds";
                 type union {
                   type string {
                     pattern "<.*>|$.*";
                   }
                   type uint32 {
                     range "1 .. 65535";
                   }
                 }
               }
             }
             case case_2 {
               leaf disable {
                 description "Do not send CSN packets on this interface";
                 type empty;
               }
             }
           }
         }
         container strict-dual-isis {
           presence "enable strict-dual-isis";
           description "Enable dual isis if spf computation is required for both ipv4 and ipv6 family";
           uses apply-advanced;
           leaf holdown {
             description "Time to wait for ipv4 and ipv6 connectivity";
             status deprecated;
             default "12";
             type union {
               type string {
                 pattern "<.*>|$.*";
               }
               type uint32 {
                 range "1 .. 65535";
               }
             }
           }
           leaf holddown {
             description "Time to wait for ipv4 and ipv6 connectivity";
             default "12";
             type union {
               type string {
                 pattern "<.*>|$.*";
               }
               type uint32 {
                 range "1 .. 65535";
               }
             }
           }
         }
         container mesh-group {
           description "Add the interface to a mesh group";
           choice mesh_group_option {
             case case_1 {
               leaf mesh-group-number {
                 description "Mesh group number for this interface";
                 type union {
                   type uint32;
                   type string {
                     pattern "<.*>|$.*";
                   }
                 }
               }
             }
             case case_2 {
               leaf blocked {
                 description "Do not flood new LSPs on this interface";
                 type empty;
               }
             }
           }
         }
         leaf point-to-point {
           description "Treat interface as point to point";
           type empty;
         }
         container passive {
           presence "enable passive";
           description "Do not run IS-IS, but advertise it";
           uses apply-advanced;
           leaf remote-node-iso {
             description "ISO System-ID of the remote node";
             type jt:sysid;
           }
           leaf remote-node-id {
             description "Remote address of the link";
             type jt:ipv4addr;
           }
         }
         leaf checksum {
           description "Enable checksum for packets on this interface";
           type empty;
         }
         leaf no-unicast-topology {
           description "Do not include this interface in the unicast topology";
           type empty;
         }
         leaf no-ipv4-multicast {
           description "Do not include this interface in the IPv4 multicast topology";
           type empty;
         }
         leaf no-ipv6-unicast {
           description "Do not include this interface in the IPv6 unicast topology";
           type empty;
         }
         leaf no-ipv6-multicast {
           description "Do not include this interface in the IPv6 multicast topology";
           type empty;
         }
         leaf no-adjacency-down-notification {
           description "Do not inform other protocols about adjacency down events";
           type empty;
         }
         container bfd-liveness-detection {
           description "Bidirectional Forwarding Detection options";
           status deprecated;
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
         list family {
           key name;
           ordered-by user;
           description "Address family specific interface attributes";
           leaf name {
             type enumeration {
               enum "inet" {
                 description "IPv4 family";
               }
               enum "inet6" {
                 description "IPv6 family";
               }
             }
           }
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             leaf holddown-interval {
               description "Time to hold the session-UP notification to the client";
               units "milliseconds";
               type union {
                 type string {
                   pattern "<.*>|$.*";
                 }
                 type uint32 {
                   range "0 .. 255000";
                 }
               }
             }
           }
         }
         leaf strict-bfd {
           description "Enable strict bfd over this interface";
           type empty;
         }
       }
       list bier-sub-domain {
         key name;
         description "Configuration of bier subdomain";
         leaf name {
           description "Enable bier subdomain id";
           type union {
             type uint8;
             type string {
               pattern "<.*>|$.*";
             }
           }
         }
       }
       container prefix-unreachable {
         presence "enable prefix-unreachable";
         description "Configure unreachable prefix advertisement parameters";
         uses apply-advanced;
         container originator {
           description "Parameters for originating unreachable prefix advertisements";
           uses apply-advanced;
           leaf unplanned-lifetime {
             description "Lifetime of unplanned UPA";
             units "seconds";
             type union {
               type string {
                 pattern "<.*>|$.*";
               }
               type uint32 {
                 range "30 .. 65535";
               }
             }
           }
           leaf metric {
             description "Metric value of unplanned UPA";
             type union {
               type string {
                 pattern "<.*>|$.*";
               }
               type uint32 {
                 range "4261412865 .. 4294967295";
               }
             }
           }
           leaf max-advertisements {
             description "Maximum UPAs that can be originated at any point of time";
             type union {
               type string {
                 pattern "<.*>|$.*";
               }
               type uint32 {
                 range "1 .. 10000";
               }
             }
           }
         }
         leaf use-only-for-leaking {
           description "Do not use this UPA route for resolution";
           type empty;
         }
       }
       container source-packet-routing {
         presence "enable source-packet-routing";
         description "Enable Source Packet Routing (SPRING)";
         uses apply-advanced;
         container adjacency-segment {
           description "Configure attributes for Adjacency Segments in SPRING";
           uses apply-advanced;
           leaf hold-time {
             description "Duration(ms) for which adjacency segments will be retained after isolating from an interface";
             type union {
               type string {
                 pattern "<.*>|$.*";
               }
               type uint32 {
                 range "180000 .. 900000";
               }
             }
           }
         }
         container udp-tunneling {
           description "Enable SR over UDP feature";
           uses apply-advanced;
           leaf encapsulation {
             description "Enable UDP Tunnel Encapsulation";
             type empty;
           }
           leaf decapsulation {
             description "Enable UDP Tunnel decapsulation";
             type empty;
           }
         }
         container srgb {
           description "Set the SRGB global block in SPRING";
           leaf start-label {
             description "Start range for SRGB label block";
             type union {
               type string {
                 pattern "<.*>|$.*";
               }
               type uint32 {
                 range "16 .. 1048575";
               }
             }
             //mandatory true;
           }
           leaf index-range {
             description "Index to the SRGB start label block";
             type union {
               type string {
                 pattern "<.*>|$.*";
               }
               type uint32 {
                 range "32 .. 1048559";
               }
             }
             //mandatory true;
           }
         }
         container node-segment {
           description "Enable support for Node segments in SPRING";
           uses apply-advanced;
           leaf ipv4-index {
             description "Set IPv4 Node Segment index";
             type union {
               type string {
                 pattern "<.*>|$.*";
               }
               type uint32 {
                 range "0 .. 1048575";
               }
             }
           }
           leaf ipv6-index {
             description "Set IPv6 Node Segment index";
             type union {
               type string {
                 pattern "<.*>|$.*";
               }
               type uint32 {
                 range "0 .. 1048575";
               }
             }
           }
           leaf index-range {
             description "Set Range of Node Segment indices allowed";
             type union {
               type string {
                 pattern "<.*>|$.*";
               }
               type uint32 {
                 range "32 .. 16385";
               }
             }
           }
         }
         leaf-list flex-algorithm {
           description "Flex-algorithms we would like to participate in";
           type union {
             type string {
               pattern "<.*>|$.*";
             }
             type uint32 {
               range "128 .. 255";
             }
           }
           max-elements 16;
         }
         leaf use-flex-algorithm-metric-always {
           description "Use flex-algo prefix metric whenever available";
           type empty;
         }
         leaf strict-asla-based-flex-algorithm {
           description "Flex-Algorithm to ignore links not having ASLA sub-TLVs";
           type empty;
         }
         leaf new-capability-subtlv {
           description "Advertise all ranges in single spring capability subtlv";
           type empty;
         }
         leaf explicit-null {
           description "Set E and P bits in all Prefix SID advertisements";
           type empty;
         }
         leaf mapping-server {
           description "Mapping server name";
           type string;
         }
         leaf no-strict-spf {
           description " Disable strict spf algo 1 advertisement";
           type empty;
         }
         leaf no-binding-sid-leaking {
           description " Disable SRMS binding sid leaking";
           type empty;
         }
         leaf ldp-stitching {
           description "Enable SR to LDP stitching";
           type empty;
         }
         leaf entropy-label {
           description " Enable entropy label";
           type empty;
         }
         container srv6 {
           presence "enable srv6";
           description "Enable IPv6 Segment Routing (SRv6)";
           uses apply-advanced;
           list locator {
             key name;
             ordered-by user;
             description "SRv6 Locator";
             leaf name {
               description "Locator name";
               type string;
               mandatory true;
             }
             uses apply-advanced;
             leaf anycast {
               description "Set A flag in the Prefix-Attribute sub-TLV";
               type empty;
             }
             list end-sid {
               key name;
               ordered-by user;
               leaf name {
                 type jt:ipv6addr;
               }
               uses apply-advanced;
             }
             container dynamic-end-sid {
               presence "enable dynamic-end-sid";
               description "Allocate end SID dynamically";
               uses apply-advanced;
               container flavor {
                 presence "enable flavor";
                 description "Configure end-SID flavor";
                 uses apply-advanced;
                 leaf psp {
                   description "Penultimate segment pop of the SRH";
                   type empty;
                 }
                 leaf usp {
                   description "Ultimate segment pop of the SRH";
                   type empty;
                 }
                 leaf usd {
                   description "Ultimate segment decapsulation";
                   type empty;
                 }
               }
             }
             leaf micro-node-sid {
               description "Program and advertise micro-node-SID";
               type empty;
             }
           }
         }
       }
       list level {
         key name;
         ordered-by user;
         description "Configure global level attributes";
         leaf name {
           description "IS-IS level number";
           type union {
             type string {
               pattern "<.*>|$.*";
             }
             type uint32 {
               range "1 .. 2";
             }
           }
         }
         uses apply-advanced;
         leaf labeled-preference {
           description "Preference of labeled IS-IS routes";
           type union {
             type uint32;
             type string {
               pattern "<.*>|$.*";
             }
           }
         }
         leaf srv6-preference {
           description "Preference of SRV6 IS-IS routes";
           type union {
             type uint32;
             type string {
               pattern "<.*>|$.*";
             }
           }
         }
         leaf flex-algorithm-preference {
           description "Preference of flex-algorithm L-ISIS routes";
           type union {
             type uint32;
             type string {
               pattern "<.*>|$.*";
             }
           }
         }
         container source-packet-routing {
           presence "enable source-packet-routing";
           description "Enable Source Packet Routing (SPRING)";
           uses apply-advanced;
           choice enable-disable {
             case case_1 {
               leaf disable {
                 description "Disable Source Packet Routing on this level";
                 type empty;
               }
             }
           }
           leaf srms-preference {
             description "Set SRMS preference value";
             type union {
               type string {
                 pattern "<.*>|$.*";
               }
               type uint32 {
                 range "0 .. 255";
               }
             }
           }
         }
         choice enable-disable {
           case case_1 {
             leaf disable {
               description "Disable IS-IS on this level";
               type empty;
             }
           }
         }
         leaf authentication-key {
           description "Authentication key (password)";
           type jt:unreadable;
         }
         leaf authentication-type {
           description "Authentication type";
           type enumeration {
             enum "md5" {
               description "MD5 authentication";
             }
             enum "simple" {
               description "Simple password authentication";
             }
           }
         }
         leaf purge-originator {
           description "Add Purge Originator information";
           type enumeration {
             enum "self" {
               description "Add POI only for self-originated purge LSPs";
             }
             enum "empty" {
               description "Add POI for purge LSPs who do not have POI information";
             }
           }
         }
         leaf no-hello-authentication {
           description "Disable authentication for hello packets";
           type empty;
         }
         leaf no-csnp-authentication {
           description "Disable authentication for CSN packets";
           type empty;
         }
         leaf no-psnp-authentication {
           description "Disable authentication for PSN packets";
           type empty;
         }
         leaf no-lsp-authentication {
           description "Disable authentication for LSP packets";
           type empty;
         }
         leaf authentication-key-chain {
           description "Key chain name";
           type string {
             length "1 .. 128";
           }
         }
         leaf wide-metrics-only {
           description "Generate wide metrics only";
           type empty;
         }
         leaf preference {
           description "Preference of internal routes";
           type union {
             type uint32;
             type string {
               pattern "<.*>|$.*";
             }
           }
         }
         leaf external-preference {
           description "Preference of external routes";
           type union {
             type uint32;
             type string {
               pattern "<.*>|$.*";
             }
           }
         }
         leaf prefix-export-limit {
           description "Maximum number of external prefixes that can be exported";
           type union {
             type string {
               pattern "<.*>|$.*";
             }
             type uint32 {
               range "0 .. 4294967295";
             }
           }
         }
         leaf max-lsp-size {
           description "Maximum size allowed for LSPs";
           type union {
             type string {
               pattern "<.*>|$.*";
             }
             type uint32 {
               range "512 .. 9192";
             }
           }
         }
         container flood-reflector {
           description "Enable flood-reflector";
           uses apply-advanced;
           choice flood-reflector-choice {
             case case_1 {
               container reflector {
                 description "Configure this as a flood-reflector";
                 uses apply-advanced;
                 leaf cluster-id {
                   description "Cluster-ID";
                   type union {
                     type string {
                       pattern "<.*>|$.*";
                     }
                     type uint32 {
                       range "1 .. 4294967295";
                     }
                   }
                   mandatory true;
                 }
               }
             }
             case case_2 {
               leaf client {
                 description "Configure interface as flood-reflector client";
                 type empty;
               }
             }
           }
         }
       }
       list interface-group {
         key name;
         description "Interface grouping configuration";
         leaf name {
           description "Interface group name";
           type string;
         }
         uses apply-advanced;
         list level {
           key name;
           ordered-by user;
           description "Configure levels on this interface-group";
           leaf name {
             description "IS-IS level number";
             type union {
               type string {
                 pattern "<.*>|$.*";
               }
               type uint32 {
                 range "1 .. 2";
               }
             }
           }
           uses apply-advanced;
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                   mandatory true;
                 }
               }
             }
           }
         }
         container link-group-protection {
           description "Configure link group protection";
           uses apply-advanced;
           leaf minimum-bandwidth {
             description "Minimum bandwidth to carry traffic";
             type string;
           }
           leaf revert-bandwidth {
             description "Revert bandwidth to carry traffic";
             type string;
           }
         }
         list interface {
           key name;
           description "List interfaces for this group";
           leaf name {
             description "Interface name";
             type union {
               type jt:interface-name;
               type string {
                 pattern "<.*>|$.*";
               }
             }
           }
           uses apply-advanced;
           leaf weight {
             description "Interface weight for adjacency set";
             type union {
               type string {
                 pattern "<.*>|$.*";
               }
               type uint32 {
                 range "1 .. 255";
               }
             }
           }
         }
       }
       container spf-options {
         description "Configure SPF attributes";
         uses apply-advanced;
         container microloop-avoidance {
           description "Configure microloop avoidance mechanisms";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Set maximum number of label supported for Micro-Loop-Avoidance calculations";
               type union {
                 type string {
                   pattern "<.*>|$.*";
                 }
                 type uint32 {
                   range "2 .. 8";
                 }
               }
             }
             leaf maximum-srv6-sids {
               description "Set maximum number of SRV6 SIDs supported for Micro-Loop-Avoidance calculations";
               type union {
                 type string {
                   pattern "<.*>|$.*";
                 }
                 type uint32 {
                   range "2 .. 12";
                 }
               }
             }
           }
         }
         leaf delay {
           description "Time to wait before running an SPF";
           units "milliseconds";
           type union {
             type string {
               pattern "<.*>|$.*";
             }
             type uint32 {
               range "50 .. 1000";
             }
           }
         }
         leaf holddown {
           description "Time to hold down before running an SPF";
           units "milliseconds";
           type union {
             type string {
               pattern "<.*>|$.*";
             }
             type uint32 {
               range "1000 .. 10000";
             }
           }
         }
         leaf rapid-runs {
           description "Number of rapid SPF runs before SPF holddown";
           type union {
             type string {
               pattern "<.*>|$.*";
             }
             type uint32 {
               range "1 .. 5";
             }
           }
         }
         container multipath {
           description "Configure multipath options";
           uses apply-advanced;
           container weighted {
             description "Weighted multipath options";
             uses apply-advanced;
             leaf one-hop {
               description "Enable load balancing on onehop multipath based on interface bandwidth";
               type empty;
             }
           }
         }
       }
       container traceoptions {
         description "Trace options for IS-IS";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "post-convergence-lfa" {
                 description "Trace post-convergence-lfa related events";
               }
               enum "error" {
                 description "Trace errored packets";
               }
               enum "spf" {
                 description "Trace SPF events";
               }
               enum "packets" {
                 description "Trace IS-IS packets";
               }
               enum "hello" {
                 description "Trace hello packets";
               }
               enum "lsp" {
                 description "Trace link-state packets";
               }
               enum "psn" {
                 description "Trace partial sequence number (PSN) packets";
               }
               enum "csn" {
                 description "Trace complete sequence number (CSN) packets";
               }
               enum "layer2-map" {
                 description "Trace ARP/ND kernel state manipulation";
               }
               enum "lsp-generation" {
                 description "Trace LSP generation";
               }
               enum "graceful-restart" {
                 description "Trace graceful restart events";
               }
               enum "ldp-synchronization" {
                 description "Trace synchronization between IS-IS and LDP";
               }
               enum "nsr-synchronization" {
                 description "Trace NSR synchronization events";
               }
               enum "spring" {
                 description "Trace source packet routing";
               }
               enum "prefix-sid" {
                 description "Trace source packet routing, prefix-sids";
               }
               enum "flex-algorithm" {
                 description "Trace flex-algorithm related events";
               }
               enum "adj-sid" {
                 description "Trace adj-sid related events";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "srv6" {
                 description "Trace srv6 related events";
               }
               enum "rmopd" {
                 description "Trace rmopd interactions";
               }
               enum "mapping-server" {
                 description "Trace mapping server related events";
               }
               enum "prefix-unreachable" {
                 description "Trace unreachable prefix advertisement related events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container backup-spf-options {
         description "Configure backup SPF attributes";
         uses apply-advanced;
         container remote-backup-calculation {
           presence "enable remote-backup-calculation";
           description "Calculate Remote LFA backup nexthops";
           uses apply-advanced;
         }
         container use-post-convergence-lfa {
           presence "enable use-post-convergence-lfa";
           description "Calculate Post Convergence Backup Nexthops";
           uses apply-advanced;
           leaf maximum-labels {
             description "Set maximum number of label supported for post convergence path calculations";
             type union {
               type string {
                 pattern "<.*>|$.*";
               }
               type uint32 {
                 range "2 .. 8";
               }
             }
           }
           leaf maximum-srv6-sids {
             description "Set maximum number of SRV6 SIDs for post convergence path calculations";
             type union {
               type string {
                 pattern "<.*>|$.*";
               }
               type uint32 {
                 range "2 .. 12";
               }
             }
           }
         }
         container use-source-packet-routing {
           presence "enable use-source-packet-routing";
           description "Use SPRING routed paths for protection";
           uses apply-advanced;
         }
         leaf per-prefix-calculation {
           description "Calculate backup nexthops for non-best prefix originators";
           type empty;
         }
         leaf node-link-degradation {
           description "Degrade to link protection when nodelink protection not available";
           type empty;
         }
       }
       list context-identifier {
         key name;
         ordered-by user;
         description "Configuration for advertisement of a context-identifier ";
         leaf name {
           description "Context identifier range";
           type jt:ipprefix;
         }
         uses apply-advanced;
         list level {
           key name;
           ordered-by user;
           description "Configure global level attributes";
           leaf name {
             description "IS-IS level number";
             type union {
               type string {
                 pattern "<.*>|$.*";
               }
               type uint32 {
                 range "1 .. 2";
               }
             }
           }
           uses apply-advanced;
           choice enable-disable {
             case case_1 {
               leaf disable {
                 description "Disable advertisements to this level";
                 type empty;
               }
             }
           }
         }
       }
       choice enable-disable {
         case case_1 {
           leaf disable {
             description "Disable IS-IS";
             type empty;
           }
         }
       }
       leaf-list export {
         ordered-by user;
         description "Export policy";
         type jt:policy-algebra;
       }
       leaf-list import {
         ordered-by user;
         description "Import policy";
         type jt:policy-algebra;
       }
       leaf reference-bandwidth {
         description "Bandwidth for calculating metric defaults";
         type string;
       }
       leaf job-stats {
         description "Collect job statistics";
         type empty;
       }
       leaf lsp-lifetime {
         description "Lifetime of LSPs";
         units "seconds";
         type union {
           type string {
             pattern "<.*>|$.*";
           }
           type uint32 {
             range "350 .. 65535";
           }
         }
       }
       leaf max-lsp-size {
         description "Maximum size allowed for LSPs";
         default "1492";
         type union {
           type string {
             pattern "<.*>|$.*";
           }
           type uint32 {
             range "512 .. 9192";
           }
         }
       }
       leaf max-hello-size {
         description "Maximum size allowed for ISIS Hello PDUs";
         default "1492";
         type union {
           type string {
             pattern "<.*>|$.*";
           }
           type uint32 {
             range "512 .. 16000";
           }
         }
       }
       leaf max-snp-size {
         description "Maximum size allowed for Sequence Number (Complete/Partial) PDUs";
         default "1400";
         type union {
           type string {
             pattern "<.*>|$.*";
           }
           type uint32 {
             range "512 .. 1400";
           }
         }
       }
       leaf spf-delay {
         description "Time to wait before running an SPF";
         status deprecated;
         units "milliseconds";
         type union {
           type string {
             pattern "<.*>|$.*";
           }
           type uint32 {
             range "50 .. 120000";
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf loose-authentication-check {
         description "Verify authentication only if PDU has authentication TLV";
         type empty;
       }
       leaf max-areas {
         description "Maximum number of advertised Areas";
         default "3";
         type union {
           type string {
             pattern "<.*>|$.*";
           }
           type uint32 {
             range "3 .. 64";
           }
         }
       }
       leaf no-authentication-check {
         description "Disable authentication checking";
         type empty;
       }
       leaf no-ipv4-routing {
         description "Disable IPv4 routing";
         type empty;
       }
       leaf no-ipv6-routing {
         description "Disable IPv6 routing";
         type empty;
       }
       leaf no-adjacency-holddown {
         description "Disable adjacency hold down";
         type empty;
       }
       leaf multicast-topology {
         description "Enable multicast topology";
         status deprecated;
         type empty;
       }
       leaf ignore-attached-bit {
         description "Ignore the attached bit in Level 1 LSPs";
         type empty;
       }
       container rib-group {
         description "Routing table group for importing IS-IS routes";
         uses rib_group_type;
       }
       container no-external-export {
         description "No external export";
         uses apply-advanced;
         list protocol {
           key name;
           ordered-by user;
           description "Protocol parameters";
           leaf name {
             type enumeration {
               enum "bgp" {
                 description "BGP";
               }
               enum "ospf" {
                 description "OSPF";
               }
               enum "isis" {
                 description "ISIS";
               }
               enum "l-isis" {
                 description "Labelled ISIS";
               }
               enum "l-ospf" {
                 description "Labelled OSPF";
               }
               enum "static" {
                 description "Static";
               }
             }
           }
         }
       }
       container strict-dual-isis {
         presence "enable strict-dual-isis";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container topologies {
         description "Enable topologies";
         uses apply-advanced;
         leaf ipv4-multicast {
           description "Enable IPv4-multicast topology";
           type empty;
         }
         leaf ipv6-unicast {
           description "Enable IPv6-unicast topology";
           type empty;
         }
         leaf ipv6-multicast {
           description "Enable IPv6-multicast topology";
           type empty;
         }
       }
       container overload {
         presence "enable overload";
         description "Set the overload bit (no transit traffic)";
         uses apply-advanced;
         leaf timeout {
           description "Time after which overload bit is reset";
           units "seconds";
           type union {
             type string {
               pattern "<.*>|$.*";
             }
             type uint32 {
               range "60 .. 3600";
             }
           }
         }
         leaf advertise-high-metrics {
           description "Advertise high metrics instead of setting the overload bit";
           type empty;
         }
         leaf allow-route-leaking {
           description "Allow routes to be leaked when overload is configured";
           type empty;
         }
         leaf internal-prefixes {
           description "Allow internal prefixes to be advertised with high metric";
           type empty;
         }
         leaf external-prefixes {
           description "Allow external prefixes to be advertised with high metric";
           type empty;
         }
       }
       container dynamic-overload {
         description "Set the dynamic overload options";
         uses apply-advanced;
         leaf no-overload-on-prefix-export-limit {
           description "Do not set overload bit when prefix export limit is reached";
           type empty;
         }
         leaf auto-recovery {
           description "Enable Auto recovery to recover from dynamic overload state";
           type empty;
         }
       }
       container graceful-restart {
         description "IS-IS graceful restart options";
         choice enable-disable {
           case case_1 {
             leaf disable {
               description "Disable graceful restart";
               type empty;
             }
           }
         }
         leaf helper-disable {
           description "Disable graceful restart helper capability";
           type empty;
         }
         leaf restart-duration {
           description "Maximum time for graceful restart to finish";
           units "seconds";
           type union {
             type string {
               pattern "<.*>|$.*";
             }
             type uint32 {
               range "30 .. 300";
             }
           }
         }
       }
       list net {
         key name;
         description "Assign Network Entity Title (NET) configuration";
         leaf name {
           description "Assign Network Entity Title (NET) address to an IS-IS router";
           type jt:isoaddr;
         }
       }
       leaf rfc7775-compliance {
         description "RFC 7775 compliance for up/down bit and prefix attribute sub-tlv";
         type empty;
       }
     }
     container l2circuit {
       description "Configuration for Layer 2 circuits over MPLS";
       uses apply-advanced;
       container traceoptions {
         description "Trace options for Layer 2 circuits";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 circuit topology changes";
               }
               enum "fec" {
                 description "Trace Layer 2 circuit VC FEC advertisements";
               }
               enum "connections" {
                 description "Trace Layer 2 circuit connections";
               }
               enum "oam" {
                 description "Trace Layer 2 circuit OAM messages";
               }
               enum "egress-protection" {
                 description "Trace Layer 2 circuit egress protection messages";
               }
               enum "auto-sensing" {
                 description "Trace Layer 2 circuit PW auto-sensing";
               }
               enum "sdb" {
                 description "Trace SDB";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list neighbor {
         key name;
         ordered-by user;
         description "List of Layer 2 circuits to this neighbor";
         leaf name {
           description "Neighbor ID";
           type jt:ipv4addr;
         }
         uses apply-advanced;
         list interface {
           key name;
           ordered-by user;
           description "Interface forming the Layer 2 circuit";
           leaf name {
             description "Interface name";
             type union {
               type jt:interface-name;
               type string {
                 pattern "<.*>|$.*";
               }
             }
           }
           uses apply-advanced;
           container static {
             presence "enable static";
             description "Configuration of static Pseudowire";
             uses apply-advanced;
             leaf incoming-label {
               description "Layer 2 circuit incoming static label";
               type union {
                 type string {
                   pattern "<.*>|$.*";
                 }
                 type uint32 {
                   range "16 .. 1048575";
                 }
               }
               mandatory true;
             }
             leaf outgoing-label {
               description "Layer 2 circuit outgoing static label";
               type union {
                 type string {
                   pattern "<.*>|$.*";
                 }
                 type uint32 {
                   range "16 .. 1048575";
                 }
               }
               mandatory true;
             }
             leaf send-oam {
               description "Turn on sending of l2ckt ping";
               type empty;
             }
           }
           leaf psn-tunnel-endpoint {
             description "Endpoint of the transport tunnel on the remote PE";
             type jt:ipv4addr;
           }
           leaf protect-interface {
             description "Name of protect interface";
             type union {
               type jt:interface-name;
               type string {
                 pattern "<.*>|$.*";
               }
             }
           }
           leaf virtual-circuit-id {
             description "Identifier for this Layer 2 circuit";
             type union {
               type string {
                 pattern "<.*>|$.*";
               }
               type uint32 {
                 range "1 .. 4294967295";
               }
             }
             mandatory true;
           }
           leaf description {
             description "Text description of Layer 2 circuit";
             type string;
           }
           choice control-word-choice {
             leaf control-word {
               description "Add control word to the Layer 2 encapsulation";
               type empty;
             }
             leaf no-control-word {
               description "Don't add control word to the Layer 2 encapsulation";
               type empty;
             }
           }
           leaf community {
             description "Community associated with this Layer 2 circuit";
             type string;
           }
           leaf mtu {
             description "MTU to be advertised for this Layer 2 circuit";
             type union {
               type string {
                 pattern "<.*>|$.*";
               }
               type uint32 {
                 range "512 .. 65535";
               }
             }
           }
           leaf ignore-encapsulation-mismatch {
             description "Allow different encapsulation types on local and remote end";
             type empty;
           }
           leaf ignore-mtu-mismatch {
             description "Allow different MTUs on interfaces";
             type empty;
           }
           leaf send-ip-addr-list-tlv {
             description "Send IP ADDR LIST TLV to remote side";
             type empty;
           }
           container pseudowire-status-tlv {
             presence "enable pseudowire-status-tlv";
             description "Send pseudowire status TLV";
             uses apply-advanced;
             leaf hot-standby-vc-on {
               description "Activate pseudowire upon arrival of 'hot-standby' status TLV message";
               type empty;
             }
           }
           leaf switchover-delay {
             description "Layer 2 circuit switchover delay";
             default "10000";
             units "milliseconds";
             type union {
               type string {
                 pattern "<.*>|$.*";
               }
               type uint32 {
                 range "0 .. 180000";
               }
             }
           }
           container revert-time {
             presence "enable revert-time";
             description "Enable pseudowire redundancy reversion";
             leaf delay {
               description "Reversion timer (seconds)";
               units "seconds";
               type union {
                 type string {
                   pattern "<.*>|$.*";
                 }
                 type uint32 {
                   range "0 .. 3600";
                 }
               }
               mandatory true;
             }
             leaf maximum {
               description "Maximum reversion interval to add over revert-time delay";
               units "seconds";
               type union {
                 type string {
                   pattern "<.*>|$.*";
                 }
                 type uint32 {
                   range "0 .. 7200";
                 }
               }
             }
           }
           list backup-neighbor {
             key name;
             ordered-by user;
             description "Configuration of redundant l2circuit";
             leaf name {
               description "Neighbor ID";
               type jt:ipv4addr;
             }
             uses apply-advanced;
             container static {
               presence "enable static";
               description "Configuration of static Pseudowire";
               uses apply-advanced;
               leaf incoming-label {
                 description "Layer 2 circuit incoming static label";
                 type union {
                   type string {
                     pattern "<.*>|$.*";
                   }
                   type uint32 {
                     range "16 .. 1048575";
                   }
                 }
                 mandatory true;
               }
               leaf outgoing-label {
                 description "Layer 2 circuit outgoing static label";
                 type union {
                   type string {
                     pattern "<.*>|$.*";
                   }
                   type uint32 {
                     range "16 .. 1048575";
                   }
                 }
                 mandatory true;
               }
             }
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               type string;
             }
             leaf psn-tunnel-endpoint {
               description "Endpoint of the transport tunnel on the remote PE";
               type jt:ipv4addr;
             }
             leaf standby {
               description "Keep backup pseudowire in continuous standby";
               type empty;
             }
             leaf hot-standby {
               description "Keep backup pseudowire in continuous standby mode and ready for traffic forwarding";
               type empty;
             }
           }
         }
       }
       container local-switching {
         description "Configuration of Layer 2 circuits local switching";
         uses apply-advanced;
         list interface {
           key name;
           ordered-by user;
           description "Interface forming the local Layer 2 circuit";
           leaf name {
             description "Interface name";
             type union {
               type jt:interface-name;
               type string {
                 pattern "<.*>|$.*";
               }
             }
           }
           uses apply-advanced;
           leaf no-revert {
             description "Do not revert to primary-interface";
             type empty;
           }
           leaf protect-interface {
             description "Name of protect interface";
             type union {
               type jt:interface-name;
               type string {
                 pattern "<.*>|$.*";
               }
             }
           }
           leaf connection-protection {
             description "End-2-end protection via OAM failure detection";
             type empty;
           }
           list neighbor {
             key name;
             ordered-by user;
             description "Configuration of Layer 2 circuit";
             leaf name {
               description "Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
               mandatory true;
             }
             leaf community {
               description "Community associated with this Layer 2 circuit";
               type string;
             }
             leaf psn-tunnel-endpoint {
               description "Endpoint of the transport tunnel on the neighbor PE";
               type jt:ipv4addr;
             }
             leaf mtu {
               description "MTU to be advertised for this Layer 2 circuit";
               type union {
                 type string {
                   pattern "<.*>|$.*";
                 }
                 type uint32 {
                   range "512 .. 65535";
                 }
               }
             }
           }
           list backup-neighbor {
             key name;
             ordered-by user;
             description "Configuration of redundant l2circuit";
             leaf name {
               description "Backup Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
               mandatory true;
             }
             leaf psn-tunnel-endpoint {
               description "Endpoint of the transport tunnel on the backup neighbor PE";
               type jt:ipv4addr;
             }
             leaf community {
               description "Community associated with this Layer 2 circuit";
               type string;
             }
             leaf mtu {
               description "MTU to be advertised for this Layer 2 circuit";
               type union {
                 type string {
                   pattern "<.*>|$.*";
                 }
                 type uint32 {
                   range "512 .. 65535";
                 }
               }
             }
           }
           container end-interface {
             description "Interface name of the other end point";
             uses apply-advanced;
             leaf interface {
               description "Interface name";
               type union {
                 type jt:interface-name;
                 type string {
                   pattern "<.*>|$.*";
                 }
               }
             }
             leaf no-revert {
               description "Do not revert to primary-interface";
               type empty;
             }
             leaf protect-interface {
               description "Name of protect interface";
               type union {
                 type jt:interface-name;
                 type string {
                   pattern "<.*>|$.*";
                 }
               }
             }
             leaf backup-interface {
               description "Name of backup interface";
               type union {
                 type jt:interface-name;
                 type string {
                   pattern "<.*>|$.*";
                 }
               }
             }
           }
           leaf description {
             description "Text description of Layer 2 circuit";
             type string;
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
         }
       }
     }
     container l2vpn {
       description "Configuration for Layer 2 VPN circuits over MPLS";
       uses apply-advanced;
       container resolution {
         description "Configuration of PW nexthop resolution";
         uses apply-advanced;
         leaf preserve-nexthop-hierarchy {
           description "Install expanded hierarchy";
           type empty;
         }
       }
     }
     container ldp {
       description "LDP options";
       uses juniper-protocols-ldp;
     }
     container mpls {
       description "Multiprotocol Label Switching options";
       uses juniper-protocols-mpls;
     }
     container ospf {
       description "OSPF configuration";
       uses juniper-protocols-ospf;
     }
     list ospf-instance {
       key name;
       ordered-by user;
       description "Multi-instance OSPF configuration";
       leaf name {
         description "OSPF instance name";
         type string;
       }
       uses apply-advanced;
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           type string;
         }
         container spf-options {
           description "Configure options for SPF";
           uses apply-advanced;
           container microloop-avoidance {
             description "Configure microloop avoidance mechanism";
             uses apply-advanced;
             container post-convergence-path {
               presence "enable post-convergence-path";
               description "Temporarily install post-convergence path for routes potentially affected by microloops";
               uses apply-advanced;
               leaf delay {
                 description "Time after which temporary post-convergence paths are removed";
                 units "milliseconds";
                 type union {
                   type string {
                     pattern "<.*>|$.*";
                   }
                   type uint32 {
                     range "500 .. 60000";
                   }
                 }
               }
               leaf maximum-labels {
                 description "Maximum number of labels installed for post-convergence paths";
                 type union {
                   type string {
                     pattern "<.*>|$.*";
                   }
                   type uint32 {
                     range "2 .. 8";
                   }
                 }
               }
             }
           }
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
           container multipath {
             description "Configure multipath options";
             uses apply-advanced;
             container weighted {
               description "Weighted multipath options";
               uses apply-advanced;
               leaf one-hop {
                 description "Enable load balancing on onehop multipath based on interface bandwidth";
                 type empty;
               }
             }
           }
         }
         container backup-spf-options {
           description "Configure options for backup SPF";
           uses apply-advanced;
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 8";
                 }
               }
             }
             leaf maximum-backup-paths {
               description "Maximum number of equal-cost post-convergence paths installed";
               type union {
                 type string {
                   pattern "<.*>|$.*";
                 }
                 type uint32 {
                   range "1 .. 8";
                 }
               }
             }
           }
           leaf use-source-packet-routing {
             description "Use spring backup paths for inet.0 routes";
             type empty;
           }
           leaf disable {
             description "Do not run backup SPF";
             type empty;
           }
           leaf no-install {
             description "Do not install backup nexthops into the RIB";
             type empty;
           }
           leaf downstream-paths-only {
             description "Use only downstream backup paths";
             type empty;
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
         }
         leaf prefix-export-limit {
           description "Maximum number of prefixes that can be exported";
           type union {
             type string {
               pattern "<.*>|$.*";
             }
             type uint32 {
               range "0 .. 4294967295";
             }
           }
         }
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       container source-packet-routing {
         presence "enable source-packet-routing";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 199999";
               }
             }
           }
           leaf index-range {
             description "Set range of node segment indices allowed";
             type union {
               type string {
                 pattern "<.*>|$.*";
               }
               type uint32 {
                 range "32 .. 16385";
               }
             }
           }
         }
         container srgb {
           description "Set the SRGB global block in SPRING";
           leaf start-label {
             description "Start range for SRGB label block";
             type union {
               type string {
                 pattern "<.*>|$.*";
               }
               type uint32 {
                 range "16 .. 1048575";
               }
             }
             //mandatory true;
           }
           leaf index-range {
             description "Index to the SRGB start label block";
             type union {
               type string {
                 pattern "<.*>|$.*";
               }
               type uint32 {
                 range "32 .. 1048559";
               }
             }
             //mandatory true;
           }
         }
         leaf mapping-server {
           description "Mapping server name";
           type string;
         }
         leaf install-prefix-sid-for-best-route {
           description "For best route install a exact prefix sid route";
           type empty;
         }
         leaf ldp-stitching {
           description "Enable SR to LDP stitching";
           type empty;
         }
         leaf-list flex-algorithm {
           description "Flex-algorithms we would like to participate in";
           type union {
             type string {
               pattern "<.*>|$.*";
             }
             type uint32 {
               range "128 .. 255";
             }
           }
           max-elements 16;
         }
         leaf strict-asla-based-flex-algorithm {
           description "Flex-Algorithm to ignore links not having ASLA sub-TLVs";
           type empty;
         }
         container sensor-based-stats {
           description "Configure sensor based stats in SPRING";
           uses apply-advanced;
           container per-interface-per-member-link {
             description "Configure sensor based stats per nexthop";
             leaf ingress {
               description "Enable sensor based stats on ingress interface";
               type empty;
             }
             leaf egress {
               description "Enable sensor based stats on egress interface";
               type empty;
             }
           }
           container per-sid {
             description "Configure sensor based stats per spring route";
             leaf ingress {
               description "Enable sensor based stats for per-sid ingress accounting";
               type empty;
             }
             leaf egress {
               description "Enable sensor based stats for IP-MPLS egress accounting";
               type empty;
             }
           }
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                     mandatory true;
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
         }
         list sham-link-remote {
           key name;
           ordered-by user;
           description "Configure parameters for remote sham link endpoint";
           leaf name {
             description "Remote sham link endpoint address";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf keychain {
             description "Key chain name";
             type string {
               length "1 .. 128";
             }
           }
         }
         list interface {
           key name;
           ordered-by user;
           description "Include an interface in this area";
           leaf name {
             description "Interface name";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 type jt:ipv4addr;
               }
             }
           }
           leaf secondary {
             description "Treat interface as secondary";
             type empty;
           }
           leaf own-router-lsa {
             description "Generate a separate router LSA for this interface";
             type empty;
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
           leaf metric {
             description "Interface metric";
             type union {
               type string {
                 pattern "<.*>|$.*";
               }
               type uint16 {
                 range "1 .. 65535";
               }
             }
           }
           leaf priority {
             description "Designated router priority";
             type union {
               type string {
                 pattern "<.*>|$.*";
               }
               type uint32 {
                 range "0 .. 255";
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             leaf full-neighbors-only {
               description "Setup BFD sessions only to Full neighbors";
               type empty;
             }
             leaf holddown-interval {
               description "Time to hold the session-UP notification to the client";
               units "milliseconds";
               type union {
                 type string {
                   pattern "<.*>|$.*";
                 }
                 type uint32 {
                   range "0 .. 255000";
                 }
               }
             }
           }
           leaf dynamic-neighbors {
             description "Learn neighbors dynamically on a p2mp interface";
             type empty;
           }
           leaf no-advertise-adjacency-segment {
             description "Do not advertise an adjacency segment for this interface";
             type empty;
           }
           list neighbor {
             key name;
             ordered-by user;
             description "NBMA neighbor";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
           leaf strict-bfd {
             description "Enable strict bfd over this interface";
             type empty;
           }
           container post-convergence-lfa {
             presence "enable post-convergence-lfa";
             description "Protect interface using post-convergence backup path";
             uses apply-advanced;
           }
           leaf te-metric {
             description "Traffic engineering metric";
             type union {
               type string {
                 pattern "<.*>|$.*";
               }
               type uint32 {
                 range "1 .. 4294967295";
               }
             }
           }
           container ldp-synchronization {
             description "Advertise maximum metric until LDP is operational";
             presence "enable ldp-synchronization";
             uses ldp-sync-obj;
           }
           container ipv4-adjacency-segment {
             description "Configure ipv4 adjacency segment";
             uses apply-advanced;
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list lan-neighbor {
             key name;
             ordered-by user;
             description "Configuration specific to a LAN neighbor";
             leaf name {
               description "Address of neighbor";
               type jt:ipaddr;
             }
             uses apply-advanced;
             container ipv4-adjacency-segment {
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
           }
           leaf delay-metric {
             description "Delay metric";
             units "microseconds";
             type union {
               type string {
                 pattern "<.*>|$.*";
               }
               type uint32 {
                 range "0 .. 16777215";
               }
             }
           }
           container delay-measurement {
             presence "enable delay-measurement";
             description "Enable delay measurement";
             uses apply-advanced;
             leaf probe-interval {
               description "Probe interval";
               units "seconds";
               type union {
                 type string {
                   pattern "<.*>|$.*";
                 }
                 type uint32 {
                   range "1 .. 255";
                 }
               }
             }
             leaf probe-count {
               description "Probe count";
               type union {
                 type string {
                   pattern "<.*>|$.*";
                 }
                 type uint32 {
                   range "1 .. 15";
                 }
               }
             }
             container advertisement {
               description "Delay advertisement";
               uses apply-advanced;
               container periodic {
                 description "Periodic advertisement parameters";
                 uses apply-advanced;
                 leaf threshold {
                   description "Threshold";
                   units "percentage";
                   type union {
                     type string {
                       pattern "<.*>|$.*";
                     }
                     type uint32 {
                       range "0 .. 100";
                     }
                   }
                 }
                 leaf interval {
                   description "Interval";
                   units "seconds";
                   type union {
                     type string {
                       pattern "<.*>|$.*";
                     }
                     type uint32 {
                       range "30 .. 3600";
                     }
                   }
                 }
               }
               container accelerated {
                 presence "enable accelerated";
                 description "Accelerated advertisement parameters";
                 uses apply-advanced;
                 leaf threshold {
                   description "Threshold";
                   units "percentage";
                   type union {
                     type string {
                       pattern "<.*>|$.*";
                     }
                     type uint32 {
                       range "0 .. 100";
                     }
                   }
                 }
               }
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf te-metric {
                 description "Traffic engineering metric for this attribute group";
                 type union {
                   type string {
                     pattern "<.*>|$.*";
                   }
                   type uint32 {
                     range "1 .. 4294967295";
                   }
                 }
               }
               leaf-list admin-group {
                 ordered-by user;
                 description "Administrative groups for this attribute-group";
                 type string;
                 max-elements 16;
               }
               leaf delay-metric {
                 description "Delay metric for this attribute-group";
                 units "microseconds";
                 type union {
                   type string {
                     pattern "<.*>|$.*";
                   }
                   type uint32 {
                     range "0 .. 16777215";
                   }
                 }
               }
               leaf advertise-interface-delay {
                 description "Use interface specific static/dynamic delay values as applicable in ASLA Sub-TLVs";
                 type empty;
               }
               container application {
                 description "Standard Applications part of this attribute-group";
                 uses apply-advanced;
                 leaf flex-algorithm {
                   description "Set X flag in standard application bit mask";
                   type empty;
                 }
               }
             }
           }
         }
         leaf no-source-packet-routing {
           description "Disable SPRING in this area";
           type empty;
         }
       }
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "traffic-statistics" {
                 description "Trace Segment Routing Traffic Statistics";
               }
               enum "backup-spf" {
                 description "Trace backup SPF (LFA) specific events";
               }
               enum "source-packet-routing" {
                 description "Trace source packet routing (SPRING) events";
               }
               enum "post-convergence-lfa" {
                 description "Trace post-convergence-lfa related events";
               }
               enum "flex-algorithm" {
                 description "Trace flex-algorithm related events";
               }
               enum "rmopd" {
                 description "Trace rmopd interactions";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           type string;
         }
         leaf inet3 {
           description "Name of the IPv4/v6 inet.3 routing table group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 3600";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
           mandatory true;
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         type union {
           type string {
             pattern "<.*>|$.*";
           }
           type uint32 {
             range "50 .. 8000";
           }
         }
       }
       leaf no-rfc-1583 {
         description "Disable RFC1583 compatibility";
         type empty;
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
     }
     container ospf3 {
       description "OSPFv3 configuration";
       uses juniper-protocols-ospf3;
     }
     container source-packet-routing {
       presence "enable source-packet-routing";
       description "Enable source packet routing (SPRING)";
       uses apply-advanced;
       container traceoptions {
         description "Trace options for soure-packet-routing";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "controller" {
                 description "Trace controller-related activity";
               }
               enum "state" {
                 description "Trace LSP state-related activity";
               }
               enum "route" {
                 description "Trace route-related activity";
               }
               enum "general" {
                 description "Trace general activity";
               }
               enum "interface" {
                 description "Trace interface-related activity";
               }
               enum "dtm" {
                 description "Trace dtm-related activity";
               }
               enum "bfd" {
                 description "Trace bfd-related activity";
               }
               enum "translation" {
                 description "Trace translation-related activity";
               }
               enum "srv6-te" {
                 description "Trace srv6-te activity";
               }
               enum "telemetry-statistics" {
                 description "Trace telemetry statistics related activity";
               }
               enum "compute" {
                 description "Trace compute profile and computed lsp related activity";
               }
               enum "nsr-replication" {
                 description "Trace NSR replication activity";
               }
               enum "traffic-engineering-database" {
                 description "Trace spring-te to ted export related activity";
               }
               enum "delay-measurement" {
                 description "Trace path delay measurement related activity";
               }
               enum "all" {
                 description "Trace everything";
               }
             }
           }
           leaf detail {
             description "Trace detailed information";
             type empty;
           }
         }
       }
       list lsp-external-controller {
         key name;
         ordered-by user;
         description "External path computing entity";
         leaf name {
           description "Name of the external path computing entity";
           type string {
             length "1 .. 64";
           }
         }
         uses apply-advanced;
       }
       leaf entropy-label {
         description "Enable entropy label for all SR-MPLS tunnels";
         type empty;
       }
       leaf preference {
         description "Route preference for SPRING-TE routes";
         type union {
           type uint32;
           type string {
             pattern "<.*>|$.*";
           }
         }
       }
       leaf sr-preference-override {
         description "SR-preference override for static SR-policies.Higher value is more preferred";
         type union {
           type string {
             pattern "<.*>|$.*";
           }
           type uint32 {
             range "0 .. 4294967295";
           }
         }
       }
       leaf sr-preference {
         description "SR-preference for static SR-policies.Higher value is more preferred";
         type union {
           type string {
             pattern "<.*>|$.*";
           }
           type uint32 {
             range "0 .. 4294967295";
           }
         }
       }
       leaf maximum-segment-list-depth {
         description "Maximum segment list depth for SR-TE policies";
         type union {
           type string {
             pattern "<.*>|$.*";
           }
           type uint32 {
             range "1 .. 16";
           }
         }
       }
       leaf maximum-srv6-te-segment-list-depth {
         description "Maximum segment list depth for SRv6-TE policies";
         type union {
           type string {
             pattern "<.*>|$.*";
           }
           type uint32 {
             range "1 .. 6";
           }
         }
       }
       leaf no-chained-composite-next-hop {
         description "Do not use chained composite next hops for SRTE routes";
         type empty;
       }
       leaf tunnel-tracking {
         description "Track route status for first hop label based tunnels";
         type empty;
       }
       list segment-list {
         key name;
         ordered-by user;
         description "Explicit path for SR-TE segments";
         leaf name {
           description "Name of SR-TE segment-list";
           type string {
             length "1 .. 64";
           }
         }
         uses apply-advanced;
         leaf inherit-label-nexthops {
           description "Inherit label nexthops for first hop in this segment list";
           type empty;
         }
         choice translation-type {
           case case_1 {
             container auto-translate {
               presence "enable auto-translate";
               description "Enable auto translation from IP address to labels";
               uses apply-advanced;
               choice protection-choice {
                 case case_1 {
                   container protected {
                     presence "enable protected";
                     description "Choose protected labels if available";
                     uses apply-advanced;
                     leaf mandatory {
                       description "Mandatorily choose protected labels";
                       type empty;
                     }
                   }
                 }
                 case case_2 {
                   container unprotected {
                     presence "enable unprotected";
                     description "Choose unprotected labels if available";
                     uses apply-advanced;
                     leaf mandatory {
                       description "Mandatorily choose unprotected labels";
                       type empty;
                     }
                   }
                 }
               }
               leaf skip-tail-end-validation {
                 description "Skip validation of end hops";
                 type empty;
               }
             }
           }
           case case_2 {
             container dynamic {
               presence "enable dynamic";
               description "Enable dynamic last hop computation";
               uses apply-advanced;
               choice protection-choice {
                 case case_1 {
                   container protected {
                     presence "enable protected";
                     description "Choose protected labels if available";
                     uses apply-advanced;
                     leaf mandatory {
                       description "Mandatorily choose protected labels";
                       type empty;
                     }
                   }
                 }
                 case case_2 {
                   container unprotected {
                     presence "enable unprotected";
                     description "Choose unprotected labels if available";
                     uses apply-advanced;
                     leaf mandatory {
                       description "Mandatorily choose unprotected labels";
                       type empty;
                     }
                   }
                 }
               }
             }
           }
         }
         leaf compute {
           description "Segment list used for specifying explicit path for computed paths";
           type empty;
         }
         leaf srv6 {
           description "Segment list used for SRv6";
           type empty;
         }
         list hop-list {
           key name;
           ordered-by user;
           max-elements 36;
           leaf name {
             description "Next hop in segment-list";
             type string {
               length "1 .. 64";
             }
           }
           uses apply-advanced;
           leaf label {
             description "Next label in SR-TE segment-list";
             type union {
               type string {
                 pattern "<.*>|$.*";
               }
               type uint32 {
                 range "0 .. 1048575";
               }
             }
           }
           leaf ip-address {
             description "IP address of the hop";
             type jt:ipaddr;
           }
           leaf srv6-sid {
             description "Sid for SRv6 segment-list in form of ipv6 address";
             type jt:ipaddr;
           }
           container micro-srv6-sid {
             description "Configure a micro srv6 sid";
             uses apply-advanced;
             leaf micro-sid {
               description "Micro sid for SRv6 segment-list in form of ipv6 address";
               type jt:ipaddr;
               mandatory true;
             }
             leaf strict-adjacency {
               description "Strictly follow the micro adjacency sid";
               type empty;
             }
           }
           choice hop-choice {
             case case_1 {
               leaf strict {
                 description "Strict hop";
                 type empty;
               }
             }
             case case_2 {
               leaf loose {
                 description "Loose hop";
                 type empty;
               }
             }
           }
           container label-type {
             description "Type of label for the hop";
             uses apply-advanced;
             leaf node {
               description "Hop represents a node";
               type empty;
             }
           }
         }
       }
       list compute-profile {
         key name;
         ordered-by user;
         description "Compute profile for dynamically computed paths";
         leaf name {
           description "Name of the computation-profile";
           type string {
             length "1 .. 64";
           }
         }
         uses apply-advanced;
         container admin-group {
           description "Administrative group policy";
           uses admin_group_include_exclude;
         }
         leaf maximum-segment-list-depth {
           description "Maximum depth of computed path";
           type union {
             type string {
               pattern "<.*>|$.*";
             }
             type uint32 {
               range "1 .. 16";
             }
           }
         }
         leaf algorithm {
           description "Algorithm to constrain the path into";
           type union {
             type string {
               pattern "<.*>|$.*";
             }
             type uint32 {
               range "1 .. 255";
             }
           }
         }
         leaf no-label-stack-compression {
           description "Provide fully expanded path, using adjacency segment identifiers";
           type empty;
         }
         choice protection-choice {
           case case_1 {
             container protected {
               presence "enable protected";
               description "Choose protected labels if available";
               uses apply-advanced;
               leaf mandatory {
                 description "Mandatorily choose protected labels";
                 type empty;
               }
             }
           }
           case case_2 {
             container unprotected {
               presence "enable unprotected";
               description "Choose unprotected labels if available";
               uses apply-advanced;
               leaf mandatory {
                 description "Mandatorily choose unprotected labels";
                 type empty;
               }
             }
           }
         }
         leaf compute-segment-list {
           description "Name of the compute type segmentlist";
           type string {
             length "1 .. 64";
           }
         }
         leaf maximum-computed-segment-lists {
           description "Maximum number of segment-lists(ECMP paths) to be computed";
           type union {
             type string {
               pattern "<.*>|$.*";
             }
             type uint32 {
               range "1 .. 128";
             }
           }
         }
         container metric-type {
           description "Metric type used for computaion";
           uses apply-advanced;
           choice metric-choice {
             case case_1 {
               leaf te {
                 description "TE metric";
                 type empty;
               }
             }
             case case_2 {
               leaf igp {
                 description "IGP metric";
                 type empty;
               }
             }
             case case_3 {
               container delay {
                 presence "enable delay";
                 description "Delay metric";
                 uses apply-advanced;
                 choice metric-choice {
                   case case_1 {
                     leaf minimum {
                       description "Minimum delay metric type";
                       type empty;
                     }
                   }
                   case case_2 {
                     leaf maximum {
                       description "Maximum delay metric type";
                       type empty;
                     }
                   }
                   case case_3 {
                     leaf average {
                       description "Average delay metric type";
                       type empty;
                     }
                   }
                 }
                 leaf delay-variation-threshold {
                   description "Link delay variation threshold";
                   type union {
                     type string {
                       pattern "<.*>|$.*";
                     }
                     type uint32 {
                       range "1 .. 16777215";
                     }
                   }
                 }
               }
             }
           }
         }
         container bound-metric {
           description "Bound metric used for computation";
           uses apply-advanced;
           leaf te {
             description "TE bound metric value";
             type union {
               type string {
                 pattern "<.*>|$.*";
               }
               type uint32 {
                 range "1 .. 4294967295";
               }
             }
           }
           leaf igp {
             description "IGP bound metric value";
             type union {
               type string {
                 pattern "<.*>|$.*";
               }
               type uint32 {
                 range "1 .. 4294967295";
               }
             }
           }
           leaf delay {
             description "Delay bound metric value";
             type union {
               type string {
                 pattern "<.*>|$.*";
               }
               type uint32 {
                 range "1 .. 4294967295";
               }
             }
           }
         }
         leaf bandwidth-requested {
           description "SR Path requested bandwidth in (bits/sec)";
           units "bps";
           type string;
         }
         container bandwidth-reservation-priority {
           presence "enable bandwidth-reservation-priority";
           description "SR path bandwidth reservation priority";
         }
         leaf setup-priority {
           description "Setup priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
       }
       leaf srv6 {
         description "Enable srv6 support for source-packet-routing";
         type empty;
       }
       container preserve-nexthop-hierarchy {
         presence "enable preserve-nexthop-hierarchy";
         description "Enable preserve-nexthop-hierarchy for source-packet-routing";
         uses apply-advanced;
         container sr-mpls {
           description "Disable preserve-nexthop-hierarchy for sr-mpls";
           uses apply-advanced;
           choice enable-disable {
             case case_1 {
               leaf disable {
                 description "Disable preserve-nexthop-hierarchy for sr-mpls";
                 type empty;
               }
             }
           }
         }
         container srv6 {
           description "Disable preserve-nexthop-hierarchy for srv6";
           uses apply-advanced;
           choice enable-disable {
             case case_1 {
               leaf disable {
                 description "Disable preserve-nexthop-hierarchy for srv6";
                 type empty;
               }
             }
           }
         }
       }
       leaf sbfd-frr {
         description "Enable sbfd frr support for source-packet-routing";
         type empty;
       }
       list source-routing-path {
         key name;
         ordered-by user;
         description "Configure a source-routing-path";
         leaf name {
           description "Name of the source routing path";
           type string {
             length "1 .. 64";
           }
         }
         uses apply-advanced;
         leaf srv6 {
           description "Tunnel type SRv6";
           type empty;
         }
         leaf ldp-tunneling {
           description "Allow LDP to use this LSP for tunneling";
           type empty;
         }
         leaf use-for-shortcut {
           description "Allow this LSP to be used as a shortcut tunnel";
           type empty;
         }
         container diversity-association {
           description "Configure diversity association for LSP";
           uses apply-advanced;
           leaf-list group {
             ordered-by user;
             description "Configure diversity association group";
             type string;
             max-elements 8;
           }
           leaf shortest-path-first {
             description "Enable priority computation";
             type empty;
           }
         }
         container te-policy-association {
           description "Configure te policy association for LSP";
           uses apply-advanced;
           leaf-list group {
             ordered-by user;
             description "Configure te policy association group";
             type string;
             max-elements 8;
           }
         }
         leaf to {
           description "Ip-address of the tunnel end-point";
           type jt:ipaddr;
           mandatory true;
         }
         leaf from {
           description "Ip-address of the tunnel start-point";
           type jt:ipaddr;
         }
         leaf color {
           description "Color identifier for the tunnel end-point";
           type union {
             type uint32;
             type string {
               pattern "<.*>|$.*";
             }
           }
         }
         leaf no-ingress {
           description "Disable ingress functionality for this tunnel";
           type empty;
         }
         leaf binding-sid {
           description "Specify the binding-label to enable transit functionality for this tunnel";
           type union {
             type string {
               pattern "<.*>|$.*";
             }
             type uint32 {
               range "16 .. 1048575";
             }
           }
         }
         list install {
           key name;
           ordered-by user;
           description "Install prefix";
           leaf name {
             description "Destination prefix";
             type jt:ipaddr;
           }
         }
         leaf preference {
           description "Preference for routes downloaded for this tunnel";
           status deprecated;
           type union {
             type uint32;
             type string {
               pattern "<.*>|$.*";
             }
           }
         }
         leaf metric {
           description "Metric for routes downloaded for this tunnel";
           type union {
             type string {
               pattern "<.*>|$.*";
             }
             type uint32 {
               range "1 .. 16777215";
             }
           }
         }
         leaf te-group-id {
           description "Te group id";
           type union {
             type string {
               pattern "<.*>|$.*";
             }
             type uint32 {
               range "1 .. 128";
             }
           }
         }
         leaf sr-preference {
           description "SR-preference for SPRING-TE routes. Higher value is more preferred";
           type union {
             type string {
               pattern "<.*>|$.*";
             }
             type uint32 {
               range "0 .. 4294967295";
             }
           }
         }
         leaf lsp-external-controller {
           description "Name of the external path computing entity";
           type string {
             length "1 .. 64";
           }
         }
         list primary {
           key name;
           ordered-by user;
           description "Configure a primary segment list for this source-routing-path";
           max-elements 128;
           leaf name {
             description "Name of SR-TE segment-list";
             type string {
               length "1 .. 64";
             }
             mandatory true;
           }
           uses apply-advanced;
           leaf weight {
             description "Specify the balance factor for this segment list in SR-TE tunnel";
             type union {
               type uint32;
               type string {
                 pattern "<.*>|$.*";
               }
             }
           }
           container bfd-liveness-detection {
             description "Bidirectional forwarding detection options";
             uses apply-advanced;
             container sbfd {
               presence "enable sbfd";
               description "Seamless BFD parameters";
               uses apply-advanced;
               leaf remote-discriminator {
                 description "Remote discriminator of reflector";
                 type union {
                   type string {
                     pattern "<.*>|$.*";
                   }
                   type uint32 {
                     range "1 .. 4294967295";
                   }
                 }
               }
               leaf responder-ip {
                 description "Seamless BFD responder address";
                 type jt:ipaddr;
               }
               leaf ip-ttl {
                 description "TTL for IP Header";
                 default "5";
                 type union {
                   type string {
                     pattern "<.*>|$.*";
                   }
                   type uint8 {
                     range "1 .. 255";
                   }
                 }
               }
               leaf destination-ipv6-local-host {
                 description "Use IPv6 local-host address as last address in SRH in compliance with RFC 7881";
                 type empty;
               }
             }
             leaf minimum-interval {
               description "Minimum transmit and receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf pdu-size {
               description "BFD transport protocol payload size";
               default "24";
               type union {
                 type string {
                   pattern "<.*>|$.*";
                 }
                 type uint32 {
                   range "24 .. 16000";
                 }
               }
             }
             leaf no-router-alert-option {
               description "Do not set the router alert option in IP header";
               type empty;
             }
           }
           container compute {
             presence "enable compute";
             description "Enable computation";
             uses apply-advanced;
             leaf compute-profile-name {
               description "Name of compute-profile";
               type string {
                 length "1 .. 64";
               }
             }
           }
           leaf lsp-external-controller {
             description "Name of the external path computing entity";
             type string {
               length "1 .. 64";
             }
           }
         }
         list secondary {
           key name;
           ordered-by user;
           description "Configure a secondary segment list for this source-routing-path";
           max-elements 1;
           leaf name {
             description "Name of SR-TE segment-list";
             type string {
               length "1 .. 64";
             }
             mandatory true;
           }
           uses apply-advanced;
           container bfd-liveness-detection {
             description "Bidirectional forwarding detection options";
             uses apply-advanced;
             container sbfd {
               presence "enable sbfd";
               description "Seamless BFD parameters";
               uses apply-advanced;
               leaf remote-discriminator {
                 description "Remote discriminator of reflector";
                 type union {
                   type string {
                     pattern "<.*>|$.*";
                   }
                   type uint32 {
                     range "1 .. 4294967295";
                   }
                 }
               }
               leaf responder-ip {
                 description "Seamless BFD responder address";
                 type jt:ipaddr;
               }
               leaf ip-ttl {
                 description "TTL for IP Header";
                 default "5";
                 type union {
                   type string {
                     pattern "<.*>|$.*";
                   }
                   type uint8 {
                     range "1 .. 255";
                   }
                 }
               }
               leaf destination-ipv6-local-host {
                 description "Use IPv6 local-host address as last address in SRH in compliance with RFC 7881";
                 type empty;
               }
             }
             leaf minimum-interval {
               description "Minimum transmit and receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf pdu-size {
               description "BFD transport protocol payload size";
               default "24";
               type union {
                 type string {
                   pattern "<.*>|$.*";
                 }
                 type uint32 {
                   range "24 .. 16000";
                 }
               }
             }
             leaf no-router-alert-option {
               description "Do not set the router alert option in IP header";
               type empty;
             }
           }
           container compute {
             presence "enable compute";
             description "Enable computation";
             uses apply-advanced;
             leaf compute-profile-name {
               description "Name of compute-profile";
               type string {
                 length "1 .. 64";
               }
             }
           }
         }
         leaf entropy-label {
           description "Enable entropy label for this tunnel";
           type empty;
         }
       }
       list source-routing-path-template {
         key name;
         ordered-by user;
         description "Configure a source-routing-path-template";
         leaf name {
           description "Name of the source routing path";
           type string {
             length "1 .. 64";
           }
         }
         uses apply-advanced;
         leaf no-ingress {
           description "Disable ingress functionality for this tunnel";
           type empty;
         }
         leaf use-for-shortcut {
           description "Allow this LSP to be used as a shortcut tunnel";
           type empty;
         }
         container diversity-association {
           description "Configure diversity association for LSP";
           uses apply-advanced;
           leaf-list group {
             ordered-by user;
             description "Configure diversity association group";
             type string;
             max-elements 8;
           }
           leaf shortest-path-first {
             description "Enable priority computation";
             type empty;
           }
         }
         container te-policy-association {
           description "Configure te policy association for LSP";
           uses apply-advanced;
           leaf-list group {
             ordered-by user;
             description "Configure te policy association group";
             type string;
             max-elements 8;
           }
         }
         leaf metric {
           description "Metric for routes downloaded for this tunnel";
           type union {
             type string {
               pattern "<.*>|$.*";
             }
             type uint32 {
               range "1 .. 16777215";
             }
           }
         }
         leaf sr-preference {
           description "SR-preference for SPRING-TE routes. Higher value is more preferred";
           type union {
             type string {
               pattern "<.*>|$.*";
             }
             type uint32 {
               range "0 .. 4294967295";
             }
           }
         }
         leaf ldp-tunneling {
           description "Allow LDP to use this LSP for tunneling";
           type empty;
         }
         leaf entropy-label {
           description "Enable entropy label for all SR-MPLS tunnels referring to this template";
           type empty;
         }
         leaf lsp-external-controller {
           description "Name of the external path computing entity";
           type string {
             length "1 .. 64";
           }
         }
         list primary {
           key name;
           ordered-by user;
           description "Configure a primary segment list for this source-routing-path";
           max-elements 128;
           leaf name {
             description "Name of SR-TE segment-list";
             type string {
               length "1 .. 64";
             }
             mandatory true;
           }
           uses apply-advanced;
           leaf weight {
             description "Specify the balance factor for this segment list in SR-TE tunnel";
             type union {
               type uint32;
               type string {
                 pattern "<.*>|$.*";
               }
             }
           }
           container compute {
             presence "enable compute";
             description "Enable computation";
             uses apply-advanced;
             leaf compute-profile-name {
               description "Name of compute-profile";
               type string {
                 length "1 .. 64";
               }
             }
           }
           leaf lsp-external-controller {
             description "Name of the external path computing entity";
             type string {
               length "1 .. 64";
             }
           }
         }
         list secondary {
           key name;
           ordered-by user;
           description "Configure a secondary segment list for this source-routing-path";
           max-elements 1;
           leaf name {
             description "Name of SR-TE segment-list";
             type string {
               length "1 .. 64";
             }
             mandatory true;
           }
           uses apply-advanced;
           container compute {
             presence "enable compute";
             description "Enable computation";
             uses apply-advanced;
             leaf compute-profile-name {
               description "Name of compute-profile";
               type string {
                 length "1 .. 64";
               }
             }
           }
         }
         container bfd-liveness-detection {
           description "Bidirectional forwarding detection options";
           uses apply-advanced;
           container sbfd {
             presence "enable sbfd";
             description "Seamless BFD parameters";
             uses apply-advanced;
             leaf remote-discriminator {
               description "Remote discriminator of reflector";
               type union {
                 type string {
                   pattern "<.*>|$.*";
                 }
                 type uint32 {
                   range "1 .. 4294967295";
                 }
               }
             }
             leaf responder-ip {
               description "Seamless BFD responder address";
               type jt:ipaddr;
             }
             leaf ip-ttl {
               description "TTL for IP Header";
               default "5";
               type union {
                 type string {
                   pattern "<.*>|$.*";
                 }
                 type uint8 {
                   range "1 .. 255";
                 }
               }
             }
             leaf destination-ipv6-local-host {
               description "Use IPv6 local-host address as last address in SRH in compliance with RFC 7881";
               type empty;
             }
           }
           leaf minimum-interval {
             description "Minimum transmit and receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf pdu-size {
             description "BFD transport protocol payload size";
             default "24";
             type union {
               type string {
                 pattern "<.*>|$.*";
               }
               type uint32 {
                 range "24 .. 16000";
               }
             }
           }
           leaf no-router-alert-option {
             description "Do not set the router alert option in IP header";
             type empty;
           }
         }
         leaf srv6 {
           description "Template type SRv6";
           type empty;
         }
       }
       leaf inherit-label-nexthops {
         description "Inherit label nexthops for first hop in segment lists";
         type empty;
       }
       container rib-group {
         description "Enable rib-group import  poilicies on SR-TE";
         uses apply-advanced;
         container ipv4 {
           presence "enable ipv4";
           description "Import  policy to be applied on ipv4 uncolored route";
           uses apply-advanced;
           leaf rib-group-name {
             description "Rib-group import policy";
             type string {
               length "1 .. 64";
             }
             mandatory true;
           }
         }
         container ipv6 {
           presence "enable ipv6";
           description "Import  policy to be applied on ipv6 uncolored route";
           uses apply-advanced;
           leaf rib-group-name {
             description "Rib-group import policy";
             type string {
               length "1 .. 64";
             }
             mandatory true;
           }
         }
         container ipv4-color {
           presence "enable ipv4-color";
           description "Import  policy to be applied on ipv4 colored route";
           uses apply-advanced;
           leaf rib-group-name {
             description "Rib-group import policy";
             type string {
               length "1 .. 64";
             }
             mandatory true;
           }
         }
         container ipv6-color {
           presence "enable ipv6-color";
           description "Import  policy to be applied on ipv6 colored route";
           uses apply-advanced;
           leaf rib-group-name {
             description "Rib-group import policy";
             type string {
               length "1 .. 64";
             }
             mandatory true;
           }
         }
         container tag {
           presence "enable tag";
           description "Import  policy to be applied on mpls route";
           uses apply-advanced;
           leaf rib-group-name {
             description "Rib-group import policy";
             type string {
               length "1 .. 64";
             }
             mandatory true;
           }
         }
       }
       container telemetry {
         description "Enable telemetry on SR-TE policies";
         uses apply-advanced;
         container statistics {
           presence "enable statistics";
           description "Enable traffic-statistics collection on SR-TE policies";
           uses apply-advanced;
           leaf no-transit {
             description "Disable statistics collection on binding sid route";
             type empty;
           }
           leaf no-ingress {
             description "Disable statistics collection on destination route";
             type empty;
           }
           container per-source {
             description "Enable traffic-statistics collection per source";
             uses apply-advanced;
             leaf per-segment-list {
               description "Enable per path level traffic-statistics collection";
               type empty;
             }
           }
         }
       }
       container traffic-engineering {
         description "Enable import of all Spring-TE policies into TED";
         uses apply-advanced;
         leaf database {
           description "Spring-TE policies Traffic engineering database";
           type empty;
         }
       }
       container use-transport-class {
         presence "enable use-transport-class";
         description "Enable transport class on SR-TE colored policies";
         uses apply-advanced;
         leaf fib-install {
           description "Install SRTE routes in FIB";
           type empty;
         }
         leaf inet3-install {
           description "Install SRTE routes in inet{6}.3 table";
           type empty;
         }
       }
       leaf inet-color-append-explicit-null {
         description "Enable appending explicit NULL for inet SRTE policy";
         type empty;
       }
       leaf retry-timer {
         description "Time before retrying auto-translation failed paths";
         units "seconds";
         type union {
           type string {
             pattern "<.*>|$.*";
           }
           type int32 {
             range "1 .. 600";
           }
         }
       }
       leaf import-color-only-cross-af {
         description "Enable importing of Null Endpoint color route for cross address family";
         type empty;
       }
       leaf inet6-color-append-explicit-null {
         description "Enable appending explicit NULL for inet6 SRTE policy";
         type empty;
       }
       leaf ipv6-tunneling-append-explicit-null {
         description "Enable appending explicit NULL for v4ov6 SRTE routes ";
         type empty;
       }
       container source-routing-path-template-map {
         description "Configure a source routing path template map";
         uses apply-advanced;
         leaf-list policy {
           ordered-by user;
           description "Configure policy";
           type jt:policy-algebra;
         }
       }
     }
     container dcbx {
       presence "enable dcbx";
     }
     container lldp {
       description "Link Layer Detection Protocol";
       uses apply-advanced;
       choice enable-disable {
         case case_1 {
           leaf disable {
             description "Disable LLDP";
             type empty;
           }
         }
       }
       container traceoptions {
         description "Trace options for LLDP";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "all" {
                 description "Trace configuration events";
               }
               enum "configuration" {
                 description "Log configuration events";
               }
               enum "rtsock" {
                 description "Trace rtsock message events";
               }
               enum "packet" {
                 description "Trace packet information";
               }
               enum "protocol" {
                 description "Trace protocol information";
               }
               enum "interface" {
                 description "Trace interface update events";
               }
               enum "vlan" {
                 description "Trace VLAN update events";
               }
               enum "snmp" {
                 description "Trace SNMP events";
               }
               enum "jvision" {
                 description "Trace Jvision events";
               }
             }
           }
           leaf disable {
             description "Disable this trace flag";
             type empty;
           }
         }
       }
       leaf management-address {
         description "LLDP management address";
         type jt:ipaddr;
       }
       leaf advertisement-interval {
         description "Transmit interval for LLDP messages";
         default "30";
         units "seconds";
         type union {
           type string {
             pattern "<.*>|$.*";
           }
           type uint32 {
             range "5 .. 32768";
           }
         }
       }
       leaf transmit-delay {
         description "Transmit delay time interval for LLDP messages";
         units "seconds";
         type union {
           type string {
             pattern "<.*>|$.*";
           }
           type uint32 {
             range "1 .. 8192";
           }
         }
       }
       leaf hold-multiplier {
         description "Hold timer interval for LLDP messages";
         default "4";
         type union {
           type string {
             pattern "<.*>|$.*";
           }
           type uint32 {
             range "2 .. 10";
           }
         }
       }
       leaf port-id-subtype {
         description "Sub-type to be used for Port ID TLV generation";
         default "locally-assigned";
         type enumeration {
           enum "locally-assigned" {
             description "Locally assigned value (SNMP index of the interface)";
           }
           enum "interface-name" {
             description "Interface name on which LLDPDU is sent";
           }
         }
       }
       container chassis-id {
         description "Chassis-id to be used for Chassis ID TLV generation";
         uses apply-advanced;
         leaf chassis-id-type {
           description "Chassis-id-type to be used for Chassis ID TLV generation";
           type enumeration {
             enum "chassis-component" {
               description "User define chassis component name.";
             }
             enum "interface-alias" {
               description "Interface description or name on which LLDPDU is sent";
             }
             enum "port-component" {
               description "User define port component name";
             }
             enum "mac-address" {
               description "MAC Address of Interface on which LLDPDU is sent";
             }
             enum "network-address" {
               description "Netwok Address of Interface on which LLDPDU is sent";
             }
             enum "interface-name" {
               description "Interface name on which LLDPDU is sent";
             }
             enum "locally-assigned" {
               description "Locally assigned value (SNMP index of the interface)";
             }
           }
           //mandatory true;
         }
         leaf chassis-id-value {
           description "Chassis-id value as per chassis id type";
           type string {
             length "1 .. 256";
           }
           //mandatory true;
         }
       }
       leaf port-description-type {
         description "The Interfaces Group MIB object to be used for Port Description TLV generation";
         default "interface-alias";
         type enumeration {
           enum "interface-alias" {
             description "Use object ifAlias value for TLV generation";
           }
           enum "interface-description" {
             description "Use object ifDescr value for TLV generation";
           }
         }
       }
       leaf neighbour-port-info-display {
         description "Show lldp neighbors to display port-id or port-description ";
         type enumeration {
           enum "port-id" {
             description "Display port-id information of neighbor in port info";
           }
           enum "port-description" {
             description "Display port description of neighbor in port info";
           }
         }
       }
       leaf mau-type {
         description "Populate mau-type in lldp PDU";
         type empty;
       }
       leaf lldp-tx-fast-init {
         description "Transmission count in fast transmission mode";
         type union {
           type string {
             pattern "<.*>|$.*";
           }
           type uint32 {
             range "1 .. 8";
           }
         }
       }
       leaf fast-rx-processing {
         description "Start optimised processing of received pdu";
         type empty;
       }
       leaf-list tlv-select {
         ordered-by user;
         description "Select TLVs to be sent";
         type enumeration {
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 link-aggregation";
           }
           enum "dcbx-ets-configuration" {
             description "OUI IEEE 802.1 dcbx ets configuration";
           }
           enum "dcbx-ets-recommendation" {
             description "OUI IEEE 802.1 dcbx ets recommendation";
           }
           enum "dcbx-priority-flow-control" {
             description "OUI IEEE 802.1 dcbx pfc";
           }
           enum "dcbx-version-101" {
             description "OUI IEEE 802.1 dcbx version 1.01";
           }
           enum "evb" {
             description "OUI IEEE 82.1QBG evb";
           }
           enum "power-via-mdi-measurements" {
             description "OUI IEEE 802.3 power-via-mdi-measurements";
           }
           enum "cloud-reach-event" {
             description "Cloud reachability event";
           }
           enum "phone-home-active" {
             description "Phone-home active configuration";
           }
           enum "cloud-connect-event" {
             description "Cloud-connectivity configuration";
           }
         }
       }
       leaf-list tlv-filter {
         ordered-by user;
         description "Filter TLVs to be sent";
         type enumeration {
           enum "all" {
             description "Filter all non mandatory TLVs";
           }
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 Link Aggregation";
           }
           enum "dcbx-priority-flow-control" {
             description "OUI IEEE 802.1 dcbx pfc";
           }
           enum "dcbx-ets-configuration" {
             description "OUI IEEE 802.1 dcbx ets configuration";
           }
           enum "dcbx-ets-recommendation" {
             description "OUI IEEE 802.1 dcbx ets recommendation";
           }
           enum "dcbx-version-101" {
             description "OUI IEEE 802.1 dcbx version 1.01";
           }
           enum "evb" {
             description "OUI IEEE 802.1QBG evb";
           }
           enum "power-via-mdi-measurements" {
             description "OUI IEEE 802.3 power-via-mdi-measurements";
           }
           enum "cloud-reach-event" {
             description "Cloud reachability event";
           }
           enum "phone-home-active" {
             description "Phone-home active configuration";
           }
           enum "cloud-connect-event" {
             description "Cloud-connectivity configuration";
           }
         }
       }
       leaf dest-mac-type {
         description "Destination address to be used";
         type enumeration {
           enum "nearest-bridge" {
             description "To set destination mac as 01:80:C2:00:00:0E";
           }
           enum "nearest-non-tpmr-bridge" {
             description "To set destination mac as 01:80:C2:00:00:03";
           }
           enum "nearest-customer-bridge" {
             description "To set destination mac as 01:80:C2:00:00:00";
           }
         }
       }
       leaf management-interface {
         description "Management interface to be used in LLDP PDUs";
         type union {
           type jt:interface-name;
           type string {
             pattern "<.*>|$.*";
           }
         }
       }
       list interface {
         key name;
         ordered-by user;
         description "Interface configuration";
         leaf name {
           type string;
         }
         uses apply-advanced;
         choice enable-disable {
           case case_1 {
             leaf disable {
               description "Disable LLDP";
               type empty;
             }
           }
         }
         leaf-list tlv-select {
           ordered-by user;
           description "Select TLV(s) to be sent";
           type enumeration {
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 link-aggregation";
             }
             enum "dcbx-ets-configuration" {
               description "OUI IEEE 802.1 dcbx ets configuration";
             }
             enum "dcbx-ets-recommendation" {
               description "OUI IEEE 802.1 dcbx ets recommendation";
             }
             enum "dcbx-priority-flow-control" {
               description "OUI IEEE 802.1 dcbx pfc";
             }
             enum "dcbx-version-101" {
               description "OUI IEEE 802.1 dcbx version 1.01";
             }
             enum "evb" {
               description "OUI IEEE 82.1QBG evb";
             }
             enum "power-via-mdi-measurements" {
               description "OUI IEEE 802.3 power-via-mdi-measurements";
             }
             enum "cloud-reach-event" {
               description "Cloud reachability event";
             }
             enum "phone-home-active" {
               description "Phone-home active configuration";
             }
             enum "cloud-connect-event" {
               description "Cloud-connectivity configuration";
             }
           }
         }
         leaf-list tlv-filter {
           ordered-by user;
           description "Filter TLV(s) to be sent";
           type enumeration {
             enum "all" {
               description "Filter all non mandatory TLVs";
             }
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 Link Aggregation";
             }
             enum "dcbx-priority-flow-control" {
               description "OUI IEEE 802.1 dcbx pfc";
             }
             enum "dcbx-ets-configuration" {
               description "OUI IEEE 802.1 dcbx ets configuration";
             }
             enum "dcbx-ets-recommendation" {
               description "OUI IEEE 802.1 dcbx ets recommendation";
             }
             enum "dcbx-version-101" {
               description "OUI IEEE 802.1 dcbx version 1.01";
             }
             enum "evb" {
               description "OUI IEEE 802.1QBG evb";
             }
             enum "power-via-mdi-measurements" {
               description "OUI IEEE 802.3 power-via-mdi-measurements";
             }
             enum "cloud-reach-event" {
               description "Cloud reachability event";
             }
             enum "phone-home-active" {
               description "Phone-home active configuration";
             }
             enum "cloud-connect-event" {
               description "Cloud-connectivity configuration";
             }
           }
         }
         leaf dest-mac-type {
           description "Destination address to be used";
           type enumeration {
             enum "nearest-bridge" {
               description "To set destination mac as 01:80:C2:00:00:0E";
             }
             enum "nearest-non-tpmr-bridge" {
               description "To set destination mac as 01:80:C2:00:00:03";
             }
             enum "nearest-customer-bridge" {
               description "To set destination mac as 01:80:C2:00:00:00";
             }
           }
         }
       }
       leaf system-name {
         description "System name to be used in system-name TLV";
         type string {
           length "1 .. 255";
         }
       }
       leaf system-description {
         description "System description to be used in system-description TLV";
         type string {
           length "1 .. 255";
         }
       }
     }
     container layer2-control {
       description "Global options for layer 2 protocols";
       uses juniper-protocols-l2control;
     }
     container loop-detect {
       presence "enable loop-detect";
       description "Layer2 Loop Detect on interface with non-IP L2 Multicast mac as destination mac";
       uses apply-advanced;
       list interface {
         key name;
         ordered-by user;
         description "Interface name to block Loop Detect PDUs on";
         leaf name {
           type string;
         }
         uses apply-advanced;
         leaf disable {
           description "Disable loop detect feature on a port";
           type empty;
         }
       }
       container enhanced {
         description "Enhanced loop detect configuration";
         uses apply-advanced;
         list interface {
           key name;
           ordered-by user;
           description "Name of interface";
           leaf name {
             type string;
           }
           uses apply-advanced;
           leaf vlan-id {
             description "VLAN identifier for trunk interface or all";
             type string;
           }
           leaf loop-detect-action {
             description "Action that needs to be taken";
             default "interface-down";
             type enumeration {
               enum "interface-down" {
                 description "Interface down action";
               }
               enum "laser-off" {
                 description "Laser off action";
               }
             }
           }
           leaf transmit-interval {
             description "Interval between loop-detect messages";
             default "1s";
             type enumeration {
               enum "1s" {
               }
               enum "10s" {
               }
               enum "1m" {
               }
               enum "10m" {
               }
             }
           }
           leaf revert-interval {
             description "Interval after which action will be reverted";
             default "0";
             units "seconds";
             type union {
               type string {
                 pattern "<.*>|$.*";
               }
               type uint32 {
                 range "0 .. 300";
               }
             }
           }
         }
       }
       leaf destination-mac {
         description "Destination non-IP L2 multicast mac to be used for transmitting Loop Detect PDUs";
         type jt:mac-multicast;
       }
       leaf transmit-interval {
         description "Loop Detect PDU TX interval in sec --default 30s";
         units "seconds";
         type union {
           type string {
             pattern "<.*>|$.*";
           }
           type uint16 {
             range "5 .. 3600";
           }
         }
       }
     }
     container mvrp {
       description "MVRP configuration";
       uses juniper-protocols-mvrp;
     }
     container oam {
       presence "enable oam";
       uses apply-advanced;
       container ethernet {
         presence "enable ethernet";
         uses apply-advanced;
         container fnp {
           presence "enable fnp";
           description "Failure notification protocol configuration";
           uses apply-advanced;
           container traceoptions {
             description "Tracing options for FNP";
             uses apply-advanced;
             container file {
               description "Trace file options";
               leaf filename {
                 description "Name of file in which to write trace information";
                 type string {
                   length "1 .. 1024";
                 }
                 mandatory true;
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "events" {
                     description "Trace protocol events";
                   }
                   enum "pdu" {
                     description "Trace PDU reception and transmission";
                   }
                   enum "timers" {
                     description "Trace protocol timers";
                   }
                   enum "error" {
                     description "Trace all failure conditions";
                   }
                   enum "all" {
                     description "Trace all";
                   }
                 }
               }
             }
           }
           leaf interval {
             description "Interval between FNP messages";
             default "1s";
             type enumeration {
               enum "100ms" {
               }
               enum "1s" {
               }
               enum "10s" {
               }
               enum "1m" {
               }
               enum "10m" {
               }
             }
           }
           leaf loss-threshold {
             description "Number of FNP messages lost before clearing FNP state";
             default "4";
             type union {
               type string {
                 pattern "<.*>|$.*";
               }
               type uint8 {
                 range "3 .. 255";
               }
             }
           }
           list interface {
             key name;
             ordered-by user;
             description "Interface configuration";
             leaf name {
               type union {
                 type jt:interface-name;
                 type string {
                   pattern "<.*>|$.*";
                 }
               }
             }
             uses apply-advanced;
             leaf domain-id {
               description "Ethernet domain identifier";
               default "0";
               type union {
                 type uint32;
                 type string {
                   pattern "<.*>|$.*";
                 }
               }
             }
           }
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping juniper-ospf-authentication {
     description "Authentication information";
     uses apply-advanced;
     choice authentication-type {
       case case_1 {
         leaf simple-password {
           description "Authentication key";
           type jt:unreadable;
         }
       }
       case case_2 {
         list md5 {
           key name;
           ordered-by user;
           description "MD5 authentication key";
           leaf name {
             description "Key ID for MD5 authentication";
             type union {
               type string {
                 pattern "<.*>|$.*";
               }
               type uint32 {
                 range "0 .. 255";
               }
             }
           }
           leaf key {
             description "MD5 authentication key value";
             type jt:unreadable;
             mandatory true;
           }
           leaf start-time {
             description "Start time for key transmission (YYYY-MM-DD.HH:MM)";
             type jt:time;
           }
         }
       }
       case case_3 {
         list multi-active-md5 {
           key name;
           ordered-by user;
           description "Authentication Multiple active MD5 keys";
           leaf name {
             description "Key ID for MD5 authentication";
             type union {
               type string {
                 pattern "<.*>|$.*";
               }
               type uint32 {
                 range "0 .. 255";
               }
             }
           }
           leaf key {
             description "MD5 authentication key value";
             type jt:unreadable;
             mandatory true;
           }
           leaf delete-if-not-inuse {
             description "Delete this key if not in use";
             type empty;
           }
         }
       }
       case case_4 {
         leaf keychain {
           description "Key chain name";
           type string {
             length "1 .. 128";
           }
         }
       }
     }
   }
   grouping juniper-protocols-bgp {
     uses apply-advanced;
     container path-selection {
       description "Configure path selection strategy";
       uses apply-advanced;
       leaf l2vpn-use-bgp-rules {
         description "Use standard BGP rules during L2VPN path selection";
         type empty;
       }
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         type empty;
       }
     }
     container accept-prpd-connection {
       presence "enable accept-prpd-connection";
       description "Enable BGP to accept PRPD connections";
     }
     container global-load-balancing {
       presence "enable global-load-balancing";
       description "Enable global load balancing";
       uses apply-advanced;
       choice mode {
         case case_1 {
           leaf helper-only {
             description "Work as helper role only";
             type empty;
           }
         }
         case case_2 {
           leaf load-balancer-only {
             description "Work as load balancer role only";
             type empty;
           }
         }
       }
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilitating make-before-break for new label advertisements";
       type empty;
     }
     container egress-te-backup-paths {
       description "Backup-path for Egress-TE peer interface failure";
       uses apply-advanced;
       list template {
         key name;
         description "Backup-path template";
         leaf name {
           description "Name of Egress-TE backup path";
           type string {
           }
         }
         uses apply-advanced;
         list peer {
           key name;
           ordered-by user;
           description "Egress peer TE backup exit path";
           leaf name {
             description "Address of BGP peer to use as backup next-hop";
             type jt:ipaddr;
           }
           uses apply-advanced;
         }
         container remote-nexthop {
           description "Resolve and use tunnel to this next-hop as backup path";
           uses apply-advanced;
           leaf remote-nh-addr {
             description "Address of remote-nexthop to use as backup path";
             type jt:ipaddr;
             mandatory true;
           }
         }
         container ip-forward {
           presence "enable ip-forward";
           description "Use IP-forward backup path for Egress TE";
           uses apply-advanced;
           leaf rti-name {
             description "Routing-instance to use as IP forward backup-path";
             type string {
             }
           }
         }
       }
     }
     leaf sr-preference-override {
       description "Replace received segment routing traffic engineering preference value with override value";
       type union {
         type uint32;
         type string {
           pattern "<.*>|$.*";
         }
       }
     }
     leaf vpn-apply-export {
       description "Apply BGP export policy when exporting VPN routes";
       type empty;
     }
     container family {
       description "Protocol family for NLRIs in updates";
       uses apply-advanced;
       container inet {
         description "IPv4 NLRI parameters";
         uses apply-advanced;
         container labeled-unicast {
           description "Include labeled unicast NLRI";
           presence "enable labeled-unicast";
           uses bgp-afi-labeled;
         }
         container segment-routing-te {
           description "Include segment-routing TE policy";
           presence "enable segment-routing-te";
           uses bgp-afi-srte;
         }
         container transport {
           description "Include Classful Transport NLRI";
           presence "enable transport";
           uses bgp-afi-inet-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow-with-redirect-ip-action;
         }
         container any {
           description "Include unicast or multicast NLRI";
           presence "enable any";
           uses bgp-afi-default;
         }
       }
       container inet-vpn {
         description "IPv4 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow-with-redirect-ip-action;
         }
         container any {
           description "Include unicast or multicast NLRI";
           presence "enable any";
           uses bgp-afi-vpn;
         }
       }
       container inet6 {
         description "IPv6 NLRI parameters";
         uses apply-advanced;
         container labeled-unicast {
           description "Include labeled unicast NLRI";
           presence "enable labeled-unicast";
           uses bgp-afi-inet6-labeled;
         }
         container segment-routing-te {
           description "Include segment-routing TE policy";
           presence "enable segment-routing-te";
           uses bgp-afi-srte;
         }
         container transport {
           description "Include Classful Transport NLRI";
           presence "enable transport";
           uses bgp-afi-inet6-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow;
         }
         container any {
           description "Include unicast or multicast NLRI";
           presence "enable any";
           uses bgp-afi-default;
         }
       }
       container inet6-vpn {
         description "IPv6 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow;
         }
         container any {
           description "Include unicast or multicast NLRI";
           presence "enable any";
           uses bgp-afi-vpn;
         }
       }
       container iso-vpn {
         description "ISO Layer 3 VPN NLRI parameters";
         uses apply-advanced;
         container unicast {
           description "Include unicast NLRI";
           presence "enable unicast";
           uses bgp-afi-vpn-protection;
         }
       }
       container l2vpn {
         description "MPLS-based Layer 2 VPN and VPLS NLRI parameters";
         uses apply-advanced;
         container auto-discovery-only {
           description "Include auto-discovery NLRI for LDP Layer 2 VPN and VPLS";
           presence "enable auto-discovery-only";
           uses bgp-afi-default;
         }
         container auto-discovery-mspw {
           description "Include auto-discovery NLRI for LDP Signalled MultiSegment PW";
           presence "enable auto-discovery-mspw";
           uses bgp-afi-default;
         }
         container signaling {
           description "Include Layer 2 VPN and VPLS signaling NLRI";
           presence "enable signaling";
           uses bgp-afi-l2vpn;
         }
       }
       container evpn {
         description "EVPN NLRI parameters";
         uses apply-advanced;
         container signaling {
           description "Include EVPN signaling NLRI";
           presence "enable signaling";
           uses bgp-afi-default;
         }
       }
       container inet-mvpn {
         description "IPv4 MVPN NLRI parameters";
         uses apply-advanced;
         container signaling {
           description "Include IPv4 multicast VPN signaling NLRI";
           presence "enable signaling";
           uses bgp-afi-default;
         }
       }
       container inet6-mvpn {
         description "IPv6 MVPN NLRI parameters";
         uses apply-advanced;
         container signaling {
           description "Include IPv6 multicast VPN signaling NLRI";
           presence "enable signaling";
           uses bgp-afi-default;
         }
       }
       container inet-mdt {
         description "IPv4 Multicast Distribution Tree (MDT) NLRI parameters";
         uses apply-advanced;
         container signaling {
           description "Include IPv4 multicast VPN auto-discovery NLRI";
           presence "enable signaling";
           uses bgp-afi-default;
         }
       }
       container traffic-engineering {
         description "Traffic Engineering (BGP-TE) NLRI parameters";
         uses apply-advanced;
         container unicast {
           description "Include BGP-TE NLRI";
           presence "enable unicast";
           uses bgp-afi-default;
         }
       }
       container route-target {
         presence "enable route-target";
         description "Route target NLRI used for VPN route filtering";
         uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
         container nexthop-resolution {
           description "Configure nexthop resolution properties";
           uses apply-advanced;
           leaf no-resolution {
             description "Consider nexthop good without resolution attempt";
             type empty;
           }
         }
         container output-queue-priority {
           description "Default output-queue to assign updates to";
           uses bgp-output-queue-priority-class;
         }
         container route-refresh-priority {
           description "Default output-queue to assign route refreshes to";
           uses bgp-output-queue-priority-class;
         }
         container withdraw-priority {
           description "Default output-queue to assign withdrawn routes to";
           uses bgp-output-queue-priority-class;
         }
         leaf-list export {
           ordered-by user;
           description "Export policy";
           type jt:policy-algebra;
         }
         leaf-list import {
           ordered-by user;
           description "Import policy";
           type jt:policy-algebra;
         }
       }
       container inet-bgpmcast {
         description "IPv4 BGPMCAST NLRI parameters";
         uses apply-advanced;
         container signaling {
           description "Include IPv4 BGP multicast signaling NLRI";
           presence "enable signaling";
           uses bgp-afi-default;
         }
       }
       container inet6-bgpmcast {
         description "IPv6 BGPMCAST NLRI parameters";
         uses apply-advanced;
         container signaling {
           description "Include IPv6 BGP multicast signaling NLRI";
           presence "enable signaling";
           uses bgp-afi-default;
         }
       }
     }
     container egress-te {
       presence "enable egress-te";
       description "Use Egress Peering traffic engineering";
       uses apply-advanced;
       leaf install-address {
         description "Address to use in egress-te created inet route";
         type jt:ipaddr;
       }
       container rib {
         description "Select primary table for Egress-TE routes";
         uses apply-advanced;
         leaf inet.0 {
           description "Install Egress-TE routes in inet.0";
           type empty;
         }
         leaf inet6.0 {
           description "Install Egress-TE routes in inet6.0";
           type empty;
         }
       }
       leaf no-install {
         description "Avoid installation to FIB or resolving over";
         type empty;
       }
       leaf-list import {
         ordered-by user;
         description "Import policy to set attributes";
         type jt:policy-algebra;
       }
       leaf backup-path {
         description "The 'egress-te-backup-paths template' to use for this peer";
         type string {
         }
       }
     }
     leaf advertise-prefix-sid {
       description "Advertise prefix sid to E-BGP peers";
       type empty;
     }
     leaf accept-prefix-sid {
       description "Accept prefix sid from E-BGP peers";
       type empty;
     }
     leaf advertise-srgb {
       description "Advertise SRGB TLV";
       type empty;
     }
     leaf tcp-connect-port {
       description "TCP port number to connect with peer on";
       type union {
         type string {
           pattern "<.*>|$.*";
         }
         type uint16 {
           range "1 .. 65535";
         }
       }
     }
     leaf egress-te-sid-stats {
       description "Create BGP-Peer-SID sensor";
       type empty;
     }
     list egress-te-set-segment {
       key name;
       ordered-by user;
       description "Configure BGP-Peer-Set segment";
       leaf name {
         description "The BGP-Peer-Set segment name";
         type string {
         }
       }
       uses apply-advanced;
       container label {
         description "BGP-Peer-Set SID label from static label pool";
         uses apply-advanced;
         leaf label-value {
           description "BGP-Peer-Set SID label value from static label pool";
           type union {
             type string {
               pattern "<.*>|$.*";
             }
             type uint32 {
               range "16 .. 1048575";
             }
           }
         }
       }
       container egress-te-backup-segment {
         description "Backup segment for FRR";
         uses apply-advanced;
         container label {
           description "Backup segment label from static label pool";
           uses apply-advanced;
           leaf label-value {
             description "Backup segment label value from static label pool";
             type union {
               type string {
                 pattern "<.*>|$.*";
               }
               type uint32 {
                 range "16 .. 1048575";
               }
             }
           }
         }
       }
       container egress-te-backup-ip-forward {
         presence "enable egress-te-backup-ip-forward";
         description "Use IP-forward backup path for Egress TE";
         uses apply-advanced;
         leaf instance-name {
           description "Routing-instance to use as IP forward backup-path";
           type string {
           }
         }
       }
     }
     list group {
       key name;
       ordered-by user;
       description "Define a peer group";
       leaf name {
         description "Group name";
         type string;
       }
       uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
       container traceoptions {
         description "Trace options for BGP";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "damping" {
                 description "Trace BGP damping information";
               }
               enum "packets" {
                 description "Trace all BGP protocol packets";
               }
               enum "open" {
                 description "Trace BGP open packets";
               }
               enum "update" {
                 description "Trace BGP update packets";
               }
               enum "keepalive" {
                 description "Trace BGP keepalive packets";
               }
               enum "refresh" {
                 description "Trace BGP refresh packets";
               }
               enum "nsr-synchronization" {
                 description "Trace NSR synchronization events";
               }
               enum "bfd" {
                 description "Trace BFD events";
               }
               enum "4byte-as" {
                 description "Trace 4 byte AS events";
               }
               enum "add-path" {
                 description "Trace add-path events";
               }
               enum "graceful-restart" {
                 description "Trace Graceful Restart events";
               }
               enum "egress-te" {
                 description "Egress Peering Traffic-Engineering events";
               }
               enum "thread-io" {
                 description "Trace threaded I/O processing";
               }
               enum "sharding" {
                 description "Trace BGP rib sharding";
               }
               enum "glb" {
                 description "Trace BGP global-load-balancing";
               }
               enum "thread-update-io" {
                 description "Trace threaded update I/O processing";
               }
               enum "route-validation" {
                 description "Trace route validation";
               }
               enum "ipsec" {
                 description "Trace ipsec";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
           container filter {
             description "Filter to apply to this flag";
             presence "enable filter";
             uses bgp_filter_obj;
           }
         }
       }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
           case case_4 {
             container effective-aigp {
               presence "enable effective-aigp";
               description "Track the effective AIGP metric";
               leaf metric-offset {
                 description "Metric offset for MED";
                 type union {
                   type int32;
                   type string {
                     pattern "<.*>|$.*";
                   }
                 }
               }
             }
           }
           case case_5 {
             container minimum-effective-aigp {
               presence "enable minimum-effective-aigp";
               description "Track the minimum effective AIGP metric";
               leaf metric-offset {
                 description "Metric offset for MED";
                 type union {
                   type int32;
                   type string {
                     pattern "<.*>|$.*";
                   }
                 }
               }
             }
           }
         }
       }
       container multihop {
         presence "enable multihop";
         description "Configure an EBGP multihop session";
         uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       container ebgp-community-cleanup {
         presence "enable ebgp-community-cleanup";
         description "Community specific cleanup for eBGP peers";
         uses apply-advanced;
         leaf origin-validation {
           description "Origin Validation State receive behavior";
           type enumeration {
             enum "accept" {
               description "Accept Origin Validation State Community";
             }
             enum "reject" {
               description "Reject Origin Validation State Community";
             }
           }
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
         }
       }
       leaf hold-time {
         description "Hold time used when negotiating with a peer";
         type union {
           type string {
             pattern "<.*>|$.*";
           }
           type uint32 {
             range "0 .. 65535";
           }
         }
       }
       leaf minimum-hold-time {
         description "Minimum hold time accepted from the peer";
         type union {
           type string {
             pattern "<.*>|$.*";
           }
           type uint32 {
             range "3 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly, enabled by default. Configure logging parameters";
         uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         uses apply-advanced;
         container inet {
           description "IPv4 NLRI parameters";
           uses apply-advanced;
           container labeled-unicast {
             description "Include labeled unicast NLRI";
             presence "enable labeled-unicast";
             uses bgp-afi-labeled;
           }
           container segment-routing-te {
             description "Include segment-routing TE policy";
             presence "enable segment-routing-te";
             uses bgp-afi-srte;
           }
           container transport {
             description "Include Classful Transport NLRI";
             presence "enable transport";
             uses bgp-afi-inet-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow-with-redirect-ip-action;
           }
           container any {
             description "Include unicast or multicast NLRI";
             presence "enable any";
             uses bgp-afi-default;
           }
         }
         container inet-vpn {
           description "IPv4 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow-with-redirect-ip-action;
           }
           container any {
             description "Include unicast or multicast NLRI";
             presence "enable any";
             uses bgp-afi-vpn;
           }
         }
         container inet6 {
           description "IPv6 NLRI parameters";
           uses apply-advanced;
           container labeled-unicast {
             description "Include labeled unicast NLRI";
             presence "enable labeled-unicast";
             uses bgp-afi-inet6-labeled;
           }
           container segment-routing-te {
             description "Include segment-routing TE policy";
             presence "enable segment-routing-te";
             uses bgp-afi-srte;
           }
           container transport {
             description "Include Classful Transport NLRI";
             presence "enable transport";
             uses bgp-afi-inet6-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow;
           }
           container any {
             description "Include unicast or multicast NLRI";
             presence "enable any";
             uses bgp-afi-default;
           }
         }
         container inet6-vpn {
           description "IPv6 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow;
           }
           container any {
             description "Include unicast or multicast NLRI";
             presence "enable any";
             uses bgp-afi-vpn;
           }
         }
         container iso-vpn {
           description "ISO Layer 3 VPN NLRI parameters";
           uses apply-advanced;
           container unicast {
             description "Include unicast NLRI";
             presence "enable unicast";
             uses bgp-afi-vpn-protection;
           }
         }
         container l2vpn {
           description "MPLS-based Layer 2 VPN and VPLS NLRI parameters";
           uses apply-advanced;
           container auto-discovery-only {
             description "Include auto-discovery NLRI for LDP Layer 2 VPN and VPLS";
             presence "enable auto-discovery-only";
             uses bgp-afi-default;
           }
           container auto-discovery-mspw {
             description "Include auto-discovery NLRI for LDP Signalled MultiSegment PW";
             presence "enable auto-discovery-mspw";
             uses bgp-afi-default;
           }
           container signaling {
             description "Include Layer 2 VPN and VPLS signaling NLRI";
             presence "enable signaling";
             uses bgp-afi-l2vpn;
           }
         }
         container evpn {
           description "EVPN NLRI parameters";
           uses apply-advanced;
           container signaling {
             description "Include EVPN signaling NLRI";
             presence "enable signaling";
             uses bgp-afi-default;
           }
         }
         container inet-mvpn {
           description "IPv4 MVPN NLRI parameters";
           uses apply-advanced;
           container signaling {
             description "Include IPv4 multicast VPN signaling NLRI";
             presence "enable signaling";
             uses bgp-afi-default;
           }
         }
         container inet6-mvpn {
           description "IPv6 MVPN NLRI parameters";
           uses apply-advanced;
           container signaling {
             description "Include IPv6 multicast VPN signaling NLRI";
             presence "enable signaling";
             uses bgp-afi-default;
           }
         }
         container inet-mdt {
           description "IPv4 Multicast Distribution Tree (MDT) NLRI parameters";
           uses apply-advanced;
           container signaling {
             description "Include IPv4 multicast VPN auto-discovery NLRI";
             presence "enable signaling";
             uses bgp-afi-default;
           }
         }
         container traffic-engineering {
           description "Traffic Engineering (BGP-TE) NLRI parameters";
           uses apply-advanced;
           container unicast {
             description "Include BGP-TE NLRI";
             presence "enable unicast";
             uses bgp-afi-default;
           }
         }
         container route-target {
           presence "enable route-target";
           description "Route target NLRI used for VPN route filtering";
           uses apply-advanced;
           container prefix-limit {
             description "Limit maximum number of prefixes from a peer";
             uses bgpaf-prefix-limit;
           }
           container accepted-prefix-limit {
             description "Limit maximum number of prefixes accepted from a peer";
             uses bgpaf-accepted-prefix-limit;
           }
           container proxy-generate {
             presence "enable proxy-generate";
             description "Generate route target NLRI for peers that don't support it";
             uses apply-advanced;
             leaf-list route-target-policy {
               ordered-by user;
               description "Limit VPN routes that are used to generate proxy route-target filters";
               type jt:policy-algebra;
             }
           }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container nexthop-resolution {
             description "Configure nexthop resolution properties";
             uses apply-advanced;
             leaf no-resolution {
               description "Consider nexthop good without resolution attempt";
               type empty;
             }
           }
           container output-queue-priority {
             description "Default output-queue to assign updates to";
             uses bgp-output-queue-priority-class;
           }
           container route-refresh-priority {
             description "Default output-queue to assign route refreshes to";
             uses bgp-output-queue-priority-class;
           }
           container withdraw-priority {
             description "Default output-queue to assign withdrawn routes to";
             uses bgp-output-queue-priority-class;
           }
           leaf-list export {
             ordered-by user;
             description "Export policy";
             type jt:policy-algebra;
           }
           leaf-list import {
             ordered-by user;
             description "Import policy";
             type jt:policy-algebra;
           }
         }
         container inet-bgpmcast {
           description "IPv4 BGPMCAST NLRI parameters";
           uses apply-advanced;
           container signaling {
             description "Include IPv4 BGP multicast signaling NLRI";
             presence "enable signaling";
             uses bgp-afi-default;
           }
         }
         container inet6-bgpmcast {
           description "IPv6 BGPMCAST NLRI parameters";
           uses apply-advanced;
           container signaling {
             description "Include IPv6 BGP multicast signaling NLRI";
             presence "enable signaling";
             uses bgp-afi-default;
           }
         }
       }
       leaf authentication-key {
         description "MD5 authentication key";
         type string {
           length "1 .. 126";
         }
       }
       leaf authentication-algorithm {
         description "Authentication algorithm name";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         type enumeration {
           enum "allow-without-tcpao" {
             description "Allow the connection establishment without TCP-AO";
           }
         }
       }
       leaf authentication-key-chain {
         description "Key chain name";
         type string {
           length "1 .. 128";
         }
       }
       leaf-list export {
         ordered-by user;
         description "Export policy";
         type jt:policy-algebra;
       }
       container remove-private {
         presence "enable remove-private";
         description "Remove well-known private AS numbers";
         uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
         }
       }
       container local-as {
         description "Local autonomous system number";
         leaf as-number {
           description " Autonomous system number in plain number or 'higher 16bits'.'Lower 16 bits' (asdot notation) format";
           type string {
           }
           //mandatory true;
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
       leaf ipsec-sa {
         description "IPSec SA name";
         type string {
           length "1 .. 32";
         }
       }
       container graceful-shutdown {
         description "BGP peer graceful shutdown option";
         uses apply-advanced;
         container receiver {
           presence "enable receiver";
           description "BGP peer graceful-shutdown receiver";
           uses apply-advanced;
           leaf disable {
             description "Disable graceful-shutdown receiver";
             type empty;
           }
           leaf local-preference {
             description "Value of receiver LOCAL_PREF path attribute";
             type union {
               type uint32;
               type string {
                 pattern "<.*>|$.*";
               }
             }
           }
         }
         container sender {
           presence "enable sender";
           description "BGP peer graceful-shutdown sender";
           uses apply-advanced;
           leaf local-preference {
             description "Value of sender LOCAL_PREF path attribute";
             type union {
               type uint32;
               type string {
                 pattern "<.*>|$.*";
               }
             }
           }
         }
       }
       container shutdown {
         presence "enable shutdown";
         description "Shutdown";
         uses apply-advanced;
         leaf notify-message {
           description "Notification message";
           type string;
         }
       }
       leaf unconfigured-peer-graceful-restart {
         description "BGP unconfigured peer graceful restart options";
         type empty;
       }
       container graceful-restart {
         presence "enable graceful-restart";
         description "BGP graceful restart options";
         uses apply-advanced;
         choice enable-disable {
           case case_1 {
             leaf disable {
               description "Disable graceful restart";
               type empty;
             }
           }
         }
         leaf restart-time {
           description "Restart time used when negotiating with a peer";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           uses apply-advanced;
           container receiver {
             description "Long-lived graceful restart receiver (helper) options";
             uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             uses apply-advanced;
             leaf omit-no-export {
               description "Do not attach no-export community to stale routes";
               type empty;
             }
           }
         }
         leaf disable-notification-extensions {
           description "Disable notification extensions";
           type empty;
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       leaf disable-4byte-as {
         description "Disable 4 byte AS capability advertisement";
         type empty;
       }
       container idle-after-switch-over {
         description "Stop peer session from coming up after nonstop-routing switch-over";
         choice idle-interval {
           case case_1 {
             leaf forever {
               description "Idle the peer until the user intervenes";
               type empty;
             }
           }
           case case_2 {
             leaf timeout {
               description "Timeout value, in seconds, for starting peer after switch over";
               type union {
                 type string {
                   pattern "<.*>|$.*";
                 }
                 type uint32 {
                   range "1 .. 4294967295";
                 }
               }
             }
           }
         }
       }
       container outbound-route-filter {
         description "Dynamically negotiated cooperative route filtering";
         uses apply-advanced;
         leaf bgp-orf-cisco-mode {
           description "Using BGP ORF capability code 130 and Prefix ORF type 128";
           type empty;
         }
         container extended-community {
           description "Extended community filtering";
           status deprecated;
           uses apply-advanced;
           choice accept-choice {
             leaf accept {
               description "Honor remote requests for extended community ORF";
               type empty;
             }
             leaf no-accept {
               description "Don't honor remote requests for extended community ORF";
               type empty;
             }
           }
           leaf vrf-filter {
             description "Request remote filtering using locally configured VRF import targets";
             type empty;
           }
         }
         container prefix-based {
           presence "enable prefix-based";
           description "Prefix-based outbound route filtering";
           uses apply-advanced;
           container accept {
             presence "enable accept";
             description "Honor Prefix-based ORFs from remote peers";
             uses apply-advanced;
             leaf inet {
               description "Honor IPv4 prefix filters";
               type empty;
             }
             leaf inet6 {
               description "Honor IPv6 prefix filters";
               type empty;
             }
           }
         }
       }
       container message-batching {
         description "DEPRECATED - Batching of outgoing messages";
         status deprecated;
         uses apply-advanced;
         choice enable-disable {
           case case_1 {
             leaf enable {
               description "Enable parameter";
               type empty;
             }
           }
           case case_2 {
             leaf disable {
               description "Disable parameter";
               type empty;
             }
           }
         }
         leaf interval {
           description "DEPRECATED - Interval over which to batch messages";
           default "250";
           units "milliseconds";
           type union {
             type string {
               pattern "<.*>|$.*";
             }
             type uint32 {
               range "100 .. 1000";
             }
           }
         }
       }
       container multipath {
         presence "enable multipath";
         description "Allow load sharing among multiple BGP paths";
         uses apply-advanced;
         leaf disable {
           description "Disable Multipath";
           type empty;
         }
         leaf multiple-as {
           description "Use paths received from different ASs";
           type empty;
         }
         leaf allow-protection {
           description "Allow protection for multipath legs";
           type empty;
         }
         leaf pause-computation-during-churn {
           description "Pause multipath job to absorb churn";
           type empty;
         }
         leaf list-nexthop {
           description "Use List-NH for homogenous nexthop-set also";
           type empty;
         }
         container allow-external-internal {
           presence "enable allow-external-internal";
           description "Allow multipath to mix EBGP and IBGP routes";
           uses apply-advanced;
           leaf-list prefix-policy {
             ordered-by user;
             description "Policy to constrain prefixes that apply";
             type jt:policy-algebra;
           }
         }
       }
       leaf tcp-mss {
         description "Maximum TCP segment size";
         type union {
           type string {
             pattern "<.*>|$.*";
           }
           type uint32 {
             range "1 .. 4096";
           }
         }
       }
       leaf bgp-identifier {
         description "BGP Identifier";
         type jt:ipv4addr;
       }
       leaf tcp-aggressive-transmission {
         description "Enable aggressive transmission of pure TCP ACKs and retransmissions";
         type empty;
       }
       container bmp {
         description "Specific settings to override the routing-options settings";
         uses apply-advanced;
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             type empty;
           }
           container pre-policy {
             presence "enable pre-policy";
             description "Send pre-policy route monitoring messages";
             leaf exclude-non-feasible {
               description "Exclude looped routes, etc";
               type empty;
             }
           }
           container post-policy {
             presence "enable post-policy";
             description "Send post-policy route monitoring messages";
             leaf exclude-non-eligible {
               description "Exclude unresolved routes, etc.";
               type empty;
             }
           }
           container rib-out {
             presence "enable rib-out";
             description "Send adj-ribs-out route monitoring messages";
             leaf pre-policy {
               description "Send pre-policy adj-ribs-out route monitoring messages";
               type empty;
             }
             leaf post-policy {
               description "Send post-policy adj-ribs-out route monitoring messages";
               type empty;
             }
           }
         }
       }
       container advertise-bgp-static {
         presence "enable advertise-bgp-static";
         description "Advertise bgp-static routes";
         uses apply-advanced;
         leaf-list policy {
           ordered-by user;
           description "Static route advertisement policy";
           type jt:policy-algebra;
         }
       }
       leaf add-path-display-ipv4-address {
         description "Display add-path path-id in IPv4 address format";
         type empty;
       }
       container domain-path-id {
         description "Domain path id attribute";
         uses apply-advanced;
         leaf send {
           description "Allow sending domain path id attribute";
           type empty;
         }
         leaf receive {
           description "Allow receiving domain path id attribute";
           type empty;
         }
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         container echo {
           description "Echo mode parameters";
           uses apply-advanced;
           leaf minimum-interval {
             description "Minimum transmit and receive interval";
             units "milliseconds";
             type union {
               type string {
                 pattern "<.*>|$.*";
               }
               type uint32 {
                 range "100 .. 255000";
               }
             }
             //mandatory true;
           }
         }
         container echo-lite {
           description "Echo-lite more parameters";
           uses apply-advanced;
           leaf minimum-interval {
             description "Minimum transmit and receive interval";
             units "milliseconds";
             type union {
               type string {
                 pattern "<.*>|$.*";
               }
               type uint32 {
                 range "100 .. 255000";
               }
             }
             //mandatory true;
           }
         }
         container strict-bfd {
           presence "enable strict-bfd";
           description "Bgp session waits for bfd";
           uses apply-advanced;
           leaf bfd-up-wait-interval {
             description "Time to wait for bfd to come up";
             units "seconds";
             type union {
               type string {
                 pattern "<.*>|$.*";
               }
               type uint32 {
                 range "10 .. 255";
               }
             }
           }
         }
         leaf holddown-interval {
           description "Time to hold the session-UP notification to the client";
           units "milliseconds";
           type union {
             type string {
               pattern "<.*>|$.*";
             }
             type uint32 {
               range "0 .. 255000";
             }
           }
         }
       }
       leaf as-override {
         description "Replace neighbor AS number with our AS number";
         type empty;
       }
       container link-bandwidth {
         description "Configure link-bandwidth options";
         uses apply-advanced;
         container auto-sense {
           presence "enable auto-sense";
           uses apply-advanced;
           leaf hold-down {
             description "Hold down in secs for link bandwidth auto-sense";
             type union {
               type string {
                 pattern "<.*>|$.*";
               }
               type uint32 {
                 range "0 .. 3600";
               }
             }
           }
         }
       }
       leaf-list allow {
         ordered-by user;
         description "Configure peer connections for specific networks";
         type jt:ipprefix;
       }
       list dynamic-neighbor {
         key name;
         ordered-by user;
         description "Configure peer options for specific networks";
         leaf name {
           description "Template name";
           type string;
         }
         uses apply-advanced;
         leaf-list allow {
           ordered-by user;
           description "Configure peer connections for specific networks";
           type jt:ipprefix;
         }
         leaf peer-limit {
           description "Limit the number of peers for each subnet configured via dynamic-neighbor";
           type union {
             type string {
               pattern "<.*>|$.*";
             }
             type uint32 {
               range "0 .. 2048";
             }
           }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         container peer-auto-discovery {
           description "Configure auto-discovery options for BGP neighbors";
           uses apply-advanced;
           container family {
             description "Address family based neighbor auto-discovery parameters";
             container inet6 {
               uses apply-advanced;
               choice auto-discovery-type {
                 case case_1 {
                   container ipv6-nd {
                     presence "enable ipv6-nd";
                     description "Use ipv6 neighbor discovery to learn neighbor address";
                   }
                 }
               }
             }
           }
           list interface {
             key name;
             leaf name {
               description "Configure interfaces over which to discover bgp neighbors";
               type union {
                 type jt:interface-name;
                 type string {
                   pattern "<.*>|$.*";
                 }
               }
             }
             uses apply-advanced;
             choice enable-disable {
               case case_1 {
                 leaf disable {
                   description "Disable peer discovery on interface";
                   type empty;
                 }
               }
             }
           }
         }
       }
       container optimal-route-reflection {
         description "Enable optimal route reflection for this client group";
         uses apply-advanced;
         leaf igp-primary {
           description "Primary node identifier for this client group";
           type jt:ipv4addr;
         }
         leaf igp-backup {
           description "Backup node identifier for this client group";
           type jt:ipv4addr;
         }
         leaf-list export {
           description "Optimal route reflection export policy";
           type jt:policy-algebra;
         }
       }
       leaf peer-as-list {
         description "Configure list of peer autonomous systems for unconfigured neighbors";
         type string;
       }
       leaf send-non-transitive-link-bandwidth {
         description "Allow sending non transitive link-bandwidth to EBGP peers";
         type empty;
       }
       leaf mvpn-iana-rt-import {
         description "Use IANA assigned rt-import type value for MVPN";
         status deprecated;
         type empty;
       }
       list neighbor {
         key name;
         ordered-by user;
         description "Configure a neighbor";
         leaf name {
           type jt:ipaddr-scoped;
         }
         uses apply-advanced;
         container traceoptions {
           description "Trace options for BGP";
           uses apply-advanced;
           container file {
             description "Trace file options";
             leaf filename {
               description "Name of file in which to write trace information";
               type string {
                 length "1 .. 1024";
               }
               //mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "damping" {
                   description "Trace BGP damping information";
                 }
                 enum "packets" {
                   description "Trace all BGP protocol packets";
                 }
                 enum "open" {
                   description "Trace BGP open packets";
                 }
                 enum "update" {
                   description "Trace BGP update packets";
                 }
                 enum "keepalive" {
                   description "Trace BGP keepalive packets";
                 }
                 enum "refresh" {
                   description "Trace BGP refresh packets";
                 }
                 enum "nsr-synchronization" {
                   description "Trace NSR synchronization events";
                 }
                 enum "bfd" {
                   description "Trace BFD events";
                 }
                 enum "4byte-as" {
                   description "Trace 4 byte AS events";
                 }
                 enum "add-path" {
                   description "Trace add-path events";
                 }
                 enum "graceful-restart" {
                   description "Trace Graceful Restart events";
                 }
                 enum "egress-te" {
                   description "Egress Peering Traffic-Engineering events";
                 }
                 enum "thread-io" {
                   description "Trace threaded I/O processing";
                 }
                 enum "sharding" {
                   description "Trace BGP rib sharding";
                 }
                 enum "glb" {
                   description "Trace BGP global-load-balancing";
                 }
                 enum "thread-update-io" {
                   description "Trace threaded update I/O processing";
                 }
                 enum "route-validation" {
                   description "Trace route validation";
                 }
                 enum "ipsec" {
                   description "Trace ipsec";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
             container filter {
               description "Filter to apply to this flag";
               presence "enable filter";
               uses bgp_filter_obj;
             }
           }
         }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
             case case_4 {
               container effective-aigp {
                 presence "enable effective-aigp";
                 description "Track the effective AIGP metric";
                 leaf metric-offset {
                   description "Metric offset for MED";
                   type union {
                     type int32;
                     type string {
                       pattern "<.*>|$.*";
                     }
                   }
                 }
               }
             }
             case case_5 {
               container minimum-effective-aigp {
                 presence "enable minimum-effective-aigp";
                 description "Track the minimum effective AIGP metric";
                 leaf metric-offset {
                   description "Metric offset for MED";
                   type union {
                     type int32;
                     type string {
                       pattern "<.*>|$.*";
                     }
                   }
                 }
               }
             }
           }
         }
         container multihop {
           presence "enable multihop";
           description "Configure an EBGP multihop session";
           uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         container ebgp-community-cleanup {
           presence "enable ebgp-community-cleanup";
           description "Community specific cleanup for eBGP peers";
           uses apply-advanced;
           leaf origin-validation {
             description "Origin Validation State receive behavior";
             type enumeration {
               enum "accept" {
                 description "Accept Origin Validation State Community";
               }
               enum "reject" {
                 description "Reject Origin Validation State Community";
               }
             }
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
           }
         }
         leaf hold-time {
           description "Hold time used when negotiating with a peer";
           type union {
             type string {
               pattern "<.*>|$.*";
             }
             type uint32 {
               range "0 .. 65535";
             }
           }
         }
         leaf minimum-hold-time {
           description "Minimum hold time accepted from the peer";
           type union {
             type string {
               pattern "<.*>|$.*";
             }
             type uint32 {
               range "3 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly, enabled by default. Configure logging parameters";
           uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           uses apply-advanced;
           container inet {
             description "IPv4 NLRI parameters";
             uses apply-advanced;
             container labeled-unicast {
               description "Include labeled unicast NLRI";
               presence "enable labeled-unicast";
               uses bgp-afi-labeled;
             }
             container segment-routing-te {
               description "Include segment-routing TE policy";
               presence "enable segment-routing-te";
               uses bgp-afi-srte;
             }
             container transport {
               description "Include Classful Transport NLRI";
               presence "enable transport";
               uses bgp-afi-inet-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow-with-redirect-ip-action;
             }
             container any {
               description "Include unicast or multicast NLRI";
               presence "enable any";
               uses bgp-afi-default;
             }
           }
           container inet-vpn {
             description "IPv4 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow-with-redirect-ip-action;
             }
             container any {
               description "Include unicast or multicast NLRI";
               presence "enable any";
               uses bgp-afi-vpn;
             }
           }
           container inet6 {
             description "IPv6 NLRI parameters";
             uses apply-advanced;
             container labeled-unicast {
               description "Include labeled unicast NLRI";
               presence "enable labeled-unicast";
               uses bgp-afi-inet6-labeled;
             }
             container segment-routing-te {
               description "Include segment-routing TE policy";
               presence "enable segment-routing-te";
               uses bgp-afi-srte;
             }
             container transport {
               description "Include Classful Transport NLRI";
               presence "enable transport";
               uses bgp-afi-inet6-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow;
             }
             container any {
               description "Include unicast or multicast NLRI";
               presence "enable any";
               uses bgp-afi-default;
             }
           }
           container inet6-vpn {
             description "IPv6 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow;
             }
             container any {
               description "Include unicast or multicast NLRI";
               presence "enable any";
               uses bgp-afi-vpn;
             }
           }
           container iso-vpn {
             description "ISO Layer 3 VPN NLRI parameters";
             uses apply-advanced;
             container unicast {
               description "Include unicast NLRI";
               presence "enable unicast";
               uses bgp-afi-vpn-protection;
             }
           }
           container l2vpn {
             description "MPLS-based Layer 2 VPN and VPLS NLRI parameters";
             uses apply-advanced;
             container auto-discovery-only {
               description "Include auto-discovery NLRI for LDP Layer 2 VPN and VPLS";
               presence "enable auto-discovery-only";
               uses bgp-afi-default;
             }
             container auto-discovery-mspw {
               description "Include auto-discovery NLRI for LDP Signalled MultiSegment PW";
               presence "enable auto-discovery-mspw";
               uses bgp-afi-default;
             }
             container signaling {
               description "Include Layer 2 VPN and VPLS signaling NLRI";
               presence "enable signaling";
               uses bgp-afi-l2vpn;
             }
           }
           container evpn {
             description "EVPN NLRI parameters";
             uses apply-advanced;
             container signaling {
               description "Include EVPN signaling NLRI";
               presence "enable signaling";
               uses bgp-afi-default;
             }
           }
           container inet-mvpn {
             description "IPv4 MVPN NLRI parameters";
             uses apply-advanced;
             container signaling {
               description "Include IPv4 multicast VPN signaling NLRI";
               presence "enable signaling";
               uses bgp-afi-default;
             }
           }
           container inet6-mvpn {
             description "IPv6 MVPN NLRI parameters";
             uses apply-advanced;
             container signaling {
               description "Include IPv6 multicast VPN signaling NLRI";
               presence "enable signaling";
               uses bgp-afi-default;
             }
           }
           container inet-mdt {
             description "IPv4 Multicast Distribution Tree (MDT) NLRI parameters";
             uses apply-advanced;
             container signaling {
               description "Include IPv4 multicast VPN auto-discovery NLRI";
               presence "enable signaling";
               uses bgp-afi-default;
             }
           }
           container traffic-engineering {
             description "Traffic Engineering (BGP-TE) NLRI parameters";
             uses apply-advanced;
             container unicast {
               description "Include BGP-TE NLRI";
               presence "enable unicast";
               uses bgp-afi-default;
             }
           }
           container route-target {
             presence "enable route-target";
             description "Route target NLRI used for VPN route filtering";
             uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container nexthop-resolution {
               description "Configure nexthop resolution properties";
               uses apply-advanced;
               leaf no-resolution {
                 description "Consider nexthop good without resolution attempt";
                 type empty;
               }
             }
             container output-queue-priority {
               description "Default output-queue to assign updates to";
               uses bgp-output-queue-priority-class;
             }
             container route-refresh-priority {
               description "Default output-queue to assign route refreshes to";
               uses bgp-output-queue-priority-class;
             }
             container withdraw-priority {
               description "Default output-queue to assign withdrawn routes to";
               uses bgp-output-queue-priority-class;
             }
             leaf-list export {
               ordered-by user;
               description "Export policy";
               type jt:policy-algebra;
             }
             leaf-list import {
               ordered-by user;
               description "Import policy";
               type jt:policy-algebra;
             }
           }
           container inet-bgpmcast {
             description "IPv4 BGPMCAST NLRI parameters";
             uses apply-advanced;
             container signaling {
               description "Include IPv4 BGP multicast signaling NLRI";
               presence "enable signaling";
               uses bgp-afi-default;
             }
           }
           container inet6-bgpmcast {
             description "IPv6 BGPMCAST NLRI parameters";
             uses apply-advanced;
             container signaling {
               description "Include IPv6 BGP multicast signaling NLRI";
               presence "enable signaling";
               uses bgp-afi-default;
             }
           }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         leaf-list export {
           ordered-by user;
           description "Export policy";
           type jt:policy-algebra;
         }
         container remove-private {
           presence "enable remove-private";
           description "Remove well-known private AS numbers";
           uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
           }
         }
         container local-as {
           description "Local autonomous system number";
           leaf as-number {
             description " Autonomous system number in plain number or 'higher 16bits'.'Lower 16 bits' (asdot notation) format";
             type string {
             }
             //mandatory true;
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           type string {
             length "1 .. 32";
           }
         }
         container graceful-shutdown {
           description "BGP peer graceful shutdown option";
           uses apply-advanced;
           container receiver {
             presence "enable receiver";
             description "BGP peer graceful-shutdown receiver";
             uses apply-advanced;
             leaf disable {
               description "Disable graceful-shutdown receiver";
               type empty;
             }
             leaf local-preference {
               description "Value of receiver LOCAL_PREF path attribute";
               type union {
                 type uint32;
                 type string {
                   pattern "<.*>|$.*";
                 }
               }
             }
           }
           container sender {
             presence "enable sender";
             description "BGP peer graceful-shutdown sender";
             uses apply-advanced;
             leaf local-preference {
               description "Value of sender LOCAL_PREF path attribute";
               type union {
                 type uint32;
                 type string {
                   pattern "<.*>|$.*";
                 }
               }
             }
           }
         }
         container shutdown {
           presence "enable shutdown";
           description "Shutdown";
           uses apply-advanced;
           leaf notify-message {
             description "Notification message";
             type string;
           }
         }
         leaf unconfigured-peer-graceful-restart {
           description "BGP unconfigured peer graceful restart options";
           type empty;
         }
         container graceful-restart {
           presence "enable graceful-restart";
           description "BGP graceful restart options";
           uses apply-advanced;
           choice enable-disable {
             case case_1 {
               leaf disable {
                 description "Disable graceful restart";
                 type empty;
               }
             }
           }
           leaf restart-time {
             description "Restart time used when negotiating with a peer";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             uses apply-advanced;
             container receiver {
               description "Long-lived graceful restart receiver (helper) options";
               uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               uses apply-advanced;
               leaf omit-no-export {
                 description "Do not attach no-export community to stale routes";
                 type empty;
               }
             }
           }
           leaf disable-notification-extensions {
             description "Disable notification extensions";
             type empty;
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         leaf disable-4byte-as {
           description "Disable 4 byte AS capability advertisement";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           description "Dynamically negotiated cooperative route filtering";
           uses apply-advanced;
           leaf bgp-orf-cisco-mode {
             description "Using BGP ORF capability code 130 and Prefix ORF type 128";
             type empty;
           }
           container extended-community {
             description "Extended community filtering";
             status deprecated;
             uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             uses apply-advanced;
             container accept {
               presence "enable accept";
               description "Honor Prefix-based ORFs from remote peers";
               uses apply-advanced;
               leaf inet {
                 description "Honor IPv4 prefix filters";
                 type empty;
               }
               leaf inet6 {
                 description "Honor IPv6 prefix filters";
                 type empty;
               }
             }
           }
         }
         container message-batching {
           description "DEPRECATED - Batching of outgoing messages";
           status deprecated;
           uses apply-advanced;
           choice enable-disable {
             case case_1 {
               leaf enable {
                 description "Enable parameter";
                 type empty;
               }
             }
             case case_2 {
               leaf disable {
                 description "Disable parameter";
                 type empty;
               }
             }
           }
           leaf interval {
             description "DEPRECATED - Interval over which to batch messages";
             default "250";
             units "milliseconds";
             type union {
               type string {
                 pattern "<.*>|$.*";
               }
               type uint32 {
                 range "100 .. 1000";
               }
             }
           }
         }
         container multipath {
           presence "enable multipath";
           description "Allow load sharing among multiple BGP paths";
           uses apply-advanced;
           leaf disable {
             description "Disable Multipath";
             type empty;
           }
           leaf multiple-as {
             description "Use paths received from different ASs";
             type empty;
           }
           leaf allow-protection {
             description "Allow protection for multipath legs";
             type empty;
           }
           leaf pause-computation-during-churn {
             description "Pause multipath job to absorb churn";
             type empty;
           }
           leaf list-nexthop {
             description "Use List-NH for homogenous nexthop-set also";
             type empty;
           }
           container allow-external-internal {
             presence "enable allow-external-internal";
             description "Allow multipath to mix EBGP and IBGP routes";
             uses apply-advanced;
             leaf-list prefix-policy {
               ordered-by user;
               description "Policy to constrain prefixes that apply";
               type jt:policy-algebra;
             }
           }
         }
         leaf tcp-mss {
           description "Maximum TCP segment size";
           type union {
             type string {
               pattern "<.*>|$.*";
             }
             type uint32 {
               range "1 .. 4096";
             }
           }
         }
         leaf bgp-identifier {
           description "BGP Identifier";
           type jt:ipv4addr;
         }
         leaf tcp-aggressive-transmission {
           description "Enable aggressive transmission of pure TCP ACKs and retransmissions";
           type empty;
         }
         container bmp {
           description "Specific settings to override the routing-options settings";
           uses apply-advanced;
           leaf monitor {
             description "Enable/Disable monitoring";
             type enumeration {
               enum "enable" {
                 description "Enable monitoring of BGP peer(s)";
               }
               enum "disable" {
                 description "Disable monitoring of BGP peer(s)";
               }
             }
           }
           container route-monitoring {
             description "Control route monitoring settings";
             uses apply-advanced;
             leaf none {
               description "Do not send route monitoring messages";
               type empty;
             }
             container pre-policy {
               presence "enable pre-policy";
               description "Send pre-policy route monitoring messages";
               leaf exclude-non-feasible {
                 description "Exclude looped routes, etc";
                 type empty;
               }
             }
             container post-policy {
               presence "enable post-policy";
               description "Send post-policy route monitoring messages";
               leaf exclude-non-eligible {
                 description "Exclude unresolved routes, etc.";
                 type empty;
               }
             }
             container rib-out {
               presence "enable rib-out";
               description "Send adj-ribs-out route monitoring messages";
               leaf pre-policy {
                 description "Send pre-policy adj-ribs-out route monitoring messages";
                 type empty;
               }
               leaf post-policy {
                 description "Send post-policy adj-ribs-out route monitoring messages";
                 type empty;
               }
             }
           }
         }
         container advertise-bgp-static {
           presence "enable advertise-bgp-static";
           description "Advertise bgp-static routes";
           uses apply-advanced;
           leaf-list policy {
             ordered-by user;
             description "Static route advertisement policy";
             type jt:policy-algebra;
           }
         }
         leaf add-path-display-ipv4-address {
           description "Display add-path path-id in IPv4 address format";
           type empty;
         }
         container domain-path-id {
           description "Domain path id attribute";
           uses apply-advanced;
           leaf send {
             description "Allow sending domain path id attribute";
             type empty;
           }
           leaf receive {
             description "Allow receiving domain path id attribute";
             type empty;
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container strict-bfd {
             presence "enable strict-bfd";
             description "Bgp session waits for bfd";
             uses apply-advanced;
             leaf bfd-up-wait-interval {
               description "Time to wait for bfd to come up";
               units "seconds";
               type union {
                 type string {
                   pattern "<.*>|$.*";
                 }
                 type uint32 {
                   range "10 .. 255";
                 }
               }
             }
           }
           leaf holddown-interval {
             description "Time to hold the session-UP notification to the client";
             units "milliseconds";
             type union {
               type string {
                 pattern "<.*>|$.*";
               }
               type uint32 {
                 range "0 .. 255000";
               }
             }
           }
         }
         leaf as-override {
           description "Replace neighbor AS number with our AS number";
           type empty;
         }
         container link-bandwidth {
           description "Configure link-bandwidth options";
           uses apply-advanced;
           container auto-sense {
             presence "enable auto-sense";
             uses apply-advanced;
             leaf hold-down {
               description "Hold down in secs for link bandwidth auto-sense";
               type union {
                 type string {
                   pattern "<.*>|$.*";
                 }
                 type uint32 {
                   range "0 .. 3600";
                 }
               }
             }
           }
         }
         leaf no-global-load-balancing {
           description "Disable glabl load balancing";
           type empty;
         }
         container egress-te-node-segment {
           description "Configure BGP-Peer-Node segment";
           uses apply-advanced;
           container label {
             description "BGP-Peer-Node SID label from static label pool";
             uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
               }
             }
           }
         }
         list egress-te-adj-segment {
           key name;
           description "Configure BGP-Peer-Adj segment";
           leaf name {
             description "The BGP-Adj-Set segment name";
             type string {
             }
           }
           uses apply-advanced;
           container label {
             description "BGP-Peer-Adj SID label from static label pool";
             uses apply-advanced;
             leaf label-value {
               description "BGP-Peer-Adj SID label value from static label pool";
               type union {
                 type string {
                   pattern "<.*>|$.*";
                 }
                 type uint32 {
                   range "16 .. 1048575";
                 }
               }
             }
           }
           container next-hop {
             description "Address of directly connected next-hop to use";
             uses apply-advanced;
             leaf next-hop-addr {
               description "Address of directly connected next-hop";
               type jt:ipaddr;
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
               }
             }
           }
           container te-link-attribute {
             presence "enable te-link-attribute";
             description "Link attribute";
             uses apply-advanced;
             leaf te-metric {
               description "TE Metric value";
               default "1";
               type union {
                 type string {
                   pattern "<.*>|$.*";
                 }
                 type uint32 {
                   range "1 .. 4294967295";
                 }
               }
             }
             leaf igp-metric {
               description "IGP Metric value";
               default "1";
               type union {
                 type string {
                   pattern "<.*>|$.*";
                 }
                 type uint32 {
                   range "1 .. 16777215";
                 }
               }
             }
             leaf delay-metric {
               description "Delay Metric";
               units "microseconds";
               type union {
                 type string {
                   pattern "<.*>|$.*";
                 }
                 type uint32 {
                   range "1 .. 16777215";
                 }
               }
             }
             leaf-list admin-group {
               ordered-by user;
               description "Administrative groups";
               type string;
               max-elements 16;
             }
           }
         }
         leaf vpn-apply-export {
           description "Apply BGP export policy when exporting VPN routes";
           type empty;
         }
         container egress-te {
           presence "enable egress-te";
           description "Use Egress Peering traffic engineering";
           uses apply-advanced;
           leaf install-address {
             description "Address to use in egress-te created inet route";
             type jt:ipaddr;
           }
           container rib {
             description "Select primary table for Egress-TE routes";
             uses apply-advanced;
             leaf inet.0 {
               description "Install Egress-TE routes in inet.0";
               type empty;
             }
             leaf inet6.0 {
               description "Install Egress-TE routes in inet6.0";
               type empty;
             }
           }
           leaf no-install {
             description "Avoid installation to FIB or resolving over";
             type empty;
           }
           leaf-list import {
             ordered-by user;
             description "Import policy to set attributes";
             type jt:policy-algebra;
           }
           leaf backup-path {
             description "The 'egress-te-backup-paths template' to use for this peer";
             type string {
             }
           }
         }
         leaf advertise-prefix-sid {
           description "Advertise prefix sid to E-BGP peers";
           type empty;
         }
         leaf accept-prefix-sid {
           description "Accept prefix sid from E-BGP peers";
           type empty;
         }
         leaf advertise-srgb {
           description "Advertise SRGB TLV";
           type empty;
         }
         leaf tcp-connect-port {
           description "TCP port number to connect with peer on";
           type union {
             type string {
               pattern "<.*>|$.*";
             }
             type uint16 {
               range "1 .. 65535";
             }
           }
         }
       }
       leaf vpn-apply-export {
         description "Apply BGP export policy when exporting VPN routes";
         type empty;
       }
       container egress-te {
         presence "enable egress-te";
         description "Use Egress Peering traffic engineering";
         uses apply-advanced;
         leaf install-address {
           description "Address to use in egress-te created inet route";
           type jt:ipaddr;
         }
         container rib {
           description "Select primary table for Egress-TE routes";
           uses apply-advanced;
           leaf inet.0 {
             description "Install Egress-TE routes in inet.0";
             type empty;
           }
           leaf inet6.0 {
             description "Install Egress-TE routes in inet6.0";
             type empty;
           }
         }
         leaf no-install {
           description "Avoid installation to FIB or resolving over";
           type empty;
         }
         leaf-list import {
           ordered-by user;
           description "Import policy to set attributes";
           type jt:policy-algebra;
         }
         leaf backup-path {
           description "The 'egress-te-backup-paths template' to use for this peer";
           type string {
           }
         }
       }
       leaf advertise-prefix-sid {
         description "Advertise prefix sid to E-BGP peers";
         type empty;
       }
       leaf accept-prefix-sid {
         description "Accept prefix sid from E-BGP peers";
         type empty;
       }
       leaf advertise-srgb {
         description "Advertise SRGB TLV";
         type empty;
       }
       leaf tcp-connect-port {
         description "TCP port number to connect with peer on";
         type union {
           type string {
             pattern "<.*>|$.*";
           }
           type uint16 {
             range "1 .. 65535";
           }
         }
       }
       leaf no-global-load-balancing {
         description "Disable glabl load balancing";
         type empty;
       }
     }
     container traffic-statistics-labeled-path {
       presence "enable traffic-statistics-labeled-path";
       description "Collect periodic ingress labeled statistics for BGP label-switched paths ";
       uses apply-advanced;
       container file {
         description "Statistics file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
     container source-packet-routing {
       description "Enable Source Packet Routing (SPRING)";
       uses apply-advanced;
       container srgb {
         description "Set the SRGB global block in SPRING";
         leaf start-label {
           description "Start range for SRGB label block";
           type union {
             type string {
               pattern "<.*>|$.*";
             }
             type uint32 {
               range "16 .. 1048575";
             }
           }
           //mandatory true;
         }
         leaf index-range {
           description "Index to the SRGB start label block";
           type union {
             type string {
               pattern "<.*>|$.*";
             }
             type uint32 {
               range "16 .. 1048575";
             }
           }
           //mandatory true;
         }
       }
       container srv6 {
         description "Enable IPv6 Segment Routing (SRv6)";
         uses apply-advanced;
         list locator {
           key name;
           ordered-by user;
           description "SRv6 Locator";
           leaf name {
             description "Locator name";
             type string;
           }
           uses apply-advanced;
           container end-dt4-sid {
             presence "enable end-dt4-sid";
             description "End dt4 sid with 128 bit address";
             uses apply-advanced;
             leaf sid {
               description "Sid value";
               type jt:ipv6addr;
             }
             leaf non-default {
               description "Non default sid for policy usage";
               type empty;
             }
           }
           container end-dt6-sid {
             presence "enable end-dt6-sid";
             description "End dt6 sid with 128 bit address";
             uses apply-advanced;
             leaf sid {
               description "Sid value";
               type jt:ipv6addr;
             }
             leaf non-default {
               description "Non default sid for policy usage";
               type empty;
             }
           }
           container end-dt46-sid {
             presence "enable end-dt46-sid";
             description "End dt46 sid with 128 bit address";
             uses apply-advanced;
             leaf sid {
               description "Sid value";
               type jt:ipv6addr;
             }
             leaf non-default {
               description "Non default sid for policy usage";
               type empty;
             }
           }
           container micro-dt4-sid {
             presence "enable micro-dt4-sid";
             description "Micro dt4 sid";
             uses apply-advanced;
             leaf micro-sid-value {
               description "Static micro sid value 16-bit or 32-bit";
               type union {
                 type uint32;
                 type string {
                   pattern "<.*>|$.*";
                 }
               }
             }
             leaf non-default {
               description "Non default micro dt4 sid for policy usage";
               type empty;
             }
           }
           container micro-dt6-sid {
             presence "enable micro-dt6-sid";
             description "Micro dt6 sid";
             uses apply-advanced;
             leaf micro-sid-value {
               description "Static micro sid value 16-bit or 32-bit";
               type union {
                 type uint32;
                 type string {
                   pattern "<.*>|$.*";
                 }
               }
             }
             leaf non-default {
               description "Non default micro dt6 sid for policy usage";
               type empty;
             }
           }
           container micro-dt46-sid {
             presence "enable micro-dt46-sid";
             description "Micro dt46 sid";
             uses apply-advanced;
             leaf micro-sid-value {
               description "Static micro sid value 16-bit or 32-bit";
               type union {
                 type uint32;
                 type string {
                   pattern "<.*>|$.*";
                 }
               }
             }
             leaf non-default {
               description "Non default micro dt46 sid for policy usage";
               type empty;
             }
           }
         }
       }
     }
     choice enable-disable {
       case case_1 {
         leaf disable {
           description "Disable BGP";
           type empty;
         }
       }
     }
     leaf protocol-instance-name {
       description "Name of protocol instance under routing instance";
       type string;
     }
     choice precision-timers-choice {
       leaf precision-timers {
         description "Use precision timers for scheduling keepalives";
         type empty;
       }
       leaf no-precision-timers {
         description "Don't use precision timers for scheduling keepalives";
         type empty;
       }
     }
     container snmp-options {
       description "Customize SNMP behaviors specifically for BGP MIBs";
       uses apply-advanced;
       leaf backward-traps-only-from-established {
         description "Limit traps for backward transitions to only those moving from Established state.";
         type empty;
       }
       leaf emit-inet-address-length-in-oid {
         description "Emit Length in OID for InetAddress MIB type.";
         type empty;
       }
     }
     leaf route-age-bgp-view {
       description "Maintain BGP route's age based on Update messages only";
       type empty;
     }
     leaf prioritize-route-queueing {
       description "Let route-queue building happen without getting throttled";
       type empty;
     }
     container traceoptions {
       description "Trace options for BGP";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "sharding" {
               description "Trace BGP rib sharding";
             }
             enum "glb" {
               description "Trace BGP global-load-balancing";
             }
             enum "thread-update-io" {
               description "Trace threaded update I/O processing";
             }
             enum "route-validation" {
               description "Trace route validation";
             }
             enum "ipsec" {
               description "Trace ipsec";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
         case case_4 {
           container effective-aigp {
             presence "enable effective-aigp";
             description "Track the effective AIGP metric";
             leaf metric-offset {
               description "Metric offset for MED";
               type union {
                 type int32;
                 type string {
                   pattern "<.*>|$.*";
                 }
               }
             }
           }
         }
         case case_5 {
           container minimum-effective-aigp {
             presence "enable minimum-effective-aigp";
             description "Track the minimum effective AIGP metric";
             leaf metric-offset {
               description "Metric offset for MED";
               type union {
                 type int32;
                 type string {
                   pattern "<.*>|$.*";
                 }
               }
             }
           }
         }
       }
     }
     container multihop {
       presence "enable multihop";
       description "Configure an EBGP multihop session";
       uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     container ebgp-community-cleanup {
       presence "enable ebgp-community-cleanup";
       description "Community specific cleanup for eBGP peers";
       uses apply-advanced;
       leaf origin-validation {
         description "Origin Validation State receive behavior";
         type enumeration {
           enum "accept" {
             description "Accept Origin Validation State Community";
           }
           enum "reject" {
             description "Reject Origin Validation State Community";
           }
         }
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
       }
     }
     leaf hold-time {
       description "Hold time used when negotiating with a peer";
       type union {
         type string {
           pattern "<.*>|$.*";
         }
         type uint32 {
           range "0 .. 65535";
         }
       }
     }
     leaf minimum-hold-time {
       description "Minimum hold time accepted from the peer";
       type union {
         type string {
           pattern "<.*>|$.*";
         }
         type uint32 {
           range "3 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly, enabled by default. Configure logging parameters";
       uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     leaf authentication-key {
       description "MD5 authentication key";
       type string {
         length "1 .. 126";
       }
     }
     leaf authentication-algorithm {
       description "Authentication algorithm name";
       default "hmac-sha-1-96";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
         enum "ao" {
           description "TCP Authentication Option";
         }
       }
     }
     leaf tcpao-auth-mismatch {
       description "Continue without TCP-AO if any one TCP endpoint does not have TCP-AO configured";
       type enumeration {
         enum "allow-without-tcpao" {
           description "Allow the connection establishment without TCP-AO";
         }
       }
     }
     leaf authentication-key-chain {
       description "Key chain name";
       type string {
         length "1 .. 128";
       }
     }
     leaf-list export {
       ordered-by user;
       description "Export policy";
       type jt:policy-algebra;
     }
     container remove-private {
       presence "enable remove-private";
       description "Remove well-known private AS numbers";
       uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
       }
     }
     container local-as {
       description "Local autonomous system number";
       leaf as-number {
         description " Autonomous system number in plain number or 'higher 16bits'.'Lower 16 bits' (asdot notation) format";
         type string {
         }
         //mandatory true;
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       type string {
         length "1 .. 32";
       }
     }
     container graceful-shutdown {
       description "BGP peer graceful shutdown option";
       uses apply-advanced;
       container receiver {
         presence "enable receiver";
         description "BGP peer graceful-shutdown receiver";
         uses apply-advanced;
         leaf disable {
           description "Disable graceful-shutdown receiver";
           type empty;
         }
         leaf local-preference {
           description "Value of receiver LOCAL_PREF path attribute";
           type union {
             type uint32;
             type string {
               pattern "<.*>|$.*";
             }
           }
         }
       }
       container sender {
         presence "enable sender";
         description "BGP peer graceful-shutdown sender";
         uses apply-advanced;
         leaf local-preference {
           description "Value of sender LOCAL_PREF path attribute";
           type union {
             type uint32;
             type string {
               pattern "<.*>|$.*";
             }
           }
         }
       }
     }
     container shutdown {
       presence "enable shutdown";
       description "Shutdown";
       uses apply-advanced;
       leaf notify-message {
         description "Notification message";
         type string;
       }
     }
     leaf unconfigured-peer-graceful-restart {
       description "BGP unconfigured peer graceful restart options";
       type empty;
     }
     container graceful-restart {
       presence "enable graceful-restart";
       description "BGP graceful restart options";
       uses apply-advanced;
       choice enable-disable {
         case case_1 {
           leaf disable {
             description "Disable graceful restart";
             type empty;
           }
         }
       }
       leaf restart-time {
         description "Restart time used when negotiating with a peer";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         uses apply-advanced;
         container receiver {
           description "Long-lived graceful restart receiver (helper) options";
           uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           uses apply-advanced;
           leaf omit-no-export {
             description "Do not attach no-export community to stale routes";
             type empty;
           }
         }
       }
       leaf disable-notification-extensions {
         description "Disable notification extensions";
         type empty;
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     leaf disable-4byte-as {
       description "Disable 4 byte AS capability advertisement";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       description "Dynamically negotiated cooperative route filtering";
       uses apply-advanced;
       leaf bgp-orf-cisco-mode {
         description "Using BGP ORF capability code 130 and Prefix ORF type 128";
         type empty;
       }
       container extended-community {
         description "Extended community filtering";
         status deprecated;
         uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         uses apply-advanced;
         container accept {
           presence "enable accept";
           description "Honor Prefix-based ORFs from remote peers";
           uses apply-advanced;
           leaf inet {
             description "Honor IPv4 prefix filters";
             type empty;
           }
           leaf inet6 {
             description "Honor IPv6 prefix filters";
             type empty;
           }
         }
       }
     }
     container message-batching {
       description "DEPRECATED - Batching of outgoing messages";
       status deprecated;
       uses apply-advanced;
       choice enable-disable {
         case case_1 {
           leaf enable {
             description "Enable parameter";
             type empty;
           }
         }
         case case_2 {
           leaf disable {
             description "Disable parameter";
             type empty;
           }
         }
       }
       leaf interval {
         description "DEPRECATED - Interval over which to batch messages";
         default "250";
         units "milliseconds";
         type union {
           type string {
             pattern "<.*>|$.*";
           }
           type uint32 {
             range "100 .. 1000";
           }
         }
       }
     }
     container multipath {
       presence "enable multipath";
       description "Allow load sharing among multiple BGP paths";
       uses apply-advanced;
       leaf disable {
         description "Disable Multipath";
         type empty;
       }
       leaf multiple-as {
         description "Use paths received from different ASs";
         type empty;
       }
       leaf allow-protection {
         description "Allow protection for multipath legs";
         type empty;
       }
       leaf pause-computation-during-churn {
         description "Pause multipath job to absorb churn";
         type empty;
       }
       leaf list-nexthop {
         description "Use List-NH for homogenous nexthop-set also";
         type empty;
       }
       container allow-external-internal {
         presence "enable allow-external-internal";
         description "Allow multipath to mix EBGP and IBGP routes";
         uses apply-advanced;
         leaf-list prefix-policy {
           ordered-by user;
           description "Policy to constrain prefixes that apply";
           type jt:policy-algebra;
         }
       }
     }
     leaf tcp-mss {
       description "Maximum TCP segment size";
       type union {
         type string {
           pattern "<.*>|$.*";
         }
         type uint32 {
           range "1 .. 4096";
         }
       }
     }
     leaf bgp-identifier {
       description "BGP Identifier";
       type jt:ipv4addr;
     }
     leaf tcp-aggressive-transmission {
       description "Enable aggressive transmission of pure TCP ACKs and retransmissions";
       type empty;
     }
     container bmp {
       description "Specific settings to override the routing-options settings";
       uses apply-advanced;
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           type empty;
         }
         container pre-policy {
           presence "enable pre-policy";
           description "Send pre-policy route monitoring messages";
           leaf exclude-non-feasible {
             description "Exclude looped routes, etc";
             type empty;
           }
         }
         container post-policy {
           presence "enable post-policy";
           description "Send post-policy route monitoring messages";
           leaf exclude-non-eligible {
             description "Exclude unresolved routes, etc.";
             type empty;
           }
         }
         container rib-out {
           presence "enable rib-out";
           description "Send adj-ribs-out route monitoring messages";
           leaf pre-policy {
             description "Send pre-policy adj-ribs-out route monitoring messages";
             type empty;
           }
           leaf post-policy {
             description "Send post-policy adj-ribs-out route monitoring messages";
             type empty;
           }
         }
       }
     }
     container advertise-bgp-static {
       presence "enable advertise-bgp-static";
       description "Advertise bgp-static routes";
       uses apply-advanced;
       leaf-list policy {
         ordered-by user;
         description "Static route advertisement policy";
         type jt:policy-algebra;
       }
     }
     leaf add-path-display-ipv4-address {
       description "Display add-path path-id in IPv4 address format";
       type empty;
     }
     container domain-path-id {
       description "Domain path id attribute";
       uses apply-advanced;
       leaf send {
         description "Allow sending domain path id attribute";
         type empty;
       }
       leaf receive {
         description "Allow receiving domain path id attribute";
         type empty;
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       container echo {
         description "Echo mode parameters";
         uses apply-advanced;
         leaf minimum-interval {
           description "Minimum transmit and receive interval";
           units "milliseconds";
           type union {
             type string {
               pattern "<.*>|$.*";
             }
             type uint32 {
               range "100 .. 255000";
             }
           }
           //mandatory true;
         }
       }
       container echo-lite {
         description "Echo-lite more parameters";
         uses apply-advanced;
         leaf minimum-interval {
           description "Minimum transmit and receive interval";
           units "milliseconds";
           type union {
             type string {
               pattern "<.*>|$.*";
             }
             type uint32 {
               range "100 .. 255000";
             }
           }
           //mandatory true;
         }
       }
       container strict-bfd {
         presence "enable strict-bfd";
         description "Bgp session waits for bfd";
         uses apply-advanced;
         leaf bfd-up-wait-interval {
           description "Time to wait for bfd to come up";
           units "seconds";
           type union {
             type string {
               pattern "<.*>|$.*";
             }
             type uint32 {
               range "10 .. 255";
             }
           }
         }
       }
       leaf holddown-interval {
         description "Time to hold the session-UP notification to the client";
         units "milliseconds";
         type union {
           type string {
             pattern "<.*>|$.*";
           }
           type uint32 {
             range "0 .. 255000";
           }
         }
       }
     }
     container output-queue-priority {
       description "BGP output queue priority scheduler for updates";
       uses apply-advanced;
       container expedited {
         presence "enable expedited";
         description "Expedited queue; highest priority";
         leaf update-tokens {
           description "Number of tokens";
           type union {
             type string {
               pattern "<.*>|$.*";
             }
             type uint32 {
               range "1 .. 100";
             }
           }
           mandatory true;
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
           mandatory true;
         }
       }
       container defaults {
         description "Map policy's priority class and BGP output-queue";
         uses apply-advanced;
         container low {
           description "Assign the 'low' priority class to this output-queue";
           uses bgp-output-queue-priority-class;
         }
         container medium {
           description "Assign the 'medium' priority class to this output-queue";
           uses bgp-output-queue-priority-class;
         }
         container high {
           description "Assign the 'high' priority class to this output-queue";
           uses bgp-output-queue-priority-class;
         }
       }
     }
     container multipath-build-priority {
       description "Configure the multipath build priority";
       uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     leaf rfc8950-compliant {
       description "Enable RFC8950 compliant";
       type empty;
     }
     container defaults {
       uses apply-advanced;
       container ebgp {
         description "Options impacting external BGP default behaviors";
         uses apply-advanced;
         container no-policy {
           description "Default ebgp behaviors in the absence of configured policy";
           uses apply-advanced;
           leaf receive {
             description "Default ebgp receive behavior";
             type enumeration {
               enum "accept" {
                 description "By default, accept routes from all address families";
               }
               enum "reject" {
                 description "By default, reject routes from IPv4/IPv6 unicast address families";
               }
               enum "reject-always" {
                 description "By default, reject routes from all address families";
               }
             }
           }
           leaf advertise {
             description "Default ebgp advertise behavior";
             type enumeration {
               enum "accept" {
                 description "By default, advertise routes for all address families";
               }
               enum "reject" {
                 description "By default, do not advertise routes from IPv4/IPv6 unicast address families";
               }
               enum "reject-always" {
                 description "By default, do not advertise routes from any address families";
               }
             }
           }
         }
       }
     }
   }
   grouping bgp-af-gr {
     uses apply-advanced;
     container long-lived {
       description "Long-lived graceful restart options";
       uses apply-advanced;
       container restarter {
         description "Long-lived graceful restart restarter options";
         uses apply-advanced;
         choice enable-disable {
           case case_1 {
             leaf disable {
               description "Disable restarter functionality";
               type empty;
             }
           }
         }
         leaf stale-time {
           description "Stale time in seconds or dhms notation (1..16777215)";
           type string;
         }
       }
       container extended-route-retention {
         description "Extended route retention (LLGR-helper extended) options";
         uses apply-advanced;
         choice enable-disable {
           case case_1 {
             leaf disable {
               description "Disable extended-route-retention (LLGR-helper) functionality";
               type empty;
             }
           }
         }
         leaf retention-time {
           description "Retention time in seconds or dhms notation (1..16777215)";
           type string;
         }
         leaf-list retention-policy {
           ordered-by user;
           description "Retention policy for Extended Route Retention";
           type jt:policy-algebra;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
   }
   grouping apath-options {
     description "Number of paths to advertise";
     uses apply-advanced;
     leaf receive {
       description "Receive multiple paths from peer";
       type empty;
     }
     container send {
       presence "enable send";
       description "Send multiple paths to peer";
       uses apply-advanced;
       container path-selection-mode {
         description "Configure how to select add-path routes";
         uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
         mandatory true;
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
   grouping bgp-afi-flow {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     leaf-list no-validate {
       ordered-by user;
       description "Bypass validation procedure for routes that match policy";
       type jt:policy-algebra;
     }
     leaf strip-nexthop {
       description "Strip the next-hop from the outgoing flow update";
       type empty;
     }
     leaf allow-policy-add-nexthop {
       description "Allow policy to add nexthop to a route without nexthop";
       status deprecated;
       type empty;
     }
   }
   grouping bgp-afi-flow-with-redirect-ip-action {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     leaf-list no-validate {
       ordered-by user;
       description "Bypass validation procedure for routes that match policy";
       type jt:policy-algebra;
     }
     leaf strip-nexthop {
       description "Strip the next-hop from the outgoing flow update";
       type empty;
     }
     container legacy-redirect-ip-action {
       presence "enable legacy-redirect-ip-action";
       description "Configure legacy redirect to IP support";
       uses apply-advanced;
       leaf receive {
         description "Accept legacy encoded redirect-to-ip action attribute";
         type empty;
       }
       leaf send {
         description "Advertise Redirect action as legacy redirect attribute";
         type empty;
       }
     }
     leaf secondary-independent-resolution {
       description "Resolve FLOW routes in VRF table independent of VPN FLOW route";
       type empty;
     }
   }
   grouping bgp-afi-inet-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container protection {
       presence "enable protection";
       description "Compute backup path for active nexthop failure";
     }
   }
   grouping bgp-afi-inet6-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet6.3 {
         description "Use inet6.3 to exchange labeled unicast routes";
         type empty;
       }
     }
     container explicit-null {
       presence "enable explicit-null";
       description "Advertise explicit null";
       leaf connected-only {
         description "Advertise explicit null only for connected routes";
         type empty;
       }
     }
     container protection {
       presence "enable protection";
       description "Compute backup path for active nexthop failure";
     }
     list topology {
       key name;
       ordered-by user;
       description "Multi topology routing tables";
       leaf name {
         description "Topology name";
         type string {
         }
       }
       uses apply-advanced;
       leaf community {
         description "Community to identify multi topology routes";
         type string;
         mandatory true;
       }
     }
   }
   grouping bgp-afi-inet6-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container lu-export {
       presence "enable lu-export";
       description "Install Classful Transport routes in inet6.3";
       uses apply-advanced;
     }
     container protection {
       presence "enable protection";
       description "Compute backup path for active nexthop failure";
     }
   }
   grouping bgp-afi-l2vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-afi-l3vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
     leaf accept-local-nexthop {
       description "Enable processing of routes with own nexthop";
       type empty;
     }
     leaf accept-own {
       description "Enable processing of routes with own originator-id or nexthop";
       type empty;
     }
   }
   grouping bgp-afi-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     list topology {
       key name;
       ordered-by user;
       description "Multi topology routing tables";
       leaf name {
         description "Topology name";
         type string {
         }
       }
       uses apply-advanced;
       leaf community {
         description "Community to identify multi topology routes";
         type string;
         mandatory true;
       }
     }
     container rib {
       description "Select table used by labeled unicast routes";
       uses rib-inet3;
     }
     container explicit-null {
       presence "enable explicit-null";
       description "Advertise explicit null";
       leaf connected-only {
         description "Advertise explicit null only for connected routes";
         type empty;
         mandatory true;
       }
     }
     container protection {
       presence "enable protection";
       description "Compute backup path for active nexthop failure";
       uses apply-advanced;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
     leaf resolve-vpn {
       description "Install received NLRI in inet.3 also";
       type empty;
     }
     container entropy-label {
       presence "enable entropy-label";
       description "Use entropy label for entropy label capable BGP LSPs";
       uses apply-advanced;
       leaf-list import {
         ordered-by user;
         description "Policy to select BGP LSPs to use entropy label";
         type jt:policy-algebra;
       }
       leaf no-next-hop-validation {
         description "Don't validate next hop field against route next hop";
         type empty;
       }
       leaf elc-v2-compatible {
         description "Send and accept ELCv2 in addition to ELCv3";
         type empty;
       }
     }
   }
   grouping bgp-afi-srte {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     leaf damping {
       description "Enable route flap damping";
       type empty;
     }
     container loops {
       description "Allow local AS in received AS paths";
       uses bgpaf-loops;
     }
     container graceful-restart {
       description "BGP graceful restart options";
       uses bgp-af-gr;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf-list export {
       ordered-by user;
       description "Export policy";
       type jt:policy-algebra;
     }
     leaf-list import {
       ordered-by user;
       description "Import policy";
       type jt:policy-algebra;
     }
   }
   grouping bgp-afi-topo {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container protection {
       presence "enable protection";
       description "Compute backup path for active nexthop failure";
     }
     list topology {
       key name;
       ordered-by user;
       description "Multi topology routing tables";
       leaf name {
         description "Topology name";
         type string {
         }
       }
       uses apply-advanced;
       leaf community {
         description "Community to identify multi topology routes";
         type string;
         mandatory true;
       }
     }
   }
   grouping bgp-afi-vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
   }
   grouping bgp-afi-vpn-protection {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minimum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list import {
       ordered-by user;
       description "Import policy";
       type jt:policy-algebra;
     }
     leaf-list export {
       ordered-by user;
       description "Export policy";
       type jt:policy-algebra;
     }
     container aggregate-label {
       presence "enable aggregate-label";
       description "Aggregate labels of incoming routes with the same FEC";
       uses apply-advanced;
       leaf community {
         description "Community to identify the FEC of incoming routes";
         type string;
         mandatory true;
       }
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-output-queue-priority-class {
     choice class {
       case case_1 {
         leaf priority {
           description "Output queue priority; higher is better";
           type union {
             type string {
               pattern "<.*>|$.*";
             }
             type uint32 {
               range "1 .. 16";
             }
           }
         }
       }
       case case_2 {
         leaf expedited {
           description "Expedited queue; highest priority";
           type empty;
         }
       }
     }
   }
   grouping bgp_filter_obj {
     description "Filter to apply to tracing";
     leaf match-on {
       description "Argument on which to match";
       type enumeration {
         enum "prefix" {
           description "Filter based on prefix";
         }
       }
       mandatory true;
     }
     leaf-list policy {
       ordered-by user;
       description "Filter policy";
       type jt:policy-algebra;
     }
   }
   grouping bgpaf-accepted-prefix-limit {
     uses apply-advanced;
     leaf maximum {
       description "Maximum number of prefixes accepted from a peer";
       type union {
         type string {
           pattern "<.*>|$.*";
         }
         type uint32 {
           range "1 .. 4294967295";
         }
       }
       //mandatory true;
     }
     container teardown {
       presence "enable teardown";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-aigp-options {
     uses apply-advanced;
     leaf disable {
       description "Disable sending and receiving of AIGP attribute";
       type empty;
     }
   }
   grouping bgpaf-loops {
     uses apply-advanced;
     leaf loops {
       description "AS-Path loop count";
       type union {
         type string {
           pattern "<.*>|$.*";
         }
         type int32 {
           range "1 .. 10";
         }
       }
       //mandatory true;
     }
   }
   grouping bgpaf-prefix-limit {
     uses apply-advanced;
     leaf maximum {
       description "Maximum number of prefixes from a peer";
       type union {
         type string {
           pattern "<.*>|$.*";
         }
         type uint32 {
           range "1 .. 4294967295";
         }
       }
       //mandatory true;
     }
     container teardown {
       presence "enable teardown";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-traffic-statistics {
     uses apply-advanced;
     leaf labeled-path {
       description "Ingress labeled path statistics";
       type empty;
     }
     container file {
       description "Statistics file options";
       leaf filename {
         description "Name of file in which to write trace information";
         type string {
           length "1 .. 1024";
         }
         //mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     leaf interval {
       description "Time to collect statistics (seconds)";
       type union {
         type string {
           pattern "<.*>|$.*";
         }
         type int32 {
           range "60 .. 65535";
         }
       }
     }
   }
   grouping juniper-protocols-isis {
     uses apply-advanced;
     list interface {
       key name;
       description "Interface configuration";
       leaf name {
         description "Interface name";
         type union {
           type jt:interface-name;
           type string {
             pattern "<.*>|$.*";
           }
         }
       }
       uses apply-advanced;
       container ldp-synchronization {
         description "Advertise maximum metric until LDP is operational";
         presence "enable ldp-synchronization";
         uses ldp-sync-obj;
       }
       list level {
         key name;
         ordered-by user;
         description "Configure levels on this interface";
         leaf name {
           description "IS-IS level number";
           type union {
             type string {
               pattern "<.*>|$.*";
             }
             type uint32 {
               range "1 .. 2";
             }
           }
         }
         uses apply-advanced;
         leaf te-metric {
           description "Traffic engineering metric";
           type union {
             type string {
               pattern "<.*>|$.*";
             }
             type uint32 {
               range "0 .. 16777215";
             }
           }
         }
         leaf no-advertise-adjacency-segment {
           description "Do not advertise an adjacency segment for this level";
           type empty;
         }
         container ipv4-adjacency-segment {
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srv6-adjacency-segment {
           description "Configure srv6 adjacency segment";
           uses apply-advanced;
           container unprotected {
             presence "enable unprotected";
             description "SRv6 Adjacency segment is uneligible for protection";
             uses apply-advanced;
             list locator {
               key name;
               ordered-by user;
               description "Locator to bind SRv6 adjacency segment";
               leaf name {
                 description "Locator name";
                 type string;
                 mandatory true;
               }
               uses apply-advanced;
               list end-x-sid {
                 key name;
                 ordered-by user;
                 description "Endpoint 128 bit address";
                 leaf name {
                   type jt:ipv6addr;
                 }
                 uses apply-advanced;
               }
               container micro-adjacency-sid {
                 presence "enable micro-adjacency-sid";
                 description "Micro-adjacency-SID";
                 uses apply-advanced;
                 leaf static-sid {
                   description "Static micro-adjacency-SID";
                   type union {
                     type uint32;
                     type string {
                       pattern "<.*>|$.*";
                     }
                   }
                 }
               }
               container dynamic-end-x-sid {
                 presence "enable dynamic-end-x-sid";
                 description "Allocate end-x-SID dynamically";
                 uses apply-advanced;
                 container flavor {
                   presence "enable flavor";
                   description "Configure end-x-SID flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
         }
         list lan-neighbor {
           key name;
           ordered-by user;
           description "Configuration specific to a LAN neighbor";
           leaf name {
             description "Neighbor's sysid";
             type jt:sysid;
           }
           uses apply-advanced;
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srv6-adjacency-segment {
             description "Configure srv6 adjacency segment";
             uses apply-advanced;
             container unprotected {
               presence "enable unprotected";
               description "SRv6 Adjacency segment is uneligible for protection";
               uses apply-advanced;
               list locator {
                 key name;
                 ordered-by user;
                 description "Locator to bind SRv6 adjacency segment";
                 leaf name {
                   description "Locator name";
                   type string;
                   mandatory true;
                 }
                 uses apply-advanced;
                 list end-x-sid {
                   key name;
                   ordered-by user;
                   description "Endpoint 128 bit address";
                   leaf name {
                     type jt:ipv6addr;
                   }
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
                 container micro-adjacency-sid {
                   presence "enable micro-adjacency-sid";
                   description "Micro-adjacency-SID";
                   uses apply-advanced;
                   leaf static-sid {
                     description "Static micro-adjacency-SID";
                     type union {
                       type uint32;
                       type string {
                         pattern "<.*>|$.*";
                       }
                     }
                   }
                 }
                 container dynamic-end-x-sid {
                   presence "enable dynamic-end-x-sid";
                   description "Allocate end-x-SID dynamically";
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
         }
         container post-convergence-lfa {
           presence "enable post-convergence-lfa";
           description "Configure backup along post convergence on this interface";
           uses apply-advanced;
         }
         choice enable-disable {
           case case_1 {
             leaf disable {
               description "Disable IS-IS for this level";
               type empty;
             }
           }
         }
         leaf metric {
           description "Metric for this level";
           type union {
             type string {
               pattern "<.*>|$.*";
             }
             type uint32 {
               range "0 .. 16777215";
             }
           }
         }
         leaf ipv4-multicast-metric {
           description "IPv4 multicast metric for this level";
           type union {
             type string {
               pattern "<.*>|$.*";
             }
             type uint32 {
               range "0 .. 16777215";
             }
           }
         }
         leaf ipv6-unicast-metric {
           description "IPv6 unicast metric for this level";
           type union {
             type string {
               pattern "<.*>|$.*";
             }
             type uint32 {
               range "0 .. 16777215";
             }
           }
         }
         leaf ipv6-multicast-metric {
           description "IPv6 multicast metric for this level";
           type union {
             type string {
               pattern "<.*>|$.*";
             }
             type uint32 {
               range "0 .. 16777215";
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
                 mandatory true;
               }
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf hello-authentication-key {
           description "Authentication key (password) for hello packets";
           type jt:unreadable;
         }
         leaf hello-authentication-type {
           description "Authentication type for hello packets";
           type enumeration {
             enum "md5" {
               description "MD5 authentication";
             }
             enum "simple" {
               description "Simple password authentication";
             }
           }
         }
         leaf hello-authentication-key-chain {
           description "Key chain name";
           type string {
             length "1 .. 128";
           }
         }
         leaf hello-interval {
           description "Interval between hello packet transmissions";
           units "seconds";
           type union {
             type string {
               pattern "<.*>|$.*";
             }
             type uint32 {
               range "1 .. 21845";
             }
           }
         }
         leaf hold-time {
           description "Time after which neighbors think the interface is down";
           units "seconds";
           type union {
             type string {
               pattern "<.*>|$.*";
             }
             type uint32 {
               range "1 .. 65535";
             }
           }
         }
         leaf priority {
           description "Designated router election priority";
           type union {
             type string {
               pattern "<.*>|$.*";
             }
             type uint32 {
               range "0 .. 127";
             }
           }
         }
         container flood-reflector {
           presence "enable flood-reflector";
           description "Configure interface as flood-reflector";
           uses apply-advanced;
           leaf cluster-id {
             description "Cluster-ID";
             type union {
               type string {
                 pattern "<.*>|$.*";
               }
               type uint32 {
                 range "1 .. 4294967295";
               }
             }
           }
         }
         container passive {
           presence "enable passive";
           description "Do not run IS-IS at this level, but advertise it";
           uses apply-advanced;
           leaf remote-node-iso {
             description "ISO System-ID of the remote node";
             type jt:sysid;
           }
           leaf remote-node-id {
             description "Remote address of the link";
             type jt:ipv4addr;
           }
         }
         leaf strict-bfd-old {
           description "Enable strict bfd over this interface";
           type empty;
         }
       }
       leaf delay-metric {
         description "Delay metric";
         units "microseconds";
         type union {
           type string {
             pattern "<.*>|$.*";
           }
           type uint32 {
             range "0 .. 16777215";
           }
         }
       }
       container delay-measurement {
         presence "enable delay-measurement";
         description "Enable delay measurement";
         uses apply-advanced;
         leaf probe-interval {
           description "Probe interval";
           units "seconds";
           type union {
             type string {
               pattern "<.*>|$.*";
             }
             type uint32 {
               range "1 .. 255";
             }
           }
         }
         leaf probe-count {
           description "Probe count";
           type union {
             type string {
               pattern "<.*>|$.*";
             }
             type uint32 {
               range "1 .. 15";
             }
           }
         }
         container normalize {
           description "Normalize Measured Link Delay";
           leaf interval {
             description "The value of the normalized interval in microseconds.";
             units "microseconds";
             type union {
               type string {
                 pattern "<.*>|$.*";
               }
               type uint32 {
                 range "1 .. 5000000";
               }
             }
             mandatory true;
           }
           leaf offset {
             description "The value of the normalized offset in microseconds (Must be < normalized interval).";
             units "microseconds";
             type union {
               type string {
                 pattern "<.*>|$.*";
               }
               type uint32 {
                 range "1 .. 5000000";
               }
             }
             mandatory true;
           }
         }
         container advertisement {
           description "Delay advertisement";
           uses apply-advanced;
           container periodic {
             description "Periodic advertisement parameters";
             uses apply-advanced;
             leaf threshold {
               description "Threshold";
               units "percentage";
               type union {
                 type string {
                   pattern "<.*>|$.*";
                 }
                 type uint32 {
                   range "0 .. 100";
                 }
               }
             }
             leaf interval {
               description "Interval";
               units "seconds";
               type union {
                 type string {
                   pattern "<.*>|$.*";
                 }
                 type uint32 {
                   range "30 .. 3600";
                 }
               }
             }
           }
           container accelerated {
             presence "enable accelerated";
             description "Accelerated advertisement parameters";
             uses apply-advanced;
             leaf threshold {
               description "Threshold";
               units "percentage";
               type union {
                 type string {
                   pattern "<.*>|$.*";
                 }
                 type uint32 {
                   range "0 .. 100";
                 }
               }
             }
           }
         }
       }
       leaf no-advertise-adjacency-segment {
         description "Do not advertise an adjacency segment for this interface";
         type empty;
       }
       choice protection-type {
         case case_1 {
           leaf link-protection {
             description "Protect interface from link faults only";
             type empty;
           }
         }
         case case_2 {
           leaf node-link-protection {
             description "Protect interface from both link and node faults";
             type empty;
           }
         }
       }
       leaf no-eligible-backup {
         description "Not eligible for backup traffic from protected interfaces";
         type empty;
       }
       leaf no-eligible-remote-backup {
         description "Not eligible for Remote-LFA backup traffic from protected interfaces";
         type empty;
       }
       container link-degradation-threshold {
         presence "enable link-degradation-threshold";
         description "Link up and down thresholds (in %) for proactive link protection";
         leaf link-down {
           description "Signal degradation threshold above which link marked down";
           type union {
             type string {
               pattern "<.*>|$.*";
             }
             type uint32 {
               range "0 .. 100";
             }
           }
           mandatory true;
         }
         leaf link-up {
           description "Signal degradation threshold below which link is marked up.";
           type union {
             type string {
               pattern "<.*>|$.*";
             }
             type uint32 {
               range "0 .. 100";
             }
           }
           mandatory true;
         }
       }
       choice enable-disable {
         case case_1 {
           leaf disable {
             description "Disable IS-IS on this interface";
             type empty;
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf flood-group {
         description "ISO Area that this interface should send LSPs to";
         type string {
         }
       }
       leaf hello-authentication-key {
         description "Authentication key (password) for hello packets";
         status deprecated;
         type jt:unreadable;
       }
       leaf hello-authentication-type {
         description "Authentication type for hello packets";
         status deprecated;
         type enumeration {
           enum "md5" {
             description "MD5 authentication";
             status deprecated;
           }
           enum "simple" {
             description "Simple password authentication";
             status deprecated;
           }
         }
       }
       leaf hello-padding-type {
         description "Type of padding for hello packets";
         default "loose";
         type enumeration {
           enum "strict" {
             description "Padding for all adjacency states";
           }
           enum "adaptive" {
             description "Padding until state of neighbor adjacency is 'up'";
           }
           enum "loose" {
             description "Padding until state of adjacency is 'initializing'";
           }
           enum "disable" {
             description "Do not add any padding for hello packets";
           }
         }
       }
       leaf interface-group-holddown-delay {
         description "Time to wait before including in BBM calculation";
         units "seconds";
         type union {
           type string {
             pattern "<.*>|$.*";
           }
           type uint32 {
             range "0 .. 60";
           }
         }
       }
       leaf max-hello-size {
         description "Maximum size allowed for ISIS Hello PDUs";
         type union {
           type string {
             pattern "<.*>|$.*";
           }
           type uint32 {
             range "512 .. 16000";
           }
         }
       }
       leaf lsp-interval {
         description "Interval between LSP transmissions";
         default "100";
         units "milliseconds";
         type union {
           type string {
             pattern "<.*>|$.*";
           }
           type uint32 {
             range "1 .. 1000";
           }
         }
       }
       container csnp-interval {
         description "Rate of CSN packets (for LAN interfaces only)";
         choice csnp_interval_option {
           case case_1 {
             leaf csnp-interval-number {
               description "Interval between CSN packets";
               units "seconds";
               type union {
                 type string {
                   pattern "<.*>|$.*";
                 }
                 type uint32 {
                   range "1 .. 65535";
                 }
               }
             }
           }
           case case_2 {
             leaf disable {
               description "Do not send CSN packets on this interface";
               type empty;
             }
           }
         }
       }
       container strict-dual-isis {
         presence "enable strict-dual-isis";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container mesh-group {
         description "Add the interface to a mesh group";
         choice mesh_group_option {
           case case_1 {
             leaf mesh-group-number {
               description "Mesh group number for this interface";
               type union {
                 type uint32;
                 type string {
                   pattern "<.*>|$.*";
                 }
               }
             }
           }
           case case_2 {
             leaf blocked {
               description "Do not flood new LSPs on this interface";
               type empty;
             }
           }
         }
       }
       leaf point-to-point {
         description "Treat interface as point to point";
         type empty;
       }
       container passive {
         presence "enable passive";
         description "Do not run IS-IS, but advertise it";
         uses apply-advanced;
         leaf remote-node-iso {
           description "ISO System-ID of the remote node";
           type jt:sysid;
         }
         leaf remote-node-id {
           description "Remote address of the link";
           type jt:ipv4addr;
         }
       }
       leaf checksum {
         description "Enable checksum for packets on this interface";
         type empty;
       }
       leaf no-unicast-topology {
         description "Do not include this interface in the unicast topology";
         type empty;
       }
       leaf no-ipv4-multicast {
         description "Do not include this interface in the IPv4 multicast topology";
         type empty;
       }
       leaf no-ipv6-unicast {
         description "Do not include this interface in the IPv6 unicast topology";
         type empty;
       }
       leaf no-ipv6-multicast {
         description "Do not include this interface in the IPv6 multicast topology";
         type empty;
       }
       leaf no-adjacency-down-notification {
         description "Do not inform other protocols about adjacency down events";
         type empty;
       }
       container bfd-liveness-detection {
         description "Bidirectional Forwarding Detection options";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list family {
         key name;
         ordered-by user;
         description "Address family specific interface attributes";
         leaf name {
           type enumeration {
             enum "inet" {
               description "IPv4 family";
             }
             enum "inet6" {
               description "IPv6 family";
             }
           }
         }
         uses apply-advanced;
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           leaf holddown-interval {
             description "Time to hold the session-UP notification to the client";
             units "milliseconds";
             type union {
               type string {
                 pattern "<.*>|$.*";
               }
               type uint32 {
                 range "0 .. 255000";
               }
             }
           }
         }
       }
       leaf strict-bfd {
         description "Enable strict bfd over this interface";
         type empty;
       }
     }
     list bier-sub-domain {
       key name;
       description "Configuration of bier subdomain";
       leaf name {
         description "Enable bier subdomain id";
         type union {
           type uint8;
           type string {
             pattern "<.*>|$.*";
           }
         }
       }
     }
     container prefix-unreachable {
       presence "enable prefix-unreachable";
       description "Configure unreachable prefix advertisement parameters";
       uses apply-advanced;
       container originator {
         description "Parameters for originating unreachable prefix advertisements";
         uses apply-advanced;
         leaf unplanned-lifetime {
           description "Lifetime of unplanned UPA";
           units "seconds";
           type union {
             type string {
               pattern "<.*>|$.*";
             }
             type uint32 {
               range "30 .. 65535";
             }
           }
         }
         leaf metric {
           description "Metric value of unplanned UPA";
           type union {
             type string {
               pattern "<.*>|$.*";
             }
             type uint32 {
               range "4261412865 .. 4294967295";
             }
           }
         }
         leaf max-advertisements {
           description "Maximum UPAs that can be originated at any point of time";
           type union {
             type string {
               pattern "<.*>|$.*";
             }
             type uint32 {
               range "1 .. 10000";
             }
           }
         }
       }
       leaf use-only-for-leaking {
         description "Do not use this UPA route for resolution";
         type empty;
       }
     }
     container source-packet-routing {
       presence "enable source-packet-routing";
       description "Enable Source Packet Routing (SPRING)";
       uses apply-advanced;
       container adjacency-segment {
         description "Configure attributes for Adjacency Segments in SPRING";
         uses apply-advanced;
         leaf hold-time {
           description "Duration(ms) for which adjacency segments will be retained after isolating from an interface";
           type union {
             type string {
               pattern "<.*>|$.*";
             }
             type uint32 {
               range "180000 .. 900000";
             }
           }
         }
       }
       container udp-tunneling {
         description "Enable SR over UDP feature";
         uses apply-advanced;
         leaf encapsulation {
           description "Enable UDP Tunnel Encapsulation";
           type empty;
         }
         leaf decapsulation {
           description "Enable UDP Tunnel decapsulation";
           type empty;
         }
       }
       container srgb {
         description "Set the SRGB global block in SPRING";
         leaf start-label {
           description "Start range for SRGB label block";
           type union {
             type string {
               pattern "<.*>|$.*";
             }
             type uint32 {
               range "16 .. 1048575";
             }
           }
           //mandatory true;
         }
         leaf index-range {
           description "Index to the SRGB start label block";
           type union {
             type string {
               pattern "<.*>|$.*";
             }
             type uint32 {
               range "32 .. 1048559";
             }
           }
           //mandatory true;
         }
       }
       container node-segment {
         description "Enable support for Node segments in SPRING";
         uses apply-advanced;
         leaf ipv4-index {
           description "Set IPv4 Node Segment index";
           type union {
             type string {
               pattern "<.*>|$.*";
             }
             type uint32 {
               range "0 .. 1048575";
             }
           }
         }
         leaf ipv6-index {
           description "Set IPv6 Node Segment index";
           type union {
             type string {
               pattern "<.*>|$.*";
             }
             type uint32 {
               range "0 .. 1048575";
             }
           }
         }
         leaf index-range {
           description "Set Range of Node Segment indices allowed";
           type union {
             type string {
               pattern "<.*>|$.*";
             }
             type uint32 {
               range "32 .. 16385";
             }
           }
         }
       }
       leaf-list flex-algorithm {
         description "Flex-algorithms we would like to participate in";
         type union {
           type string {
             pattern "<.*>|$.*";
           }
           type uint32 {
             range "128 .. 255";
           }
         }
         max-elements 16;
       }
       leaf use-flex-algorithm-metric-always {
         description "Use flex-algo prefix metric whenever available";
         type empty;
       }
       leaf strict-asla-based-flex-algorithm {
         description "Flex-Algorithm to ignore links not having ASLA sub-TLVs";
         type empty;
       }
       leaf new-capability-subtlv {
         description "Advertise all ranges in single spring capability subtlv";
         type empty;
       }
       leaf explicit-null {
         description "Set E and P bits in all Prefix SID advertisements";
         type empty;
       }
       leaf mapping-server {
         description "Mapping server name";
         type string;
       }
       leaf no-strict-spf {
         description " Disable strict spf algo 1 advertisement";
         type empty;
       }
       leaf no-binding-sid-leaking {
         description " Disable SRMS binding sid leaking";
         type empty;
       }
       leaf ldp-stitching {
         description "Enable SR to LDP stitching";
         type empty;
       }
       leaf entropy-label {
         description " Enable entropy label";
         type empty;
       }
       container srv6 {
         presence "enable srv6";
         description "Enable IPv6 Segment Routing (SRv6)";
         uses apply-advanced;
         list locator {
           key name;
           ordered-by user;
           description "SRv6 Locator";
           leaf name {
             description "Locator name";
             type string;
             mandatory true;
           }
           uses apply-advanced;
           leaf anycast {
             description "Set A flag in the Prefix-Attribute sub-TLV";
             type empty;
           }
           list end-sid {
             key name;
             ordered-by user;
             leaf name {
               type jt:ipv6addr;
             }
             uses apply-advanced;
           }
           container dynamic-end-sid {
             presence "enable dynamic-end-sid";
             description "Allocate end SID dynamically";
             uses apply-advanced;
             container flavor {
               presence "enable flavor";
               description "Configure end-SID flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
           leaf micro-node-sid {
             description "Program and advertise micro-node-SID";
             type empty;
           }
         }
       }
     }
     list level {
       key name;
       ordered-by user;
       description "Configure global level attributes";
       leaf name {
         description "IS-IS level number";
         type union {
           type string {
             pattern "<.*>|$.*";
           }
           type uint32 {
             range "1 .. 2";
           }
         }
       }
       uses apply-advanced;
       leaf labeled-preference {
         description "Preference of labeled IS-IS routes";
         type union {
           type uint32;
           type string {
             pattern "<.*>|$.*";
           }
         }
       }
       leaf srv6-preference {
         description "Preference of SRV6 IS-IS routes";
         type union {
           type uint32;
           type string {
             pattern "<.*>|$.*";
           }
         }
       }
       leaf flex-algorithm-preference {
         description "Preference of flex-algorithm L-ISIS routes";
         type union {
           type uint32;
           type string {
             pattern "<.*>|$.*";
           }
         }
       }
       container source-packet-routing {
         presence "enable source-packet-routing";
         description "Enable Source Packet Routing (SPRING)";
         uses apply-advanced;
         choice enable-disable {
           case case_1 {
             leaf disable {
               description "Disable Source Packet Routing on this level";
               type empty;
             }
           }
         }
         leaf srms-preference {
           description "Set SRMS preference value";
           type union {
             type string {
               pattern "<.*>|$.*";
             }
             type uint32 {
               range "0 .. 255";
             }
           }
         }
       }
       choice enable-disable {
         case case_1 {
           leaf disable {
             description "Disable IS-IS on this level";
             type empty;
           }
         }
       }
       leaf authentication-key {
         description "Authentication key (password)";
         type jt:unreadable;
       }
       leaf authentication-type {
         description "Authentication type";
         type enumeration {
           enum "md5" {
             description "MD5 authentication";
           }
           enum "simple" {
             description "Simple password authentication";
           }
         }
       }
       leaf purge-originator {
         description "Add Purge Originator information";
         type enumeration {
           enum "self" {
             description "Add POI only for self-originated purge LSPs";
           }
           enum "empty" {
             description "Add POI for purge LSPs who do not have POI information";
           }
         }
       }
       leaf no-hello-authentication {
         description "Disable authentication for hello packets";
         type empty;
       }
       leaf no-csnp-authentication {
         description "Disable authentication for CSN packets";
         type empty;
       }
       leaf no-psnp-authentication {
         description "Disable authentication for PSN packets";
         type empty;
       }
       leaf no-lsp-authentication {
         description "Disable authentication for LSP packets";
         type empty;
       }
       leaf authentication-key-chain {
         description "Key chain name";
         type string {
           length "1 .. 128";
         }
       }
       leaf wide-metrics-only {
         description "Generate wide metrics only";
         type empty;
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf prefix-export-limit {
         description "Maximum number of external prefixes that can be exported";
         type union {
           type string {
             pattern "<.*>|$.*";
           }
           type uint32 {
             range "0 .. 4294967295";
           }
         }
       }
       leaf max-lsp-size {
         description "Maximum size allowed for LSPs";
         type union {
           type string {
             pattern "<.*>|$.*";
           }
           type uint32 {
             range "512 .. 9192";
           }
         }
       }
       container flood-reflector {
         description "Enable flood-reflector";
         uses apply-advanced;
         choice flood-reflector-choice {
           case case_1 {
             container reflector {
               description "Configure this as a flood-reflector";
               uses apply-advanced;
               leaf cluster-id {
                 description "Cluster-ID";
                 type union {
                   type string {
                     pattern "<.*>|$.*";
                   }
                   type uint32 {
                     range "1 .. 4294967295";
                   }
                 }
                 mandatory true;
               }
             }
           }
           case case_2 {
             leaf client {
               description "Configure interface as flood-reflector client";
               type empty;
             }
           }
         }
       }
     }
     list interface-group {
       key name;
       description "Interface grouping configuration";
       leaf name {
         description "Interface group name";
         type string;
       }
       uses apply-advanced;
       list level {
         key name;
         ordered-by user;
         description "Configure levels on this interface-group";
         leaf name {
           description "IS-IS level number";
           type union {
             type string {
               pattern "<.*>|$.*";
             }
             type uint32 {
               range "1 .. 2";
             }
           }
         }
         uses apply-advanced;
         container ipv4-adjacency-segment {
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
                 mandatory true;
               }
             }
           }
         }
       }
       container link-group-protection {
         description "Configure link group protection";
         uses apply-advanced;
         leaf minimum-bandwidth {
           description "Minimum bandwidth to carry traffic";
           type string;
         }
         leaf revert-bandwidth {
           description "Revert bandwidth to carry traffic";
           type string;
         }
       }
       list interface {
         key name;
         description "List interfaces for this group";
         leaf name {
           description "Interface name";
           type union {
             type jt:interface-name;
             type string {
               pattern "<.*>|$.*";
             }
           }
         }
         uses apply-advanced;
         leaf weight {
           description "Interface weight for adjacency set";
           type union {
             type string {
               pattern "<.*>|$.*";
             }
             type uint32 {
               range "1 .. 255";
             }
           }
         }
       }
     }
     container spf-options {
       description "Configure SPF attributes";
       uses apply-advanced;
       container microloop-avoidance {
         description "Configure microloop avoidance mechanisms";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Set maximum number of label supported for Micro-Loop-Avoidance calculations";
             type union {
               type string {
                 pattern "<.*>|$.*";
               }
               type uint32 {
                 range "2 .. 8";
               }
             }
           }
           leaf maximum-srv6-sids {
             description "Set maximum number of SRV6 SIDs supported for Micro-Loop-Avoidance calculations";
             type union {
               type string {
                 pattern "<.*>|$.*";
               }
               type uint32 {
                 range "2 .. 12";
               }
             }
           }
         }
       }
       leaf delay {
         description "Time to wait before running an SPF";
         units "milliseconds";
         type union {
           type string {
             pattern "<.*>|$.*";
           }
           type uint32 {
             range "50 .. 1000";
           }
         }
       }
       leaf holddown {
         description "Time to hold down before running an SPF";
         units "milliseconds";
         type union {
           type string {
             pattern "<.*>|$.*";
           }
           type uint32 {
             range "1000 .. 10000";
           }
         }
       }
       leaf rapid-runs {
         description "Number of rapid SPF runs before SPF holddown";
         type union {
           type string {
             pattern "<.*>|$.*";
           }
           type uint32 {
             range "1 .. 5";
           }
         }
       }
       container multipath {
         description "Configure multipath options";
         uses apply-advanced;
         container weighted {
           description "Weighted multipath options";
           uses apply-advanced;
           leaf one-hop {
             description "Enable load balancing on onehop multipath based on interface bandwidth";
             type empty;
           }
         }
       }
     }
     container traceoptions {
       description "Trace options for IS-IS";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "post-convergence-lfa" {
               description "Trace post-convergence-lfa related events";
             }
             enum "error" {
               description "Trace errored packets";
             }
             enum "spf" {
               description "Trace SPF events";
             }
             enum "packets" {
               description "Trace IS-IS packets";
             }
             enum "hello" {
               description "Trace hello packets";
             }
             enum "lsp" {
               description "Trace link-state packets";
             }
             enum "psn" {
               description "Trace partial sequence number (PSN) packets";
             }
             enum "csn" {
               description "Trace complete sequence number (CSN) packets";
             }
             enum "layer2-map" {
               description "Trace ARP/ND kernel state manipulation";
             }
             enum "lsp-generation" {
               description "Trace LSP generation";
             }
             enum "graceful-restart" {
               description "Trace graceful restart events";
             }
             enum "ldp-synchronization" {
               description "Trace synchronization between IS-IS and LDP";
             }
             enum "nsr-synchronization" {
               description "Trace NSR synchronization events";
             }
             enum "spring" {
               description "Trace source packet routing";
             }
             enum "prefix-sid" {
               description "Trace source packet routing, prefix-sids";
             }
             enum "flex-algorithm" {
               description "Trace flex-algorithm related events";
             }
             enum "adj-sid" {
               description "Trace adj-sid related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "srv6" {
               description "Trace srv6 related events";
             }
             enum "rmopd" {
               description "Trace rmopd interactions";
             }
             enum "mapping-server" {
               description "Trace mapping server related events";
             }
             enum "prefix-unreachable" {
               description "Trace unreachable prefix advertisement related events";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container backup-spf-options {
       description "Configure backup SPF attributes";
       uses apply-advanced;
       container remote-backup-calculation {
         presence "enable remote-backup-calculation";
         description "Calculate Remote LFA backup nexthops";
         uses apply-advanced;
       }
       container use-post-convergence-lfa {
         presence "enable use-post-convergence-lfa";
         description "Calculate Post Convergence Backup Nexthops";
         uses apply-advanced;
         leaf maximum-labels {
           description "Set maximum number of label supported for post convergence path calculations";
           type union {
             type string {
               pattern "<.*>|$.*";
             }
             type uint32 {
               range "2 .. 8";
             }
           }
         }
         leaf maximum-srv6-sids {
           description "Set maximum number of SRV6 SIDs for post convergence path calculations";
           type union {
             type string {
               pattern "<.*>|$.*";
             }
             type uint32 {
               range "2 .. 12";
             }
           }
         }
       }
       container use-source-packet-routing {
         presence "enable use-source-packet-routing";
         description "Use SPRING routed paths for protection";
         uses apply-advanced;
       }
       leaf per-prefix-calculation {
         description "Calculate backup nexthops for non-best prefix originators";
         type empty;
       }
       leaf node-link-degradation {
         description "Degrade to link protection when nodelink protection not available";
         type empty;
       }
     }
     list context-identifier {
       key name;
       ordered-by user;
       description "Configuration for advertisement of a context-identifier ";
       leaf name {
         description "Context identifier range";
         type jt:ipprefix;
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
       }
     }
     choice enable-disable {
       case case_1 {
         leaf disable {
           description "Disable IS-IS";
           type empty;
         }
       }
     }
     leaf-list export {
       ordered-by user;
       description "Export policy";
       type jt:policy-algebra;
     }
     leaf-list import {
       ordered-by user;
       description "Import policy";
       type jt:policy-algebra;
     }
     leaf reference-bandwidth {
       description "Bandwidth for calculating metric defaults";
       type string;
     }
     leaf job-stats {
       description "Collect job statistics";
       type empty;
     }
     leaf lsp-lifetime {
       description "Lifetime of LSPs";
       units "seconds";
       type union {
         type string {
           pattern "<.*>|$.*";
         }
         type uint32 {
           range "350 .. 65535";
         }
       }
     }
     leaf max-lsp-size {
       description "Maximum size allowed for LSPs";
       default "1492";
       type union {
         type string {
           pattern "<.*>|$.*";
         }
         type uint32 {
           range "512 .. 9192";
         }
       }
     }
     leaf max-hello-size {
       description "Maximum size allowed for ISIS Hello PDUs";
       default "1492";
       type union {
         type string {
           pattern "<.*>|$.*";
         }
         type uint32 {
           range "512 .. 16000";
         }
       }
     }
     leaf max-snp-size {
       description "Maximum size allowed for Sequence Number (Complete/Partial) PDUs";
       default "1400";
       type union {
         type string {
           pattern "<.*>|$.*";
         }
         type uint32 {
           range "512 .. 1400";
         }
       }
     }
     leaf spf-delay {
       description "Time to wait before running an SPF";
       status deprecated;
       units "milliseconds";
       type union {
         type string {
           pattern "<.*>|$.*";
         }
         type uint32 {
           range "50 .. 120000";
         }
       }
     }
     leaf authentication-key {
       description "Authentication key (password)";
       status deprecated;
       type jt:unreadable;
     }
     leaf authentication-type {
       description "Authentication type";
       status deprecated;
       type enumeration {
         enum "md5" {
           description "MD5 authentication";
           status deprecated;
         }
         enum "simple" {
           description "Simple password authentication";
           status deprecated;
         }
       }
     }
     leaf loose-authentication-check {
       description "Verify authentication only if PDU has authentication TLV";
       type empty;
     }
     leaf max-areas {
       description "Maximum number of advertised Areas";
       default "3";
       type union {
         type string {
           pattern "<.*>|$.*";
         }
         type uint32 {
           range "3 .. 64";
         }
       }
     }
     leaf no-authentication-check {
       description "Disable authentication checking";
       type empty;
     }
     leaf no-ipv4-routing {
       description "Disable IPv4 routing";
       type empty;
     }
     leaf no-ipv6-routing {
       description "Disable IPv6 routing";
       type empty;
     }
     leaf no-adjacency-holddown {
       description "Disable adjacency hold down";
       type empty;
     }
     leaf multicast-topology {
       description "Enable multicast topology";
       status deprecated;
       type empty;
     }
     leaf ignore-attached-bit {
       description "Ignore the attached bit in Level 1 LSPs";
       type empty;
     }
     container rib-group {
       description "Routing table group for importing IS-IS routes";
       uses rib_group_type;
     }
     container no-external-export {
       description "No external export";
       uses apply-advanced;
       list protocol {
         key name;
         ordered-by user;
         description "Protocol parameters";
         leaf name {
           type enumeration {
             enum "bgp" {
               description "BGP";
             }
             enum "ospf" {
               description "OSPF";
             }
             enum "isis" {
               description "ISIS";
             }
             enum "l-isis" {
               description "Labelled ISIS";
             }
             enum "l-ospf" {
               description "Labelled OSPF";
             }
             enum "static" {
               description "Static";
             }
           }
         }
       }
     }
     container strict-dual-isis {
       presence "enable strict-dual-isis";
       description "Enable dual isis if spf computation is required for both ipv4 and ipv6 family";
       uses apply-advanced;
       leaf holdown {
         description "Time to wait for ipv4 and ipv6 connectivity";
         status deprecated;
         default "12";
         type union {
           type string {
             pattern "<.*>|$.*";
           }
           type uint32 {
             range "1 .. 65535";
           }
         }
       }
       leaf holddown {
         description "Time to wait for ipv4 and ipv6 connectivity";
         default "12";
         type union {
           type string {
             pattern "<.*>|$.*";
           }
           type uint32 {
             range "1 .. 65535";
           }
         }
       }
     }
     container topologies {
       description "Enable topologies";
       uses apply-advanced;
       leaf ipv4-multicast {
         description "Enable IPv4-multicast topology";
         type empty;
       }
       leaf ipv6-unicast {
         description "Enable IPv6-unicast topology";
         type empty;
       }
       leaf ipv6-multicast {
         description "Enable IPv6-multicast topology";
         type empty;
       }
     }
     container overload {
       presence "enable overload";
       description "Set the overload bit (no transit traffic)";
       uses apply-advanced;
       leaf timeout {
         description "Time after which overload bit is reset";
         units "seconds";
         type union {
           type string {
             pattern "<.*>|$.*";
           }
           type uint32 {
             range "60 .. 3600";
           }
         }
       }
       leaf advertise-high-metrics {
         description "Advertise high metrics instead of setting the overload bit";
         type empty;
       }
       leaf allow-route-leaking {
         description "Allow routes to be leaked when overload is configured";
         type empty;
       }
       leaf internal-prefixes {
         description "Allow internal prefixes to be advertised with high metric";
         type empty;
       }
       leaf external-prefixes {
         description "Allow external prefixes to be advertised with high metric";
         type empty;
       }
     }
     container dynamic-overload {
       description "Set the dynamic overload options";
       uses apply-advanced;
       leaf no-overload-on-prefix-export-limit {
         description "Do not set overload bit when prefix export limit is reached";
         type empty;
       }
       leaf auto-recovery {
         description "Enable Auto recovery to recover from dynamic overload state";
         type empty;
       }
     }
     container graceful-restart {
       description "IS-IS graceful restart options";
       choice enable-disable {
         case case_1 {
           leaf disable {
             description "Disable graceful restart";
             type empty;
           }
         }
       }
       leaf helper-disable {
         description "Disable graceful restart helper capability";
         type empty;
       }
       leaf restart-duration {
         description "Maximum time for graceful restart to finish";
         units "seconds";
         type union {
           type string {
             pattern "<.*>|$.*";
           }
           type uint32 {
             range "30 .. 300";
           }
         }
       }
     }
     list net {
       key name;
       description "Assign Network Entity Title (NET) configuration";
       leaf name {
         description "Assign Network Entity Title (NET) address to an IS-IS router";
         type jt:isoaddr;
       }
     }
     leaf rfc7775-compliance {
       description "RFC 7775 compliance for up/down bit and prefix attribute sub-tlv";
       type empty;
     }
   }
   grouping juniper-protocols-l2control {
     uses apply-advanced;
     container traceoptions {
       description "Global tracing options for STP";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "ppmlite" {
               description "Trace libppmlite processing";
             }
             enum "all" {
               description "Trace everything";
             }
           }
         }
         leaf disable {
           description "Disable this trace flag";
           type empty;
         }
       }
     }
   }
   grouping juniper-protocols-ldp {
     uses apply-advanced;
     container traceoptions {
       description "Trace options for LDP";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "event" {
               description "Trace LDP state machine events";
             }
             enum "packet-dump" {
               description "Dump the contents of selected packet types";
             }
             enum "packets" {
               description "Trace all LDP packets";
             }
             enum "periodic" {
               description "Trace periodic (hello and keepalive) packets";
             }
             enum "initialization" {
               description "Trace initialization packets";
             }
             enum "notification" {
               description "Trace notification packets";
             }
             enum "address" {
               description "Trace address packets";
             }
             enum "label" {
               description "Trace label packets";
             }
             enum "binding" {
               description "Trace label binding state";
             }
             enum "path" {
               description "Trace label path state";
             }
             enum "ppmd" {
               description "Trace state and events for ppmd process";
             }
             enum "nsr-synchronization" {
               description "Trace NSR synchronization events";
             }
             enum "link-protection" {
               description "Trace link protection events";
             }
             enum "p2mp-nsr-synchronization" {
               description "Trace p2mp NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses ldp_filter_obj;
         }
       }
     }
     container auto-targeted-session {
       presence "enable auto-targeted-session";
       description "Configure auto targeted session parameters";
       uses apply-advanced;
       leaf teardown-delay {
         description "Auto targeted session tear down delay";
         default "90";
         units "seconds";
         type union {
           type string {
             pattern "<.*>|$.*";
           }
           type uint32 {
             range "1 .. 300";
           }
         }
       }
       leaf maximum-sessions {
         description "Auto targeted maximum sessions";
         default "100";
         type union {
           type string {
             pattern "<.*>|$.*";
           }
           type uint32 {
             range "1 .. 1000";
           }
         }
       }
       leaf no-rlfa {
         description "Do not allow RLFA in auto targeted sessions";
         type empty;
       }
       leaf no-dynamic-tunnels {
         description "Do not allow dynamic tunnels in auto targeted sessions";
         type empty;
       }
     }
     leaf preference {
       description "Route preference";
       type union {
         type uint32;
         type string {
           pattern "<.*>|$.*";
         }
       }
     }
     leaf no-forwarding {
       description "Do not use LDP ingress routes for forwarding";
       type empty;
     }
     leaf rib-group {
       description "Routing table group for importing ingress routes";
       type string;
     }
     leaf rib-group6 {
       description "Routing table group for importing ingress v6 routes";
       type string;
     }
     leaf l2-smart-policy {
       description "Do not export or import Layer 3 FECs for Layer 2 sessions";
       type empty;
     }
     leaf track-igp-metric {
       description "Track the IGP metric";
       type empty;
     }
     leaf strict-targeted-hellos {
       description "Do not send targeted hellos to unconfigured neighbors";
       type empty;
     }
     container longest-match {
       presence "enable longest-match";
       description "Configure longest match";
       uses apply-advanced;
       leaf-list policy {
         ordered-by user;
         description "Longest match import policy";
         type jt:policy-algebra;
       }
     }
     leaf-list import {
       ordered-by user;
       description "Import policy";
       type jt:policy-algebra;
     }
     leaf-list export {
       ordered-by user;
       description "Export policy";
       type jt:policy-algebra;
     }
     leaf-list egress-policy {
       ordered-by user;
       description "Configure LSP egress policy";
       type jt:policy-algebra;
     }
     leaf-list dod-request-policy {
       ordered-by user;
       description "Configure DoD label request policy";
       type jt:policy-algebra;
     }
     choice deaggregate-choice {
       leaf deaggregate {
         description "Deaggregate FECs into separate labels";
         type empty;
       }
       leaf no-deaggregate {
         description "Don't deaggregate FECs into separate labels";
         type empty;
       }
     }
     leaf explicit-null {
       description "Advertise the EXPLICIT_NULL label for egress FECs";
       type empty;
     }
     leaf label-withdrawal-delay {
       description "Delay label withdrawal for FECs to avoid label churn";
       default "60";
       units "seconds";
       type union {
         type string {
           pattern "<.*>|$.*";
         }
         type uint32 {
           range "0 .. 120";
         }
       }
     }
     container transport-address {
       description "Address used for TCP sessions";
       choice address-choice {
         case case_1 {
           leaf router-id {
             description "Use router ID for TCP connections";
             type empty;
           }
         }
         case case_2 {
           leaf interface {
             description "Use interface address for TCP connections";
             type empty;
           }
         }
         case case_3 {
           leaf address {
             description "Use specified address for TCP connections";
             type jt:ipaddr;
           }
         }
       }
     }
     leaf keepalive-interval {
       description "Keepalive interval (seconds)";
       type union {
         type string {
           pattern "<.*>|$.*";
         }
         type uint32 {
           range "1 .. 65535";
         }
       }
     }
     leaf keepalive-timeout {
       description "Keepalive timeout (seconds)";
       type union {
         type string {
           pattern "<.*>|$.*";
         }
         type uint32 {
           range "1 .. 65535";
         }
       }
     }
     list interface {
       key name;
       description "Enable LDP on this interface";
       leaf name {
         description "Interface name";
         type union {
           type jt:interface-name;
           type string {
             pattern "<.*>|$.*";
           }
         }
       }
       uses apply-advanced;
       choice enable-disable {
         case case_1 {
           leaf disable {
             description "Disable LDP on this interface";
             type empty;
           }
         }
       }
       leaf hello-interval {
         description "Hello interval (seconds)";
         type union {
           type string {
             pattern "<.*>|$.*";
           }
           type uint32 {
             range "1 .. 65535";
           }
         }
       }
       leaf hold-time {
         description "Hello hold time (seconds)";
         type union {
           type string {
             pattern "<.*>|$.*";
           }
           type uint32 {
             range "1 .. 65535";
           }
         }
       }
       container transport-address {
         description "Address used for TCP sessions";
         choice address-choice {
           case case_1 {
             leaf router-id {
               description "Use router ID for TCP connections";
               type empty;
             }
           }
           case case_2 {
             leaf interface {
               description "Use interface address for TCP connections";
               type empty;
             }
           }
           case case_3 {
             leaf address {
               description "Use specified address for TCP connections";
               type jt:ipaddr;
             }
           }
         }
       }
     }
     list neighbor {
       key name;
       description "Configure a remote LDP neighbor";
       leaf name {
         description "Neighbor address";
         type jt:ipaddr;
       }
       uses apply-advanced;
     }
     list session {
       key name;
       description "Configure session parameters";
       leaf name {
         description "Session destination address";
         type jt:ipaddr;
       }
       uses apply-advanced;
       leaf authentication-key {
         description "MD5 authentication key";
         type string {
           length "1 .. 126";
         }
       }
       leaf downstream-on-demand {
         description "Configure downstream on demand label distribution mode";
         type empty;
       }
       leaf transport-address {
         description "Address used for TCP sessions to the neighbor";
         type jt:ipaddr;
       }
     }
     list session-group {
       key name;
       description "Configure session group parameters";
       leaf name {
         description "Session destination address/prefix length";
         type jt:ipprefix;
       }
       uses apply-advanced;
       leaf authentication-key {
         description "MD5 authentication key";
         type string {
           length "1 .. 126";
         }
       }
       leaf downstream-on-demand {
         description "Configure downstream on demand label distribution mode";
         type empty;
       }
       leaf transport-address {
         description "Address used for TCP sessions to the neighbor";
         type jt:ipaddr;
       }
     }
     container session-protection {
       presence "enable session-protection";
       description "Configure session protection";
       leaf timeout {
         description "Session protection timeout";
         units "seconds";
         type union {
           type string {
             pattern "<.*>|$.*";
           }
           type uint16 {
             range "1 .. 65535";
           }
         }
       }
     }
     container igp-synchronization {
       description "Configure IGP synchronization parameters";
       uses apply-advanced;
       leaf holddown-interval {
         description "Time to hold the up notification to the IGPs";
         units "seconds";
         type union {
           type string {
             pattern "<.*>|$.*";
           }
           type uint32 {
             range "10 .. 300";
           }
         }
       }
     }
     container targeted-hello {
       description "Configure targeted hello parameters";
       uses apply-advanced;
       leaf hello-interval {
         description "Hello interval (seconds)";
         type union {
           type string {
             pattern "<.*>|$.*";
           }
           type uint32 {
             range "1 .. 65535";
           }
         }
       }
       leaf hold-time {
         description "Hold interval (seconds)";
         type union {
           type string {
             pattern "<.*>|$.*";
           }
           type uint32 {
             range "1 .. 65535";
           }
         }
       }
     }
     container sr-mapping-client {
       presence "enable sr-mapping-client";
       description "Enable LDP to SR mapping-client functionality";
       uses apply-advanced;
       leaf-list policy {
         ordered-by user;
         description "SR mapping-client policy";
         type jt:policy-algebra;
       }
     }
     leaf upstream-label-assignment {
       description "Allow Upstream Label Assignment capability";
       type empty;
     }
     list family {
       key name;
       ordered-by user;
       description "Address family";
       leaf name {
         type enumeration {
           enum "inet" {
             description "IPv4 family";
           }
           enum "inet6" {
             description "IPv6 family";
           }
         }
       }
       uses apply-advanced;
     }
     leaf transport-preference {
       description "TCP transport preference";
       type enumeration {
         enum "ipv4" {
           description "Use IPv4 for TCP connections";
         }
         enum "ipv6" {
           description "Use IPv6 for TCP connections";
         }
       }
     }
     container dual-transport {
       presence "enable dual-transport";
       description "Use separate IPv4 and IPv6 TCP transport";
       uses apply-advanced;
       leaf inet-lsr-id {
         description "LSR identifier for address family inet";
         type jt:ipv4addr;
         mandatory true;
       }
       leaf inet6-lsr-id {
         description "LSR identifier for address family inet6";
         type jt:ipv4addr;
         mandatory true;
       }
     }
     leaf no-propagate-ttl {
       description "Disable TTL propagation from IP to MPLS (on push) and MPLS to IP (on pop)";
       type empty;
     }
   }
   grouping juniper-protocols-mpls {
     description "Multiprotocol Label Switching options";
     uses apply-advanced;
     list lsp-external-controller {
       key name;
       ordered-by user;
       description "External path computing entity";
       leaf name {
         description "Name of the external path computing entity";
         type string {
         }
       }
       uses apply-advanced;
       container label-switched-path-template {
         description "Template for externally provisioned LSP parameters";
         uses apply-advanced;
         choice dynamic-template {
           case case_1 {
             leaf template-name {
               description "Name of point-to-point LSP template";
               type string {
                 length "1 .. 32";
               }
             }
           }
           case case_2 {
             leaf default-template {
               description "Use default parameters";
               type empty;
             }
           }
         }
       }
       container label-switched-path-p2mp-template {
         description "Template for externally provisioned P2MP LSP parameters";
         uses apply-advanced;
         choice dynamic-template {
           case case_1 {
             leaf template-name {
               description "Name of point-to-multipoint LSP template";
               type string {
                 length "1 .. 32";
               }
             }
           }
           case case_2 {
             leaf default-template {
               description "Use default parameters";
               type empty;
             }
           }
         }
       }
       list pce-controlled-lsp {
         key name;
         ordered-by user;
         description "Template for externally provisioned LSP using regular expression";
         leaf name {
           description "Template regular expression";
           type string {
           }
         }
         uses apply-advanced;
         container label-switched-path-template {
           description "Template for externally provisioned LSP parameters";
           uses apply-advanced;
           leaf template-name {
             description "Name of point-to-point LSP template";
             type string {
               length "1 .. 64";
             }
           }
         }
         container label-switched-path-p2mp-template {
           description "Template for externally provisioned P2MP LSP parameters";
           uses apply-advanced;
           leaf template-name {
             description "Name of point-to-multipoint LSP template";
             type string {
               length "1 .. 64";
             }
           }
         }
       }
     }
     container path-mtu {
       presence "enable path-mtu";
       description "Path MTU configuration";
       uses apply-advanced;
       leaf allow-fragmentation {
         description "If needed, fragment IP before encapsulating in MPLS";
         type empty;
       }
       container rsvp {
         presence "enable rsvp";
         description "RSVP-specific path MTU options";
         uses apply-advanced;
         leaf mtu-signaling {
           description "Enable RSVP path MTU signaling";
           type empty;
         }
       }
     }
     container diffserv-te {
       description "Global diffserv-traffic-engineering options";
       uses apply-advanced;
       leaf bandwidth-model {
         description "Bandwidth constraint model supported";
         type enumeration {
           enum "extended-mam" {
             description "Maximum allocation model with support for E-LSPs";
           }
           enum "mam" {
             description "Maximum allocation model";
           }
           enum "rdm" {
             description "Russian dolls model";
           }
         }
       }
       container te-class-matrix {
         description "Supported combinations of traffic-class and preemption";
         uses apply-advanced;
         container te0 {
           description "Definition for traffic-engineering class te0";
           uses te-class-object;
         }
         container te1 {
           description "Definition for traffic-engineering class te1";
           uses te-class-object;
         }
         container te2 {
           description "Definition for traffic-engineering class te2";
           uses te-class-object;
         }
         container te3 {
           description "Definition for traffic-engineering class te3";
           uses te-class-object;
         }
         container te4 {
           description "Definition for traffic-engineering class te4";
           uses te-class-object;
         }
         container te5 {
           description "Definition for traffic-engineering class te5";
           uses te-class-object;
         }
         container te6 {
           description "Definition for traffic-engineering class te6";
           uses te-class-object;
         }
         container te7 {
           description "Definition for traffic-engineering class te7";
           uses te-class-object;
         }
       }
     }
     container auto-policing {
       description "Automatic policing of LSPs";
       uses apply-advanced;
       list class {
         key name;
         ordered-by user;
         description "Forwarding class";
         leaf name {
           type enumeration {
             enum "all" {
               description "All forwarding classes";
             }
             enum "ct0" {
               description "Forwarding class 0";
             }
             enum "ct1" {
               description "Forwarding class 1";
             }
             enum "ct2" {
               description "Forwarding class 2";
             }
             enum "ct3" {
               description "Forwarding class 3";
             }
           }
         }
         uses apply-advanced;
         choice policing-action {
           case case_1 {
             leaf drop {
               description "Drop packets if bandwidth is exceeded";
               type empty;
             }
           }
           case case_2 {
             leaf loss-priority-high {
               description "Set loss priority to high if bandwidth is exceeded";
               type empty;
             }
           }
           case case_3 {
             leaf loss-priority-low {
               description "Set loss priority to low if bandwidth is exceeded";
               type empty;
             }
           }
         }
       }
     }
     container statistics {
       description "Collect statistics for signaled label-switched paths";
       uses apply-advanced;
       container file {
         presence "enable file";
         description "Statistics file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "1 .. 65535";
           }
         }
       }
       leaf auto-bandwidth {
         description "Enable auto bandwidth allocation";
         type empty;
       }
       leaf no-transit-statistics {
         description "Disable transit LSP statistics collection";
         type empty;
       }
       choice transit-polling-type {
         case case_1 {
           leaf transit-statistics-polling {
             description "Enable polling and display of transit lsp statistics";
             type empty;
           }
         }
       }
       leaf no-bypass-statistics-polling {
         description "Disable polling and display of bypass lsp statistics";
         type empty;
       }
       leaf statistics-query-batch-size {
         description "Number of LSPs for which statistics will be queried together";
         type union {
           type string {
             pattern "<.*>|$.*";
           }
           type int32 {
             range "1 .. 25";
           }
         }
       }
     }
     container p2mp-lsp {
       description "P2MP LSP control configuration";
       uses apply-advanced;
       leaf single-abr {
         description "Try to use same exit node for all inter-domain sub LSPs";
         type empty;
       }
       leaf no-re-merge {
         description "Avoid LSP CSPF creating remerge";
         type empty;
       }
     }
     container log-updown {
       description "Logging actions for LSP up/down events";
       uses apply-advanced;
       choice syslog-choice {
         leaf syslog {
           description "Send syslog messages";
           type empty;
         }
         leaf no-syslog {
           description "Don't send syslog messages";
           type empty;
         }
       }
       choice trap-choice {
         case case_1 {
           leaf trap {
             description "Send SNMP traps";
             type empty;
           }
         }
         case case_2 {
           container no-trap {
             presence "enable no-trap";
             description "Don't send SNMP traps";
             uses apply-advanced;
             leaf mpls-lsp-traps {
               description "Dont send mpls lsp up/down traps";
               type empty;
             }
             leaf rfc3812-traps {
               description "Dont send rfc3812 traps";
               type empty;
             }
           }
         }
       }
       leaf trap-path-down {
         description "Send SNMP traps when a path goes down";
         type empty;
       }
       leaf trap-path-up {
         description "Send SNMP traps when a path goes up";
         type empty;
       }
     }
     container optimize-adaptive-teardown {
       description "Post make before break adaptive teardown";
       uses apply-advanced;
       leaf p2p {
         description "Turn on post make before break adaptive teardown for p2p";
         type empty;
       }
       leaf timeout {
         description "Timeout for adaptive teardown to clean up LSP";
         units "seconds";
         type union {
           type string {
             pattern "<.*>|$.*";
           }
           type int32 {
             range "1 .. 65535";
           }
         }
       }
       container delay {
         description "Delay tearing down old optimized path after adaptive-teardown kicks in";
         uses apply-advanced;
         leaf delay-value {
           description "Delay tearing down old optimized path after adaptive-teardown kicks in";
           units "seconds";
           type union {
             type string {
               pattern "<.*>|$.*";
             }
             type int32 {
               range "3 .. 65535";
             }
           }
         }
       }
     }
     container traffic-engineering {
       presence "enable traffic-engineering";
       description "Traffic-engineering control";
       uses apply-advanced;
       choice protocols {
         case case_1 {
           leaf bgp {
             description "BGP destinations only";
             type empty;
           }
         }
         case case_2 {
           leaf bgp-igp {
             description "BGP and IGP destinations";
             type empty;
           }
         }
         case case_3 {
           leaf bgp-igp-both-ribs {
             description "BGP and IGP destinations with routes in both routing tables";
             type empty;
           }
         }
         case case_4 {
           leaf mpls-forwarding {
             description "Use MPLS routes for forwarding, not routing";
             type empty;
           }
         }
       }
       container database {
         description "Traffic engineering database";
         uses apply-advanced;
         container import {
           description "Configure TED import parameters";
           uses apply-advanced;
           container l3-unicast-topology {
             presence "enable l3-unicast-topology";
             description "Download L3-Unicast topology into RIB";
             uses apply-advanced;
             leaf bgp-link-state {
               description "Export L3-Unicast topology, instead of TE topology, into BGP-LS";
               type empty;
             }
           }
           leaf-list policy {
             ordered-by user;
             description "Configure import policy";
             type jt:policy-algebra;
           }
           leaf identifier {
             description "BGP-TE identifier";
             type union {
               type string {
                 pattern "<.*>|$.*";
               }
               type uint64 {
                 range "2 .. 18446744073709551615";
               }
             }
           }
           leaf bgp-ls-identifier {
             description "BGP-TE domain identifier";
             type union {
               type uint32;
               type string {
                 pattern "<.*>|$.*";
               }
             }
           }
           leaf ipv6 {
             description "Import ipv6 addresses";
             type empty;
           }
         }
         container export {
           description "Configure TED export related parameters";
           uses apply-advanced;
           leaf-list policy {
             ordered-by user;
             description "Export policy";
             type jt:policy-algebra;
           }
           container credibility {
             description "TED credibility value for entries from BGP-TE";
             uses apply-advanced;
             leaf unknown {
               description "Entries sourced from unknown entities";
               type union {
                 type string {
                   pattern "<.*>|$.*";
                 }
                 type uint32 {
                   range "0 .. 512";
                 }
               }
             }
             leaf direct {
               description "Entries sourced from directly connected links";
               type union {
                 type string {
                   pattern "<.*>|$.*";
                 }
                 type uint32 {
                   range "0 .. 512";
                 }
               }
             }
             leaf static {
               description "Entries sourced from static configuration";
               type union {
                 type string {
                   pattern "<.*>|$.*";
                 }
                 type uint32 {
                   range "0 .. 512";
                 }
               }
             }
             leaf ospf {
               description "Entries sourced from ospf";
               type union {
                 type string {
                   pattern "<.*>|$.*";
                 }
                 type uint32 {
                   range "0 .. 512";
                 }
               }
             }
             leaf isis-level-1 {
               description "Entries sourced from ISIS Level 1";
               type union {
                 type string {
                   pattern "<.*>|$.*";
                 }
                 type uint32 {
                   range "0 .. 512";
                 }
               }
             }
             leaf isis-level-2 {
               description "Entries sourced from ISIS Level 2";
               type union {
                 type string {
                   pattern "<.*>|$.*";
                 }
                 type uint32 {
                   range "0 .. 512";
                 }
               }
             }
             leaf bgp {
               description "Entries sourced from BGP";
               type union {
                 type string {
                   pattern "<.*>|$.*";
                 }
                 type uint32 {
                   range "0 .. 512";
                 }
               }
             }
           }
           leaf l3-unicast-topology {
             description "Download RIB entries into L3-Unicast topology";
             type empty;
           }
         }
       }
     }
     list admin-groups {
       key name;
       ordered-by user;
       description "Administrative groups";
       leaf name {
         description "Group name";
         type string;
       }
       uses apply-advanced;
       leaf group-value {
         description "Group bit position";
         type union {
           type string {
             pattern "<.*>|$.*";
           }
           type uint32 {
             range "0 .. 31";
           }
         }
       }
     }
     leaf advertisement-hold-time {
       description "Time that an 'LSP down' advertisement will be delayed";
       default "5";
       units "seconds";
       type union {
         type string {
           pattern "<.*>|$.*";
         }
         type uint32 {
           range "0 .. 65535";
         }
       }
     }
     leaf rsvp-error-hold-time {
       description "Time that RSVP PathErr events will be remembered";
       default "25";
       units "seconds";
       type union {
         type string {
           pattern "<.*>|$.*";
         }
         type uint32 {
           range "0 .. 240";
         }
       }
     }
     leaf optimize-aggressive {
       description "Run aggressive optimization algorithm based on IGP metric only";
       type empty;
     }
     leaf smart-optimize-timer {
       description "Path optimization interval after a link traversed by the path goes down";
       units "seconds";
       type union {
         type string {
           pattern "<.*>|$.*";
         }
         type int32 {
           range "0 .. 65535";
         }
       }
     }
     leaf optimize-switchover-delay {
       description "Delay before switching LSP to newly optimized path";
       units "seconds";
       type union {
         type string {
           pattern "<.*>|$.*";
         }
         type int32 {
           range "1 .. 900";
         }
       }
     }
     leaf no-propagate-ttl {
       description "Disable TTL propagation from IP to MPLS (on push) and MPLS to IP (on pop)";
       type empty;
     }
     leaf explicit-null {
       description "Advertise the EXPLICIT_NULL label when the router is the egress";
       type empty;
     }
     leaf icmp-tunneling {
       description "Allow MPLS LSPs to be used for tunneling ICMP error packets";
       type empty;
     }
     leaf non-aggressive-make-before-break-cleanup {
       description "Defer path-degraded notifys until old instance is deleted";
       type empty;
     }
     leaf revert-timer {
       description "Hold-down window before reverting back to primary path, 0 means disable";
       units "seconds";
       type union {
         type string {
           pattern "<.*>|$.*";
         }
         type int32 {
           range "0 .. 65535";
         }
       }
     }
     leaf optimize-hold-dead-delay {
       description "Delay before tearing down the old optimized path";
       units "seconds";
       type union {
         type string {
           pattern "<.*>|$.*";
         }
         type int32 {
           range "0 .. 65535";
         }
       }
     }
     leaf cspf-backoff-time {
       description "Delay before CSPF, when there is PathErr on backup path";
       units "seconds";
       type union {
         type string {
           pattern "<.*>|$.*";
         }
         type int32 {
           range "0 .. 65535";
         }
       }
     }
     container adaptive-wait-timer {
       presence "enable adaptive-wait-timer";
       description "Enable adaptive wait timer for path messages.";
       uses apply-advanced;
       leaf initial-time {
         description "Initial time for adaptive wait timer";
         default "180";
         units "seconds";
         type union {
           type string {
             pattern "<.*>|$.*";
           }
           type int32 {
             range "180 .. 1800";
           }
         }
       }
       leaf max-time {
         description "Maximum time for adaptive wait timer";
         default "1800";
         units "seconds";
         type union {
           type string {
             pattern "<.*>|$.*";
           }
           type int32 {
             range "180 .. 3600";
           }
         }
       }
       leaf backoff-multiplier {
         description "Multiplier to exponentially backoff the adaptive-wait-timer";
         default "2";
         type union {
           type string {
             pattern "<.*>|$.*";
           }
           type int32 {
             range "1 .. 5";
           }
         }
       }
     }
     leaf expand-loose-hop {
       description "Perform CSPF path computation to expand loose hops";
       type empty;
     }
     leaf mib-mpls-show-p2mp {
       description "Show p2mp tunnels entries in mpls mib walk";
       type empty;
     }
     container bandwidth {
       description "Bandwidth to reserve (bps)";
       uses bandwidth-type;
     }
     container admin-group {
       description "Administrative group policy";
       uses admin_group_include_exclude;
     }
     container admin-group-extended {
       description "Extended administrative group policy";
       uses admin_group_include_exclude;
     }
     container priority {
       presence "enable priority";
       description "Preemption priorities";
     }
     leaf setup-priority {
       description "Set-up priority";
       type union {
         type string {
           pattern "<.*>|$.*";
         }
         type uint32 {
           range "0 .. 7";
         }
       }
     }
     leaf reservation-priority {
       description "Reservation priority";
       type union {
         type string {
           pattern "<.*>|$.*";
         }
         type uint32 {
           range "0 .. 7";
         }
       }
     }
     container oam {
       description "Periodic OAM";
       uses periodic_oam;
     }
     leaf class-of-service {
       description "Class-of-service value";
       type union {
         type string {
           pattern "<.*>|$.*";
         }
         type int32 {
           range "0 .. 7";
         }
       }
     }
     leaf no-decrement-ttl {
       description "Do not decrement the TTL within an LSP";
       type empty;
     }
     leaf hop-limit {
       description "Maximum allowed router hops";
       type union {
         type string {
           pattern "<.*>|$.*";
         }
         type int32 {
           range "2 .. 255";
         }
       }
     }
     leaf no-cspf {
       description "Disable automatic path computation";
       type empty;
     }
     leaf admin-down {
       description "Set GMPLS LSP to administrative down state";
       type empty;
     }
     leaf optimize-timer {
       description "Periodical path reoptimizations";
       units "seconds";
       type union {
         type string {
           pattern "<.*>|$.*";
         }
         type int32 {
           range "0 .. 65535";
         }
       }
     }
     leaf preference {
       description "Preference value";
       type union {
         type uint32;
         type string {
           pattern "<.*>|$.*";
         }
       }
     }
     choice record-choice {
       leaf record {
         description "Record transit routers";
         type empty;
       }
       leaf no-record {
         description "Don't record transit routers";
         type empty;
       }
     }
     leaf standby {
       description "Keep backup paths in continuous standby";
       type empty;
     }
     leaf exclude-srlg {
       description "Exclude SRLG links for secondary path";
       type empty;
     }
     leaf ultimate-hop-popping {
       description "Request ultimate hop popping from egress";
       type empty;
     }
     leaf sync-active-path-bandwidth {
       description "Signal standby path with bandwidth obtained from active path";
       type empty;
     }
     leaf cross-credibility-cspf {
       description "Compute paths across multi-protocol links and nodes";
       type empty;
     }
     leaf top-credibility-only-cspf {
       description "Compute paths only using highest credibility links and nodes";
       type empty;
     }
     list label-switched-path {
       key name;
       ordered-by user;
       description "Label-switched path";
       leaf name {
         description "Name of path";
         type string {
           length "1 .. 64";
         }
       }
       uses apply-advanced;
       choice enable-disable {
         case case_1 {
           leaf disable {
             description "Disable MPLS label-switched path";
             type empty;
           }
         }
       }
       container traceoptions {
         description "Trace options for MPLS label-switched path";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "cspf" {
                 description "Trace CSPF computation";
               }
               enum "cspf-node" {
                 description "Trace nodes visited during CSPF";
               }
               enum "cspf-link" {
                 description "Trace links visited during CSPF";
               }
               enum "cspf-abstract" {
                 description "Trace abstract hop based CSPF details";
               }
               enum "state" {
                 description "Trace state transitions";
               }
               enum "all" {
                 description "Trace everything";
               }
             }
           }
         }
       }
       leaf no-install-to-address {
         description "Don't install host route 'to' address into routing tables";
         type empty;
       }
       leaf backup {
         description "Use LSP for IGP backup";
         type empty;
       }
       leaf from {
         description "Address of ingress router";
         type jt:ipv4addr;
       }
       container pop-and-forward {
         presence "enable pop-and-forward";
         description "Enable LSP as pop-and-forward with auto-delegation";
       }
       choice label-switched-path-or-template {
         case case_1 {
           leaf to {
             description "Address of egress router";
             type jt:ipv4addr;
           }
         }
         case case_2 {
           leaf template {
             description "Template for dynamic lsp paramaters";
             type empty;
           }
         }
       }
       leaf corouted-bidirectional {
         description "Setup the LSP as a corouted bidirectional LSP";
         type empty;
       }
       leaf corouted-bidirectional-passive {
         description "Associate LSP with incoming corouted bidirectional LSP";
         type empty;
       }
       leaf metric {
         description "Metric value";
         type union {
           type string {
             pattern "<.*>|$.*";
           }
           type uint32 {
             range "1 .. 16777215";
           }
         }
       }
       container conditional-metric {
         description "Set a conditional metric value for the LSP";
         uses apply-advanced;
         list igp-metric-threshold {
           key name;
           description "Set conditional LSP metric based on IGP metric, up to 4 conditions";
           max-elements 4;
           leaf name {
             description "Conditional IGP metric threshold";
             type union {
               type string {
                 pattern "<.*>|$.*";
               }
               type uint32 {
                 range "1 .. 16777215";
               }
             }
           }
           leaf conditional-metric-value {
             description "Conditional LSP metric value";
             type union {
               type string {
                 pattern "<.*>|$.*";
               }
               type uint32 {
                 range "1 .. 16777215";
               }
             }
           }
         }
       }
       container metric-type {
         description "Metric type used for computaion";
         uses apply-advanced;
         choice metric-type-choice {
           case case_1 {
             leaf te {
               description "TE metric";
               type empty;
             }
           }
           case case_2 {
             leaf igp {
               description "IGP metric";
               type empty;
             }
           }
           case case_3 {
             container delay {
               presence "enable delay";
               description "Delay metric";
               uses apply-advanced;
               choice metric-choice {
                 case case_1 {
                   leaf minimum {
                     description "Minimum delay metric type";
                     type empty;
                   }
                 }
                 case case_2 {
                   leaf maximum {
                     description "Maximum delay metric type";
                     type empty;
                   }
                 }
                 case case_3 {
                   leaf average {
                     description "Average delay metric type";
                     type empty;
                   }
                 }
               }
               leaf delay-variation-threshold {
                 description "Link delay variation threshold";
                 type union {
                   type string {
                     pattern "<.*>|$.*";
                   }
                   type uint32 {
                     range "1 .. 16777215";
                   }
                 }
               }
             }
           }
         }
       }
       leaf ldp-tunneling {
         description "Allow LDP to use this LSP for tunneling";
         type empty;
       }
       container soft-preemption {
         presence "enable soft-preemption";
         description "Attempt make-before-break service while preempting this LSP";
         uses apply-advanced;
       }
       list install {
         key name;
         ordered-by user;
         description "Install prefix";
         leaf name {
           description "Destination prefix";
           type jt:ipprefix;
         }
         leaf active {
           description "Install prefix into forwarding table";
           type empty;
         }
       }
       leaf retry-timer {
         description "Time before retrying the primary path";
         units "seconds";
         type union {
           type string {
             pattern "<.*>|$.*";
           }
           type uint32 {
             range "1 .. 600";
           }
         }
       }
       leaf retry-limit {
         description "Maximum number of times to retry primary path";
         type union {
           type string {
             pattern "<.*>|$.*";
           }
           type uint32 {
             range "0 .. 10000";
           }
         }
       }
       leaf revert-timer {
         description "Hold-down window before reverting back to primary path, 0 means disable";
         units "seconds";
         type union {
           type string {
             pattern "<.*>|$.*";
           }
           type int32 {
             range "0 .. 65535";
           }
         }
       }
       leaf optimize-hold-dead-delay {
         description "Delay before tearing down the old optimized path";
         units "seconds";
         type union {
           type string {
             pattern "<.*>|$.*";
           }
           type int32 {
             range "0 .. 65535";
           }
         }
       }
       leaf cspf-backoff-time {
         description "Delay before CSPF, when there is PathErr on backup path";
         units "seconds";
         type union {
           type string {
             pattern "<.*>|$.*";
           }
           type int32 {
             range "0 .. 65535";
           }
         }
       }
       container bandwidth {
         description "Bandwidth to reserve (bps)";
         uses bandwidth-type;
       }
       container admin-group {
         description "Administrative group policy";
         uses admin_group_include_exclude;
       }
       container admin-group-extended {
         description "Extended administrative group policy";
         uses admin_group_include_exclude;
       }
       container priority {
         presence "enable priority";
         description "Preemption priorities";
       }
       leaf setup-priority {
         description "Set-up priority";
         type union {
           type string {
             pattern "<.*>|$.*";
           }
           type uint32 {
             range "0 .. 7";
           }
         }
       }
       leaf reservation-priority {
         description "Reservation priority";
         type union {
           type string {
             pattern "<.*>|$.*";
           }
           type uint32 {
             range "0 .. 7";
           }
         }
       }
       container oam {
         description "Periodic OAM";
         uses periodic_oam;
       }
       leaf class-of-service {
         description "Class-of-service value";
         type union {
           type string {
             pattern "<.*>|$.*";
           }
           type int32 {
             range "0 .. 7";
           }
         }
       }
       leaf no-decrement-ttl {
         description "Do not decrement the TTL within an LSP";
         type empty;
       }
       leaf hop-limit {
         description "Maximum allowed router hops";
         type union {
           type string {
             pattern "<.*>|$.*";
           }
           type int32 {
             range "2 .. 255";
           }
         }
       }
       leaf no-cspf {
         description "Disable automatic path computation";
         type empty;
       }
       leaf admin-down {
         description "Set GMPLS LSP to administrative down state";
         type empty;
       }
       leaf optimize-timer {
         description "Periodical path reoptimizations";
         units "seconds";
         type union {
           type string {
             pattern "<.*>|$.*";
           }
           type int32 {
             range "0 .. 65535";
           }
         }
       }
       leaf preference {
         description "Preference value";
         type union {
           type uint32;
           type string {
             pattern "<.*>|$.*";
           }
         }
       }
       choice record-choice {
         leaf record {
           description "Record transit routers";
           type empty;
         }
         leaf no-record {
           description "Don't record transit routers";
           type empty;
         }
       }
       leaf standby {
         description "Keep backup paths in continuous standby";
         type empty;
       }
       leaf exclude-srlg {
         description "Exclude SRLG links for secondary path";
         type empty;
       }
       leaf ultimate-hop-popping {
         description "Request ultimate hop popping from egress";
         type empty;
       }
       leaf sync-active-path-bandwidth {
         description "Signal standby path with bandwidth obtained from active path";
         type empty;
       }
       leaf cross-credibility-cspf {
         description "Compute paths across multi-protocol links and nodes";
         type empty;
       }
       leaf top-credibility-only-cspf {
         description "Compute paths only using highest credibility links and nodes";
         type empty;
       }
       leaf entropy-label {
         description "Enable entropy label";
         type empty;
       }
       leaf self-ping-duration {
         description "Duration over which to run self-ping (65535 = until success). Default = 1800s";
         units "seconds";
         type union {
           type string {
             pattern "<.*>|$.*";
           }
           type int32 {
             range "1 .. 65535";
           }
         }
       }
       leaf no-self-ping {
         description "Do not run self-ping for this LSP";
         type empty;
       }
       choice cspf-attribute {
         case case_1 {
           leaf random {
             description "Randomly select among equal-cost paths";
             type empty;
           }
         }
         case case_2 {
           leaf least-fill {
             description "Select the least filled among equal-cost paths";
             type empty;
           }
         }
         case case_3 {
           leaf most-fill {
             description "Select the most filled among equal-cost paths";
             type empty;
           }
         }
       }
       leaf description {
         description "Text description of label-switched path";
         type string {
           length "1 .. 80";
         }
       }
       container adaptive-wait-timer {
         presence "enable adaptive-wait-timer";
         description "Enable adaptive wait timer for path messages.";
         uses apply-advanced;
         leaf initial-time {
           description "Initial time for adaptive wait timer";
           default "180";
           units "seconds";
           type union {
             type string {
               pattern "<.*>|$.*";
             }
             type int32 {
               range "180 .. 1800";
             }
           }
         }
         leaf max-time {
           description "Maximum time for adaptive wait timer";
           default "1800";
           units "seconds";
           type union {
             type string {
               pattern "<.*>|$.*";
             }
             type int32 {
               range "180 .. 3600";
             }
           }
         }
         leaf backoff-multiplier {
           description "Multiplier to exponentially backoff the adaptive-wait-timer";
           default "2";
           type union {
             type string {
               pattern "<.*>|$.*";
             }
             type int32 {
               range "1 .. 5";
             }
           }
         }
       }
       choice lp-type {
         case case_1 {
           container link-protection {
             presence "enable link-protection";
             description "Protect LSP from link faults only";
             uses apply-advanced;
             choice constraint-choice {
               case case_1 {
                 container inherit-lsp {
                   description "Inherit bypass properties from Primary LSPs";
                   leaf constraints {
                     description "Inherit bypass constraints from primary LSP";
                     type empty;
                   }
                 }
               }
               case case_2 {
                 container bypass-constraints {
                   description "Explicitly defined constraints for bypass LSPs";
                   uses apply-advanced;
                   leaf hop-limit {
                     description "Maximum allowed router hops";
                     type union {
                       type string {
                         pattern "<.*>|$.*";
                       }
                       type int32 {
                         range "0 .. 255";
                       }
                     }
                   }
                   choice include_any_or_no_include_any {
                     case case_1 {
                       leaf no-include-any {
                         description "Disable include-any checking";
                         type empty;
                       }
                     }
                     case case_2 {
                       leaf-list include-any {
                         ordered-by user;
                         description "Groups, one or more of which must be present";
                         type string;
                       }
                     }
                   }
                   choice include_all_or_no_include_all {
                     case case_1 {
                       leaf no-include-all {
                         description "Disable include-all checking";
                         type empty;
                       }
                     }
                     case case_2 {
                       leaf-list include-all {
                         ordered-by user;
                         description "Groups, all of which must be present";
                         type string;
                       }
                     }
                   }
                   choice exclude_or_no_exclude {
                     case case_1 {
                       leaf no-exclude {
                         description "Disable exclude checking";
                         type empty;
                       }
                     }
                     case case_2 {
                       leaf-list exclude {
                         ordered-by user;
                         description "Groups, all of which must be absent";
                         type string;
                       }
                     }
                   }
                 }
               }
             }
           }
         }
         case case_2 {
           container node-link-protection {
             presence "enable node-link-protection";
             description "Protect LSP from both link and node faults";
             uses apply-advanced;
             choice constraint-choice {
               case case_1 {
                 container inherit-lsp {
                   description "Inherit bypass properties from Primary LSPs";
                   leaf constraints {
                     description "Inherit bypass constraints from primary LSP";
                     type empty;
                   }
                 }
               }
               case case_2 {
                 container bypass-constraints {
                   description "Explicitly defined constraints for bypass LSPs";
                   uses apply-advanced;
                   leaf hop-limit {
                     description "Maximum allowed router hops";
                     type union {
                       type string {
                         pattern "<.*>|$.*";
                       }
                       type int32 {
                         range "0 .. 255";
                       }
                     }
                   }
                   choice include_any_or_no_include_any {
                     case case_1 {
                       leaf no-include-any {
                         description "Disable include-any checking";
                         type empty;
                       }
                     }
                     case case_2 {
                       leaf-list include-any {
                         ordered-by user;
                         description "Groups, one or more of which must be present";
                         type string;
                       }
                     }
                   }
                   choice include_all_or_no_include_all {
                     case case_1 {
                       leaf no-include-all {
                         description "Disable include-all checking";
                         type empty;
                       }
                     }
                     case case_2 {
                       leaf-list include-all {
                         ordered-by user;
                         description "Groups, all of which must be present";
                         type string;
                       }
                     }
                   }
                   choice exclude_or_no_exclude {
                     case case_1 {
                       leaf no-exclude {
                         description "Disable exclude checking";
                         type empty;
                       }
                     }
                     case case_2 {
                       leaf-list exclude {
                         ordered-by user;
                         description "Groups, all of which must be absent";
                         type string;
                       }
                     }
                   }
                 }
               }
             }
           }
         }
       }
       leaf inter-domain {
         description "Inter-domain LSP";
         type empty;
       }
       leaf adaptive {
         description "Have the LSP smoothly cut over to new routes";
         type empty;
       }
       container in-place-lsp-bandwidth-update {
         presence "enable in-place-lsp-bandwidth-update";
         description "Update LSP in-place re-using the same LSP identifier";
       }
       container fast-reroute {
         presence "enable fast-reroute";
         description "Fast reroute";
         uses apply-advanced;
         leaf hop-limit {
           description "Maximum allowed router hops";
           type union {
             type string {
               pattern "<.*>|$.*";
             }
             type int32 {
               range "0 .. 255";
             }
           }
         }
         choice bw-attribute {
           case case_1 {
             leaf bandwidth {
               description "Bandwidth to reserve (bps)";
               type string;
             }
           }
           case case_2 {
             leaf bandwidth-percent {
               description "Percentage of main path bandwidth to reserve";
               type union {
                 type string {
                   pattern "<.*>|$.*";
                 }
                 type int32 {
                   range "1 .. 100";
                 }
               }
             }
           }
         }
         choice include_any_or_no_include_any {
           case case_1 {
             leaf no-include-any {
               description "Disable include-any checking";
               type empty;
             }
           }
           case case_2 {
             leaf-list include-any {
               ordered-by user;
               description "Groups, one or more of which must be present";
               type string;
             }
           }
         }
         choice include_all_or_no_include_all {
           case case_1 {
             leaf no-include-all {
               description "Disable include-all checking";
               type empty;
             }
           }
           case case_2 {
             leaf-list include-all {
               ordered-by user;
               description "Groups, all of which must be present";
               type string;
             }
           }
         }
         choice exclude_or_no_exclude {
           case case_1 {
             leaf no-exclude {
               description "Disable exclude checking";
               type empty;
             }
           }
           case case_2 {
             leaf-list exclude {
               ordered-by user;
               description "Groups, all of which must be absent";
               type string;
             }
           }
         }
       }
       container p2mp {
         presence "enable p2mp";
         description "Point-to-multipoint label-switched path";
         leaf path_name {
           description "Name of point-to-multipoint LSP";
           type string {
           }
         }
       }
       container auto-bandwidth {
         presence "enable auto-bandwidth";
         description "Do auto bandwidth allocation for this LSP";
         uses apply-advanced;
         leaf adjust-interval {
           description "Time to adjust LSP bandwidth";
           default "86400";
           units "seconds";
           type union {
             type string {
               pattern "<.*>|$.*";
             }
             type uint32 {
               range "300 .. 315360000";
             }
           }
         }
         leaf adjust-threshold {
           description "Percentage change in average LSP utilization to trigger auto-adjustment";
           default "0";
           units "percent";
           type union {
             type string {
               pattern "<.*>|$.*";
             }
             type uint32 {
               range "0 .. 50";
             }
           }
         }
         leaf adjust-threshold-absolute {
           description "Change in average LSP utilization to trigger auto-adjustment";
           default "0";
           units "bps";
           type string;
         }
         leaf adjust-threshold-activate-bandwidth {
           description "Adjusts signaled bw if greater than this value";
           units "bps";
           type string;
         }
         leaf minimum-bandwidth {
           description "Minimum LSP bandwidth";
           units "bps";
           type string;
         }
         leaf maximum-bandwidth {
           description "Maximum LSP bandwidth";
           units "bps";
           type string;
         }
         leaf minimum-bandwidth-adjust-interval {
           description "Duration for which minimum bandwidth will be frozen";
           units "seconds";
           type union {
             type string {
               pattern "<.*>|$.*";
             }
             type uint32 {
               range "300 .. 31536000";
             }
           }
         }
         leaf minimum-bandwidth-adjust-threshold-change {
           description "Change in max average bandwidth to freeze min bandwidth";
           units "percent";
           type union {
             type string {
               pattern "<.*>|$.*";
             }
             type uint32 {
               range "0 .. 100";
             }
           }
         }
         leaf minimum-bandwidth-adjust-threshold-value {
           description "Freeze min bandwidth if max average bandwidth falls below this bw";
           status deprecated;
           units "bps";
           type string;
         }
         leaf monitor-bandwidth {
           description "Monitor LSP bandwidth without adjustments";
           type empty;
         }
         leaf adjust-threshold-overflow-limit {
           description "Number of consecutive overflow samples to trigger auto-adjustment";
           type union {
             type string {
               pattern "<.*>|$.*";
             }
             type uint32 {
               range "1 .. 65535";
             }
           }
         }
         leaf adjust-threshold-underflow-limit {
           description "Number of consecutive underflow samples to trigger auto-adjustment";
           type union {
             type string {
               pattern "<.*>|$.*";
             }
             type uint32 {
               range "1 .. 65535";
             }
           }
         }
         leaf resignal-minimum-bandwidth {
           description "Resignal the LSP using minimum-bandwidth";
           type empty;
         }
         leaf sync-active-path-bandwidth {
           description "Signal standby path with bandwidth obtained from active path";
           type empty;
         }
       }
       container optimize-on-change {
         description "Specify additional re-optimization triggers for this LSP";
         uses apply-advanced;
         leaf link-congestion {
           description "Optimize when a link becomes congested";
           type empty;
         }
       }
       container deselect-on-bandwidth-failure {
         presence "enable deselect-on-bandwidth-failure";
         description "Deselect active path if it cannot meet the bandwidth constraint";
         uses apply-advanced;
         leaf tear-lsp {
           description "Bring down active path when all paths fail to reserve required bandwidth";
           type empty;
         }
       }
       container track-igp-metric {
         description "Track IGP metric for LSP install prefixes";
         uses apply-advanced;
         leaf install-v4-prefixes {
           description "Track IGP metric for IPV4 prefixes";
           type empty;
         }
         leaf install-v6-prefixes {
           description "Track IGP metric for IPV6 prefixes";
           type empty;
         }
       }
       container associate-lsp {
         description "Associate the LSP for OAM";
         uses apply-advanced;
         leaf lsp-name {
           description "Name of assocation LSP";
           type string {
           }
           mandatory true;
         }
         leaf from {
           description "Address of ingress router of associated LSP";
           type jt:ipv4addr;
         }
       }
       list primary {
         key name;
         ordered-by user;
         description "Preferred path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf top-credibility-only-cspf {
           description "Compute paths only using highest credibility links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             type union {
               type string {
                 pattern "<.*>|$.*";
               }
               type uint32 {
                 range "1 .. 4094";
               }
             }
           }
         }
         container optimize-on-change {
           description "Specify additional re-optimization triggers for this path";
           uses apply-advanced;
           leaf link-congestion {
             description "Optimize when a link becomes congested";
             type empty;
           }
         }
       }
       list secondary {
         key name;
         ordered-by user;
         description "Backup path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf top-credibility-only-cspf {
           description "Compute paths only using highest credibility links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             type union {
               type string {
                 pattern "<.*>|$.*";
               }
               type uint32 {
                 range "1 .. 4094";
               }
             }
           }
         }
         container optimize-on-change {
           description "Specify additional re-optimization triggers for this path";
           uses apply-advanced;
           leaf link-congestion {
             description "Optimize when a link becomes congested";
             type empty;
           }
         }
         container non-active-hold-priority {
           description "Non-active hold priority";
           leaf non-active-hold-prio-value {
             description "Non-active hold priority value";
             type union {
               type string {
                 pattern "<.*>|$.*";
               }
               type uint32 {
                 range "0 .. 7";
               }
             }
           }
         }
       }
       container policing {
         description "Traffic policing for this LSP";
         leaf no-auto-policing {
           description "Turn off automatic policing for this LSP";
           type empty;
         }
       }
       container lsp-external-controller {
         description "External path computing entity";
         uses apply-advanced;
         leaf ctrler_name {
           description "Name of the external path computing entity";
           type string {
           }
           mandatory true;
         }
         leaf te-metric-bound {
           description "Maximum metric value, a path can have, for the metric-type TE";
           type union {
             type string {
               pattern "<.*>|$.*";
             }
             type uint32 {
               range "1 .. 4294967295";
             }
           }
         }
         leaf igp-metric-bound {
           description "Maximum metric value, a path can have, for the metric-type IGP";
           type union {
             type string {
               pattern "<.*>|$.*";
             }
             type uint32 {
               range "1 .. 4294967295";
             }
           }
         }
         leaf delay-metric-bound {
           description "Maximum metric value, a path can have, for the metric-type delay variation";
           type union {
             type string {
               pattern "<.*>|$.*";
             }
             type uint32 {
               range "1 .. 4294967295";
             }
           }
         }
         container diversity-association {
           description "Configure diversity association for LSP";
           uses apply-advanced;
           leaf-list group {
             ordered-by user;
             description "Configure diversity association group";
             type string;
             max-elements 8;
           }
           leaf shortest-path-first {
             description "Enable priority computation";
             type empty;
           }
         }
         container te-policy-association {
           description "Configure te policy association for LSP";
           uses apply-advanced;
           leaf-list group {
             ordered-by user;
             description "Configure te policy association group";
             type string;
             max-elements 8;
           }
         }
       }
       leaf associate-backup-pe-groups {
         description "Associate this LSP with backup-pe groups";
         type empty;
       }
       leaf egress-protection {
         description "Use this LSP for egress protection data transport";
         type empty;
       }
       leaf transport-class {
         description "Transport class this LSP belongs to";
         type string {
         }
       }
     }
     container deselect-on-bandwidth-failure {
       presence "enable deselect-on-bandwidth-failure";
       description "Deselect active path if it cannot meet the bandwidth constraint";
       uses apply-advanced;
       leaf tear-lsp {
         description "Bring down active path when all paths fail to reserve required bandwidth";
         type empty;
       }
     }
     container track-igp-metric {
       description "Track IGP metric for LSP install prefixes";
       uses apply-advanced;
       leaf install-v4-prefixes {
         description "Track IGP metric for IPV4 prefixes";
         type empty;
       }
       leaf install-v6-prefixes {
         description "Track IGP metric for IPV6 prefixes";
         type empty;
       }
     }
     list container-label-switched-path {
       key name;
       ordered-by user;
       leaf name {
         description "Name of container-lsp";
         type string {
         }
       }
       uses apply-advanced;
       choice enable-disable {
         case case_1 {
           leaf disable {
             description "Disable MPLS container-label-switched path";
             type empty;
           }
         }
       }
       leaf description {
         description "Text description of label-switched path";
         type string {
           length "1 .. 80";
         }
       }
       container label-switched-path-template {
         description "Template for dynamic point-to-point LSP parameters";
         uses apply-advanced;
         choice dynamic-template {
           case case_1 {
             leaf template-name {
               description "Name of point-to-point LSP template";
               type string {
                 length "1 .. 64";
               }
             }
           }
           case case_2 {
             leaf default-template {
               description "Use default parameters";
               type empty;
             }
           }
         }
       }
       leaf to {
         description "Address of egress router";
         type jt:ipv4addr;
         mandatory true;
       }
       leaf suffix {
         description "Suffix to generate names of members of container LSP";
         type string {
           length "1 .. 64";
         }
       }
       container splitting-merging {
         description "Do splitting and merging";
         uses apply-advanced;
         leaf maximum-member-lsps {
           description "Maximum number of LSPs";
           type union {
             type string {
               pattern "<.*>|$.*";
             }
             type int32 {
               range "1 .. 64";
             }
           }
         }
         leaf minimum-member-lsps {
           description "Minimum number of LSPs";
           type union {
             type string {
               pattern "<.*>|$.*";
             }
             type int32 {
               range "1 .. 64";
             }
           }
         }
         leaf splitting-bandwidth {
           description "Maximum bandwidth threshold for splitting";
           units "bps";
           type string;
         }
         leaf merging-bandwidth {
           description "Minimum bandwidth threshold for merging";
           units "bps";
           type string;
         }
         leaf maximum-signaling-bandwidth {
           description "Maximum bandwidth for signaling during normalization";
           units "bps";
           type string;
         }
         leaf minimum-signaling-bandwidth {
           description "Minimum bandwidth for signaling during normalization";
           units "bps";
           type string;
         }
         leaf splitting-merging-threshold {
           description "Change in aggregate LSP utilization to trigger splitting or merging";
           default "10";
           units "percent";
           type union {
             type string {
               pattern "<.*>|$.*";
             }
             type uint32 {
               range "0 .. 100";
             }
           }
         }
         container normalization {
           description "Do normalization";
           uses apply-advanced;
           leaf normalize-interval {
             description "Time to normalize container LSP";
             default "86400";
             units "seconds";
             type union {
               type string {
                 pattern "<.*>|$.*";
               }
               type uint32 {
                 range "300 .. 315360000";
               }
             }
           }
           leaf failover-normalization {
             description "Do pre-mature normalization in case some LSPs go down before next normalization";
             type empty;
           }
           leaf no-incremental-normalize {
             description "Do not normalize unless all LSPs are successfully signaled";
             type empty;
           }
           leaf normalization-retry-duration {
             description "Time before retrying the container LSP normalization";
             units "seconds";
             type union {
               type string {
                 pattern "<.*>|$.*";
               }
               type uint32 {
                 range "1 .. 86400";
               }
             }
           }
           leaf normalization-retry-limits {
             description "Maximum number of times to retry container LSP normalization";
             type union {
               type string {
                 pattern "<.*>|$.*";
               }
               type uint32 {
                 range "1 .. 1000";
               }
             }
           }
           leaf no-normalize-same-members {
             description "Do not normalize when we are not splitting or merging member LSPs";
             type empty;
           }
         }
         container sampling {
           description "Sampling information";
           uses apply-advanced;
           leaf cut-off-threshold {
             description "Cut-off percentile to remove outliers from aggregate samples";
             default "0";
             type union {
               type string {
                 pattern "<.*>|$.*";
               }
               type uint32 {
                 range "0 .. 100";
               }
             }
           }
           choice sampling-mode {
             case case_1 {
               leaf use-average-aggregate {
                 description "Use average of the samples";
                 type empty;
               }
             }
             case case_2 {
               leaf use-percentile {
                 description "Use a percentile of the samples";
                 default "100";
                 type union {
                   type string {
                     pattern "<.*>|$.*";
                   }
                   type uint32 {
                     range "0 .. 100";
                   }
                 }
               }
             }
           }
         }
       }
       container lsp-external-controller {
         description "External path computing entity";
         uses apply-advanced;
         leaf ctrler_name {
           description "Name of the external path computing entity";
           type string {
           }
           mandatory true;
         }
         leaf te-metric-bound {
           description "Maximum metric value, a path can have, for the metric-type TE";
           type union {
             type string {
               pattern "<.*>|$.*";
             }
             type uint32 {
               range "1 .. 4294967295";
             }
           }
         }
         leaf igp-metric-bound {
           description "Maximum metric value, a path can have, for the metric-type IGP";
           type union {
             type string {
               pattern "<.*>|$.*";
             }
             type uint32 {
               range "1 .. 4294967295";
             }
           }
         }
         leaf delay-metric-bound {
           description "Maximum metric value, a path can have, for the metric-type delay variation";
           type union {
             type string {
               pattern "<.*>|$.*";
             }
             type uint32 {
               range "1 .. 4294967295";
             }
           }
         }
         container diversity-association {
           description "Configure diversity association for LSP";
           uses apply-advanced;
           leaf-list group {
             ordered-by user;
             description "Configure diversity association group";
             type string;
             max-elements 8;
           }
           leaf shortest-path-first {
             description "Enable priority computation";
             type empty;
           }
         }
         container te-policy-association {
           description "Configure te policy association for LSP";
           uses apply-advanced;
           leaf-list group {
             ordered-by user;
             description "Configure te policy association group";
             type string;
             max-elements 8;
           }
         }
       }
     }
     list transit-lsp-association {
       key name;
       ordered-by user;
       description "Transit label switch path assoication";
       leaf name {
         description "Name of transit assocation LSP group";
         type string {
         }
       }
       uses apply-advanced;
       leaf lsp-name-1 {
         description "Name of assocation LSP 1";
         type string {
         }
       }
       leaf from-1 {
         description "Address of associated LSP 1";
         type jt:ipv4addr;
       }
       leaf lsp-name-2 {
         description "Name of assocation LSP 2";
         type string {
         }
       }
       leaf from-2 {
         description "Address of associated LSP 2";
         type jt:ipv4addr;
       }
     }
     list exclude-hops {
       key name;
       ordered-by user;
       description "List of routers to exclude in a label-switched path";
       leaf name {
         description "Name of exclude-hops";
         type string {
         }
       }
       uses apply-advanced;
       list exclude-hop-list {
         key name;
         description "List of routers in the label-switched path";
         leaf name {
           description "Address of routers to exclude";
           type jt:ipv4addr;
         }
       }
     }
     list path {
       key name;
       ordered-by user;
       description "Route of a label-switched path";
       leaf name {
         description "Name of label-switched path";
         type string {
         }
       }
       uses apply-advanced;
       container exclude {
         presence "enable exclude";
         description "Name of the list of routers to exclude in the label-switched path";
         uses apply-advanced;
         leaf exclude-name {
           description "Name of exclude-hops";
           type string {
           }
           mandatory true;
         }
       }
       list path-list {
         key name;
         ordered-by user;
         description "List of routers in the label-switched path";
         leaf name {
           description "Address of next system in path";
           type string {
           }
         }
         leaf abstract {
           description "Next system in path is abstract";
           type empty;
         }
         choice loose_strict_none {
           case case_1 {
             leaf loose {
               description "Next hop might not be adjacent";
               type empty;
             }
           }
           case case_2 {
             leaf loose-link {
               description "Next hop link might not be adjacent";
               type empty;
             }
           }
           case case_3 {
             leaf strict {
               description "Next hop must be adjacent";
               type empty;
             }
           }
         }
       }
     }
     list constituent-list {
       key name;
       ordered-by user;
       description "MPLS constituent list for abstract hops";
       leaf name {
         description "Constituent list name";
         type string {
         }
       }
       uses apply-advanced;
       leaf-list srlg {
         ordered-by user;
         description "SRLG Name";
         type string;
         max-elements 16;
       }
       leaf-list admin-group {
         ordered-by user;
         description "Administrative groups";
         type string;
         max-elements 16;
       }
       leaf-list admin-group-extended {
         ordered-by user;
         description "Extended administrative groups";
         type string;
         max-elements 16;
       }
     }
     list abstract-hop {
       key name;
       ordered-by user;
       description "MPLS abstract hop";
       leaf name {
         description "Abstract hop name";
         type string {
         }
       }
       uses apply-advanced;
       leaf operator {
         description "Operation among constituent lists";
         type enumeration {
           enum "AND" {
             description "AND";
           }
           enum "OR" {
             description "OR";
           }
         }
         mandatory true;
       }
       list constituent-list {
         key name;
         ordered-by user;
         description "Building abstract hop using constituent lists";
         leaf name {
           description "Constituent list name";
           type string {
             length "1 .. 64";
           }
         }
         uses apply-advanced;
         choice list-type {
           case case_1 {
             leaf include-any-list {
               description "Include any";
               type empty;
             }
           }
           case case_2 {
             leaf include-all-list {
               description "Include all";
               type empty;
             }
           }
           case case_3 {
             leaf exclude-any-list {
               description "Exclude any";
               type empty;
             }
           }
           case case_4 {
             leaf exclude-all-list {
               description "Exclude all";
               type empty;
             }
           }
         }
       }
     }
     container egress-protection {
       description "Egress router protection";
       uses apply-advanced;
       list context-identifier {
         key name;
         description "Context identifier";
         leaf name {
           description "IP address";
           type jt:ipv4addr;
         }
         uses apply-advanced;
         choice context-type {
           case case_1 {
             leaf primary {
               description "Primary";
               type empty;
             }
           }
           case case_2 {
             leaf protector {
               description "Protector";
               type empty;
             }
           }
         }
         leaf metric {
           description "IGP metric";
           type union {
             type string {
               pattern "<.*>|$.*";
             }
             type uint32 {
               range "2 .. 16777215";
             }
           }
         }
         leaf advertise-mode {
           description "Advertise mode";
           type enumeration {
             enum "stub-proxy" {
               description "Proxy";
             }
             enum "stub-alias" {
               description "Alias";
             }
           }
         }
         leaf-list admin-group {
           ordered-by user;
           description "Administrative groups";
           type string;
         }
       }
       container traceoptions {
         description "Trace options for egress-protection";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "state" {
                 description "Trace state transitions";
               }
               enum "route" {
                 description "Trace route transitions";
               }
               enum "error" {
                 description "Trace error conditions";
               }
               enum "all" {
                 description "Trace everything";
               }
             }
           }
         }
       }
     }
     container label-range {
       description "MPLS labels ranges";
       uses apply-advanced;
       list lsi-label-range {
         key name;
         ordered-by user;
         description "LSI-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list dynamic-label-range {
         key name;
         ordered-by user;
         description "Dynamic-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list block-label-range {
         key name;
         ordered-by user;
         description "Block-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list srgb-label-range {
         key name;
         ordered-by user;
         description "SRGB-label-range";
         max-elements 1;
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       leaf label-limit {
         description "Limit for the number of concurrent active labels";
         type union {
           type string {
             pattern "<.*>|$.*";
           }
           type uint32 {
             range "0 .. 1048575";
           }
         }
       }
       list static-label-range {
         key name;
         ordered-by user;
         description "Static-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
     }
     choice enable-disable {
       case case_1 {
         leaf disable {
           description "Disable MPLS";
           type empty;
         }
       }
     }
     container label-history {
       presence "enable label-history";
       description "MPLS label history recording";
       uses apply-advanced;
       leaf max-entries {
         description "Limit for the number of history entry per label";
         type union {
           type string {
             pattern "<.*>|$.*";
           }
           type uint32 {
             range "1 .. 4294967295";
           }
         }
       }
     }
     container traceoptions {
       description "Trace options for MPLS";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "connection" {
               description "Trace CCC activity";
             }
             enum "connection-detail" {
               description "Trace CCC activity in detail";
             }
             enum "cspf" {
               description "Trace CSPF computation";
             }
             enum "cspf-node" {
               description "Trace nodes visited during CSPF";
             }
             enum "cspf-link" {
               description "Trace links visited during CSPF";
             }
             enum "cspf-abstract" {
               description "Trace abstract hop based CSPF details";
             }
             enum "state" {
               description "Trace state transitions";
             }
             enum "error" {
               description "Trace error conditions";
             }
             enum "lsping" {
               description "Trace LSP ping packets received";
             }
             enum "graceful-restart" {
               description "Trace graceful-restart-related events";
             }
             enum "nsr-synchronization" {
               description "Trace NSR synchronization events";
             }
             enum "nsr-synchronization-detail" {
               description "Trace NSR synchronization events in detail";
             }
             enum "static" {
               description "Trace static label-switched path";
             }
             enum "egress-protection" {
               description "Trace egress protection events";
             }
             enum "all" {
               description "Trace everything";
             }
             enum "autobw-state" {
               description "Trace autobandwidth events in mpls trace";
             }
             enum "externally-controlled-lsp" {
               description "Trace externally controlled LSP events in mpls trace";
             }
             enum "ted-import" {
               description "Trace leaking TED entries into lsdist.0 table";
             }
             enum "ted-export" {
               description "Trace leaking of entries from lsdist.0 table into TED";
             }
             enum "lsp-history" {
               description "Trace LSP history events";
             }
             enum "abstract-hop" {
               description "Trace abstract hop related events";
             }
             enum "remote-pce" {
               description "Trace cPCE events in mpls trace";
             }
           }
         }
       }
     }
     leaf ipv6-tunneling {
       description "Allow MPLS LSPs to be used for tunneling IPv6 traffic";
       type empty;
     }
     list interface {
       key name;
       ordered-by user;
       description "MPLS interface options";
       uses juniper-protocols-mpls-interface;
     }
     list static-label-switched-path {
       key name;
       ordered-by user;
       description "Static label-switched path";
       leaf name {
         description "Name of path";
         type string {
           length "1 .. 64";
         }
       }
       uses apply-advanced;
       choice lsp-type {
         case case_1 {
           container bypass {
             description "Bypass ingress label-switched path";
             uses apply-advanced;
             leaf bandwidth {
               description "Bandwidth to reserve";
               units "bps";
               type string;
             }
             leaf description {
               description "Text description of label-switched path";
               type string {
                 length "1 .. 80";
               }
             }
             leaf next-hop {
               description "IPv4 or IPv6 address or interface of next-hop router";
               type union {
                 type jt:ipaddr-or-interface;
                 type string {
                   pattern "<.*>|$.*";
                 }
               }
             }
             leaf next-table {
               description "Next-table for lookup";
               type string;
             }
             leaf push {
               description "Label to push";
               type union {
                 type string {
                   pattern "<.*>|$.*";
                 }
                 type uint32 {
                   range "0 .. 1048575";
                 }
               }
             }
             leaf to {
               description "Address of egress router";
               type jt:ipaddr;
               mandatory true;
             }
           }
         }
         case case_2 {
           list transit {
             key name;
             ordered-by user;
             description "Transit label-switched path";
             leaf name {
               description "Incoming label value";
               type union {
                 type string {
                   pattern "<.*>|$.*";
                 }
                 type uint32 {
                   range "16 .. 1048575";
                 }
               }
             }
             uses apply-advanced;
             leaf bandwidth {
               description "Bandwidth to reserve";
               units "bps";
               type string;
             }
             leaf description {
               description "Text description of label-switched path";
               type string {
                 length "1 .. 80";
               }
             }
             container link-protection {
               description "Bypass link protection";
               leaf bypass-name {
                 description "Bypass label-switched path name";
                 type string {
                   length "1 .. 64";
                 }
                 mandatory true;
               }
             }
             leaf next-hop {
               description "IPv4 or IPv6 address or interface of next-hop router";
               type union {
                 type jt:ipaddr-or-interface;
                 type string {
                   pattern "<.*>|$.*";
                 }
               }
               mandatory true;
             }
             leaf member-interface {
               description "AE member interface name";
               type union {
                 type jt:interface-unit;
                 type string {
                   pattern "<.*>|$.*";
                 }
               }
             }
             container node-protection {
               description "Bypass node protection";
               leaf bypass-name {
                 description "Bypass label-switched path name";
                 type string {
                   length "1 .. 64";
                 }
                 mandatory true;
               }
               leaf next-next-label {
                 description "Label expected by next-next-hop";
                 type union {
                   type string {
                     pattern "<.*>|$.*";
                   }
                   type uint32 {
                     range "0 .. 1048575";
                   }
                 }
               }
             }
             choice label-action {
               case case_1 {
                 leaf swap {
                   description "Swap top label with this label";
                   type union {
                     type string {
                       pattern "<.*>|$.*";
                     }
                     type uint32 {
                       range "0 .. 1048575";
                     }
                   }
                 }
               }
               case case_2 {
                 leaf pop {
                   description "Pop the top label";
                   type empty;
                 }
               }
               case case_3 {
                 leaf stitch {
                   description "Swap top label with the resolved LSP";
                   type empty;
                 }
               }
             }
           }
         }
         case case_3 {
           container ingress {
             description "Ingress LSR configuration for a static LSP";
             uses apply-advanced;
             leaf bandwidth {
               description "Bandwidth to reserve";
               units "bps";
               type string;
             }
             leaf class-of-service {
               description "Class-of-service value";
               type union {
                 type string {
                   pattern "<.*>|$.*";
                 }
                 type int32 {
                   range "0 .. 7";
                 }
               }
             }
             leaf description {
               description "Text description of label-switched path";
               type string {
                 length "1 .. 80";
               }
             }
             list install {
               key name;
               ordered-by user;
               description "Install prefix";
               leaf name {
                 description "Destination prefix";
                 type jt:ipv4prefix;
               }
               leaf active {
                 description "Install prefix into forwarding table";
                 type empty;
               }
             }
             leaf metric {
               description "Metric value";
               type union {
                 type string {
                   pattern "<.*>|$.*";
                 }
                 type uint32 {
                   range "1 .. 16777215";
                 }
               }
             }
             leaf next-hop {
               description "IPv4 address or interface of next-hop router";
               type union {
                 type jt:ipv4addr-or-interface;
                 type string {
                   pattern "<.*>|$.*";
                 }
               }
               mandatory true;
             }
             container link-protection {
               description "Bypass link protection";
               leaf bypass-name {
                 description "Bypass label-switched path name";
                 type string {
                   length "1 .. 64";
                 }
                 mandatory true;
               }
             }
             container node-protection {
               description "Bypass node protection";
               leaf bypass-name {
                 description "Bypass label-switched path name";
                 type string {
                   length "1 .. 64";
                 }
                 mandatory true;
               }
               leaf next-next-label {
                 description "Label expected by next-next-hop";
                 type union {
                   type string {
                     pattern "<.*>|$.*";
                   }
                   type uint32 {
                     range "0 .. 1048575";
                   }
                 }
               }
             }
             leaf no-install-to-address {
               description "Don't install host route 'to' address into routing tables";
               type empty;
             }
             container policing {
               description "Traffic policing for this LSP";
               leaf filter {
                 description "Name of filter to use for policing LSP traffic";
                 type string {
                 }
               }
               leaf no-auto-policing {
                 description "Turn off automatic policing for this LSP";
                 type empty;
               }
             }
             leaf preference {
               description "Preference value";
               type union {
                 type uint32;
                 type string {
                   pattern "<.*>|$.*";
                 }
               }
             }
             leaf to {
               description "Address of egress router";
               type jt:ipv4addr;
               mandatory true;
             }
             leaf push {
               description "Label to push";
               type union {
                 type string {
                   pattern "<.*>|$.*";
                 }
                 type uint32 {
                   range "0 .. 1048575";
                 }
               }
             }
             leaf entropy-label {
               description "Enable entropy label";
               type empty;
             }
           }
         }
         case case_4 {
         }
       }
     }
   }
   grouping bandwidth-type {
     uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping juniper-protocols-mpls-interface {
     leaf name {
       description "Interface name";
       type union {
         type jt:interface-name;
         type string {
           pattern "<.*>|$.*";
         }
       }
     }
     uses apply-advanced;
     choice enable-disable {
       case case_1 {
         leaf disable {
           description "Disable MPLS on this interface";
           type empty;
         }
       }
     }
     leaf-list srlg {
       ordered-by user;
       description "SRLG Name";
       type string;
       max-elements 64;
     }
     leaf always-mark-connection-protection-tlv {
       description "Mark connection protection tlv on this interface";
       type empty;
     }
     leaf switch-away-lsps {
       description "Switch away protected LSPs to their bypass LSPs";
       type empty;
     }
     leaf-list admin-group {
       ordered-by user;
       description "Administrative groups";
       type string;
     }
     leaf-list admin-group-extended {
       ordered-by user;
       description "Extended administrative groups";
       type string;
     }
     container static {
       description "Static label-switch path related configurations";
       uses apply-advanced;
       leaf protection-revert-time {
         description "FRR revert wait time, 0 means disable";
         units "seconds";
         type union {
           type string {
             pattern "<.*>|$.*";
           }
           type uint32 {
             range "0 .. 65535";
           }
         }
       }
     }
   }
   grouping juniper-protocols-mvrp {
     description "MVRP Configuration";
     uses apply-advanced;
     container traceoptions {
       description "Tracing options for MVRP";
       uses mrp-trace-options;
     }
     leaf join-timer {
       description "Join timer interval";
       default "200";
       units "milliseconds";
       type union {
         type string {
           pattern "<.*>|$.*";
         }
         type uint16 {
           range "100 .. 500";
         }
       }
     }
     leaf leave-timer {
       description "Leave timer interval";
       default "800";
       units "milliseconds";
       type union {
         type string {
           pattern "<.*>|$.*";
         }
         type uint16 {
           range "300 .. 1000";
         }
       }
     }
     leaf leaveall-timer {
       description "Leaveall timer interval";
       default "10";
       units "seconds";
       type union {
         type string {
           pattern "<.*>|$.*";
         }
         type uint16 {
           range "10 .. 60";
         }
       }
     }
     leaf no-dynamic-vlan {
       description "Disable dynamic VLAN creation";
       type empty;
     }
     leaf no-attribute-length-in-pdu {
       description "No attribute length while sending pdu ";
       type empty;
     }
     leaf bpdu-destination-mac-address {
       description "Destination MAC address in the MVRP BPDUs";
       type enumeration {
         enum "provider-bridge-group" {
           description "802.1ad provider bridge group address";
         }
       }
     }
     list interface {
       key name;
       ordered-by user;
       description "Configure interface options";
       leaf name {
         description "Interface name";
         type union {
           type jt:interface-device;
           type string {
             pattern "<.*>|$.*";
           }
         }
       }
       uses apply-advanced;
       leaf join-timer {
         description "Join timer interval";
         units "milliseconds";
         type union {
           type string {
             pattern "<.*>|$.*";
           }
           type uint16 {
             range "100 .. 500";
           }
         }
       }
       leaf leave-timer {
         description "Leave timer interval";
         units "milliseconds";
         type union {
           type string {
             pattern "<.*>|$.*";
           }
           type uint16 {
             range "300 .. 1000";
           }
         }
       }
       leaf leaveall-timer {
         description "Leaveall timer interval";
         units "seconds";
         type union {
           type string {
             pattern "<.*>|$.*";
           }
           type uint16 {
             range "10 .. 60";
           }
         }
       }
       leaf point-to-point {
         description "Port is point to point";
         type empty;
       }
       leaf registration {
         description "Registration mode";
         default "normal";
         type enumeration {
           enum "normal" {
             description "Normal registration mode";
           }
           enum "restricted" {
             description "Restricted registration mode";
           }
           enum "forbidden" {
             description "Forbidden registration mode";
           }
         }
       }
     }
   }
   grouping juniper-protocols-ospf {
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         type string;
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       container microloop-avoidance {
         description "Configure microloop avoidance mechanism";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
       container multipath {
         description "Configure multipath options";
         uses apply-advanced;
         container weighted {
           description "Weighted multipath options";
           uses apply-advanced;
           leaf one-hop {
             description "Enable load balancing on onehop multipath based on interface bandwidth";
             type empty;
           }
         }
       }
     }
     container backup-spf-options {
       description "Configure options for backup SPF";
       uses apply-advanced;
       container remote-backup-calculation {
         presence "enable remote-backup-calculation";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         description "Calculate post-convergence backup paths";
         uses apply-advanced;
         leaf maximum-labels {
           description "Maximum number of labels installed for post-convergence paths";
           type union {
             type string {
               pattern "<.*>|$.*";
             }
             type uint32 {
               range "2 .. 8";
             }
           }
         }
       }
       leaf use-source-packet-routing {
         description "Use spring backup paths for inet.0 routes";
         type empty;
       }
       leaf disable {
         description "Do not run backup SPF";
         type empty;
       }
       leaf no-install {
         description "Do not install backup nexthops into the RIB";
         type empty;
       }
       leaf downstream-paths-only {
         description "Use only downstream backup paths";
         type empty;
       }
       container per-prefix-calculation {
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         type empty;
       }
     }
     container source-packet-routing {
       presence "enable source-packet-routing";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         description "Set the SRGB global block in SPRING";
         leaf start-label {
           description "Start range for SRGB label block";
           type union {
             type string {
               pattern "<.*>|$.*";
             }
             type uint32 {
               range "16 .. 1048575";
             }
           }
           //mandatory true;
         }
         leaf index-range {
           description "Index to the SRGB start label block";
           type union {
             type string {
               pattern "<.*>|$.*";
             }
             type uint32 {
               range "32 .. 1048559";
             }
           }
           //mandatory true;
         }
       }
       leaf mapping-server {
         description "Mapping server name";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
       leaf strict-asla-based-flex-algorithm {
         description "Flex-Algorithm to ignore links not having ASLA sub-TLVs";
         type empty;
       }
       container sensor-based-stats {
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                   mandatory true;
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
       }
       list sham-link-remote {
         key name;
         ordered-by user;
         description "Configure parameters for remote sham link endpoint";
         leaf name {
           description "Remote sham link endpoint address";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf keychain {
           description "Key chain name";
           type string {
             length "1 .. 128";
           }
         }
       }
       list interface {
         key name;
         ordered-by user;
         description "Include an interface in this area";
         leaf name {
           description "Interface name";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               type jt:ipv4addr;
             }
           }
         }
         leaf secondary {
           description "Treat interface as secondary";
           type empty;
         }
         leaf own-router-lsa {
           description "Generate a separate router LSA for this interface";
           type empty;
         }
         container bandwidth-based-metrics {
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
               mandatory true;
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           type empty;
         }
         leaf no-advertise-adjacency-segment {
           description "Do not advertise an adjacency segment for this interface";
           type empty;
         }
         list neighbor {
           key name;
           ordered-by user;
           description "NBMA neighbor";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           type empty;
         }
         container post-convergence-lfa {
           presence "enable post-convergence-lfa";
           description "Protect interface using post-convergence backup path";
           uses apply-advanced;
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           description "Configure ipv4 adjacency segment";
           uses apply-advanced;
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           leaf name {
             description "Address of neighbor";
             type jt:ipaddr;
           }
           uses apply-advanced;
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               type union {
                 type string {
                   pattern "<.*>|$.*";
                 }
                 type uint32 {
                   range "1 .. 4294967295";
                 }
               }
             }
             leaf-list admin-group {
               ordered-by user;
               description "Administrative groups for this attribute-group";
               type string;
               max-elements 16;
             }
             leaf delay-metric {
               description "Delay metric for this attribute-group";
               units "microseconds";
               type union {
                 type string {
                   pattern "<.*>|$.*";
                 }
                 type uint32 {
                   range "0 .. 16777215";
                 }
               }
             }
             leaf advertise-interface-delay {
               description "Use interface specific static/dynamic delay values as applicable in ASLA Sub-TLVs";
               type empty;
             }
             container application {
               description "Standard Applications part of this attribute-group";
               uses apply-advanced;
               leaf flex-algorithm {
                 description "Set X flag in standard application bit mask";
                 type empty;
               }
             }
           }
         }
       }
       leaf no-source-packet-routing {
         description "Disable SPRING in this area";
         type empty;
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "traffic-statistics" {
               description "Trace Segment Routing Traffic Statistics";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         type string;
       }
       leaf inet3 {
         description "Name of the IPv4/v6 inet.3 routing table group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
         mandatory true;
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-protocols-ospf3 {
     list realm {
       key name;
       ordered-by user;
       description "OSPFv3 realm configuration";
       leaf name {
         description "OSPFv3 realm name";
         type enumeration {
           enum "ipv6-unicast" {
             description "IPv6 unicast realm";
           }
           enum "ipv6-multicast" {
             description "IPv6 multicast realm";
           }
           enum "ipv4-unicast" {
             description "IPv4 unicast realm";
           }
           enum "ipv4-multicast" {
             description "IPv4 multicast realm";
           }
         }
       }
       uses apply-advanced;
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           type string;
         }
         container spf-options {
           description "Configure options for SPF";
           uses apply-advanced;
           container microloop-avoidance {
             description "Configure microloop avoidance mechanism";
             uses apply-advanced;
             container post-convergence-path {
               presence "enable post-convergence-path";
               description "Temporarily install post-convergence path for routes potentially affected by microloops";
               uses apply-advanced;
               leaf delay {
                 description "Time after which temporary post-convergence paths are removed";
                 units "milliseconds";
                 type union {
                   type string {
                     pattern "<.*>|$.*";
                   }
                   type uint32 {
                     range "500 .. 60000";
                   }
                 }
               }
               leaf maximum-labels {
                 description "Maximum number of labels installed for post-convergence paths";
                 type union {
                   type string {
                     pattern "<.*>|$.*";
                   }
                   type uint32 {
                     range "2 .. 8";
                   }
                 }
               }
             }
           }
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
           container multipath {
             description "Configure multipath options";
             uses apply-advanced;
             container weighted {
               description "Weighted multipath options";
               uses apply-advanced;
               leaf one-hop {
                 description "Enable load balancing on onehop multipath based on interface bandwidth";
                 type empty;
               }
             }
           }
         }
         container backup-spf-options {
           description "Configure options for backup SPF";
           uses apply-advanced;
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 8";
                 }
               }
             }
             leaf maximum-backup-paths {
               description "Maximum number of equal-cost post-convergence paths installed";
               type union {
                 type string {
                   pattern "<.*>|$.*";
                 }
                 type uint32 {
                   range "1 .. 8";
                 }
               }
             }
           }
           leaf use-source-packet-routing {
             description "Use spring backup paths for inet.0 routes";
             type empty;
           }
           leaf disable {
             description "Do not run backup SPF";
             type empty;
           }
           leaf no-install {
             description "Do not install backup nexthops into the RIB";
             type empty;
           }
           leaf downstream-paths-only {
             description "Use only downstream backup paths";
             type empty;
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
         }
         leaf prefix-export-limit {
           description "Maximum number of prefixes that can be exported";
           type union {
             type string {
               pattern "<.*>|$.*";
             }
             type uint32 {
               range "0 .. 4294967295";
             }
           }
         }
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       container traffic-engineering {
         presence "enable traffic-engineering";
         description "Configure traffic engineering attributes";
         uses apply-advanced;
         leaf no-topology {
           description "Disable dissemination of TE link-state topology information";
           type empty;
         }
         leaf multicast-rpf-routes {
           description "Install routes for multicast RPF checks into inet.2";
           type empty;
         }
         leaf l3-unicast-topology {
           description "Download IGP topology into TED";
           type empty;
         }
         container ignore-lsp-metrics {
           presence "enable ignore-lsp-metrics";
           description "Ignore label-switched path metrics when doing shortcuts";
           uses apply-advanced;
           leaf unconfigured-only {
             description "Ignore lsp metrics for unconfigured only";
             type empty;
           }
         }
         container shortcuts {
           presence "enable shortcuts";
           description "Use label-switched paths as next hops, if possible";
           uses apply-advanced;
           leaf ignore-lsp-metrics {
             description "Ignore label-switched path metrics when doing shortcuts";
             status deprecated;
             type empty;
           }
           leaf lsp-metric-into-summary {
             description "Advertise LSP metric into summary LSAs";
             type empty;
           }
           list family {
             key name;
             ordered-by user;
             description "Address family specific traffic-engineering attributes";
             leaf name {
               type enumeration {
                 enum "inet" {
                   description "IPv4 family";
                 }
                 enum "inet-mpls" {
                   description "IPv4-MPLS family";
                 }
               }
             }
             uses apply-advanced;
           }
         }
         leaf advertise-unnumbered-interfaces {
           description "Advertise unnumbered interfaces";
           type empty;
         }
         leaf credibility-protocol-preference {
           description "TED protocol credibility follows protocol preference";
           type empty;
         }
         container advertisement {
           description "Advertise TE parameters even if RSVP is not turned on";
           uses apply-advanced;
           leaf always {
             description "Advertise TE parameters in TE LSAs";
             type empty;
           }
         }
         container tunnel-source-protocol {
           description "Protocols from which to pick label-switched paths";
           uses apply-advanced;
           container rsvp {
             presence "enable rsvp";
             description "Pick label-switched paths from rsvp";
             uses apply-advanced;
             leaf preference {
               description "Preference for label-switched paths from this protocol";
               type union {
                 type string {
                   pattern "<.*>|$.*";
                 }
                 type uint32 {
                   range "1 .. 255";
                 }
               }
             }
           }
           container spring-te {
             presence "enable spring-te";
             description "Pick label-switched paths from spring-te";
             uses apply-advanced;
             leaf preference {
               description "Preference for label-switched paths from this protocol";
               type union {
                 type string {
                   pattern "<.*>|$.*";
                 }
                 type uint32 {
                   range "1 .. 255";
                 }
               }
             }
           }
         }
       }
       container source-packet-routing {
         presence "enable source-packet-routing";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 199999";
               }
             }
           }
           leaf index-range {
             description "Set range of node segment indices allowed";
             type union {
               type string {
                 pattern "<.*>|$.*";
               }
               type uint32 {
                 range "32 .. 16385";
               }
             }
           }
         }
         container srgb {
           description "Set the SRGB global block in SPRING";
           leaf start-label {
             description "Start range for SRGB label block";
             type union {
               type string {
                 pattern "<.*>|$.*";
               }
               type uint32 {
                 range "16 .. 1048575";
               }
             }
             //mandatory true;
           }
           leaf index-range {
             description "Index to the SRGB start label block";
             type union {
               type string {
                 pattern "<.*>|$.*";
               }
               type uint32 {
                 range "32 .. 1048559";
               }
             }
             //mandatory true;
           }
         }
         leaf mapping-server {
           description "Mapping server name";
           type string;
         }
         leaf install-prefix-sid-for-best-route {
           description "For best route install a exact prefix sid route";
           type empty;
         }
         leaf ldp-stitching {
           description "Enable SR to LDP stitching";
           type empty;
         }
         leaf-list flex-algorithm {
           description "Flex-algorithms we would like to participate in";
           type union {
             type string {
               pattern "<.*>|$.*";
             }
             type uint32 {
               range "128 .. 255";
             }
           }
           max-elements 16;
         }
         leaf strict-asla-based-flex-algorithm {
           description "Flex-Algorithm to ignore links not having ASLA sub-TLVs";
           type empty;
         }
         container sensor-based-stats {
           description "Configure sensor based stats in SPRING";
           uses apply-advanced;
           container per-interface-per-member-link {
             description "Configure sensor based stats per nexthop";
             leaf ingress {
               description "Enable sensor based stats on ingress interface";
               type empty;
             }
             leaf egress {
               description "Enable sensor based stats on egress interface";
               type empty;
             }
           }
           container per-sid {
             description "Configure sensor based stats per spring route";
             leaf ingress {
               description "Enable sensor based stats for per-sid ingress accounting";
               type empty;
             }
             leaf egress {
               description "Enable sensor based stats for IP-MPLS egress accounting";
               type empty;
             }
           }
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                     mandatory true;
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
         }
         list sham-link-remote {
           key name;
           ordered-by user;
           description "Configure parameters for remote sham link endpoint";
           leaf name {
             description "Remote sham link endpoint address";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf keychain {
             description "Key chain name";
             type string {
               length "1 .. 128";
             }
           }
         }
         list interface {
           key name;
           ordered-by user;
           description "Include an interface in this area";
           leaf name {
             description "Interface name";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 type jt:ipv4addr;
               }
             }
           }
           leaf secondary {
             description "Treat interface as secondary";
             type empty;
           }
           leaf own-router-lsa {
             description "Generate a separate router LSA for this interface";
             type empty;
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
           leaf metric {
             description "Interface metric";
             type union {
               type string {
                 pattern "<.*>|$.*";
               }
               type uint16 {
                 range "1 .. 65535";
               }
             }
           }
           leaf priority {
             description "Designated router priority";
             type union {
               type string {
                 pattern "<.*>|$.*";
               }
               type uint32 {
                 range "0 .. 255";
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             leaf full-neighbors-only {
               description "Setup BFD sessions only to Full neighbors";
               type empty;
             }
             leaf holddown-interval {
               description "Time to hold the session-UP notification to the client";
               units "milliseconds";
               type union {
                 type string {
                   pattern "<.*>|$.*";
                 }
                 type uint32 {
                   range "0 .. 255000";
                 }
               }
             }
           }
           leaf dynamic-neighbors {
             description "Learn neighbors dynamically on a p2mp interface";
             type empty;
           }
           leaf no-advertise-adjacency-segment {
             description "Do not advertise an adjacency segment for this interface";
             type empty;
           }
           list neighbor {
             key name;
             ordered-by user;
             description "NBMA neighbor";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
           leaf strict-bfd {
             description "Enable strict bfd over this interface";
             type empty;
           }
           container post-convergence-lfa {
             presence "enable post-convergence-lfa";
             description "Protect interface using post-convergence backup path";
             uses apply-advanced;
           }
           leaf te-metric {
             description "Traffic engineering metric";
             type union {
               type string {
                 pattern "<.*>|$.*";
               }
               type uint32 {
                 range "1 .. 4294967295";
               }
             }
           }
           container ldp-synchronization {
             description "Advertise maximum metric until LDP is operational";
             presence "enable ldp-synchronization";
             uses ldp-sync-obj;
           }
           container ipv4-adjacency-segment {
             description "Configure ipv4 adjacency segment";
             uses apply-advanced;
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list lan-neighbor {
             key name;
             ordered-by user;
             description "Configuration specific to a LAN neighbor";
             leaf name {
               description "Address of neighbor";
               type jt:ipaddr;
             }
             uses apply-advanced;
             container ipv4-adjacency-segment {
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
           }
           leaf delay-metric {
             description "Delay metric";
             units "microseconds";
             type union {
               type string {
                 pattern "<.*>|$.*";
               }
               type uint32 {
                 range "0 .. 16777215";
               }
             }
           }
           container delay-measurement {
             presence "enable delay-measurement";
             description "Enable delay measurement";
             uses apply-advanced;
             leaf probe-interval {
               description "Probe interval";
               units "seconds";
               type union {
                 type string {
                   pattern "<.*>|$.*";
                 }
                 type uint32 {
                   range "1 .. 255";
                 }
               }
             }
             leaf probe-count {
               description "Probe count";
               type union {
                 type string {
                   pattern "<.*>|$.*";
                 }
                 type uint32 {
                   range "1 .. 15";
                 }
               }
             }
             container advertisement {
               description "Delay advertisement";
               uses apply-advanced;
               container periodic {
                 description "Periodic advertisement parameters";
                 uses apply-advanced;
                 leaf threshold {
                   description "Threshold";
                   units "percentage";
                   type union {
                     type string {
                       pattern "<.*>|$.*";
                     }
                     type uint32 {
                       range "0 .. 100";
                     }
                   }
                 }
                 leaf interval {
                   description "Interval";
                   units "seconds";
                   type union {
                     type string {
                       pattern "<.*>|$.*";
                     }
                     type uint32 {
                       range "30 .. 3600";
                     }
                   }
                 }
               }
               container accelerated {
                 presence "enable accelerated";
                 description "Accelerated advertisement parameters";
                 uses apply-advanced;
                 leaf threshold {
                   description "Threshold";
                   units "percentage";
                   type union {
                     type string {
                       pattern "<.*>|$.*";
                     }
                     type uint32 {
                       range "0 .. 100";
                     }
                   }
                 }
               }
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf te-metric {
                 description "Traffic engineering metric for this attribute group";
                 type union {
                   type string {
                     pattern "<.*>|$.*";
                   }
                   type uint32 {
                     range "1 .. 4294967295";
                   }
                 }
               }
               leaf-list admin-group {
                 ordered-by user;
                 description "Administrative groups for this attribute-group";
                 type string;
                 max-elements 16;
               }
               leaf delay-metric {
                 description "Delay metric for this attribute-group";
                 units "microseconds";
                 type union {
                   type string {
                     pattern "<.*>|$.*";
                   }
                   type uint32 {
                     range "0 .. 16777215";
                   }
                 }
               }
               leaf advertise-interface-delay {
                 description "Use interface specific static/dynamic delay values as applicable in ASLA Sub-TLVs";
                 type empty;
               }
               container application {
                 description "Standard Applications part of this attribute-group";
                 uses apply-advanced;
                 leaf flex-algorithm {
                   description "Set X flag in standard application bit mask";
                   type empty;
                 }
               }
             }
           }
         }
         leaf no-source-packet-routing {
           description "Disable SPRING in this area";
           type empty;
         }
       }
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "traffic-statistics" {
                 description "Trace Segment Routing Traffic Statistics";
               }
               enum "backup-spf" {
                 description "Trace backup SPF (LFA) specific events";
               }
               enum "source-packet-routing" {
                 description "Trace source packet routing (SPRING) events";
               }
               enum "post-convergence-lfa" {
                 description "Trace post-convergence-lfa related events";
               }
               enum "flex-algorithm" {
                 description "Trace flex-algorithm related events";
               }
               enum "rmopd" {
                 description "Trace rmopd interactions";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           type string;
         }
         leaf inet3 {
           description "Name of the IPv4/v6 inet.3 routing table group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 3600";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
           mandatory true;
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         type union {
           type string {
             pattern "<.*>|$.*";
           }
           type uint32 {
             range "50 .. 8000";
           }
         }
       }
       leaf no-rfc-1583 {
         description "Disable RFC1583 compatibility";
         type empty;
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
     }
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         type string;
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       container microloop-avoidance {
         description "Configure microloop avoidance mechanism";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
       container multipath {
         description "Configure multipath options";
         uses apply-advanced;
         container weighted {
           description "Weighted multipath options";
           uses apply-advanced;
           leaf one-hop {
             description "Enable load balancing on onehop multipath based on interface bandwidth";
             type empty;
           }
         }
       }
     }
     container source-packet-routing {
       presence "enable source-packet-routing";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         description "Set the SRGB global block in SPRING";
         leaf start-label {
           description "Start range for SRGB label block";
           type union {
             type string {
               pattern "<.*>|$.*";
             }
             type uint32 {
               range "16 .. 1048575";
             }
           }
           //mandatory true;
         }
         leaf index-range {
           description "Index to the SRGB start label block";
           type union {
             type string {
               pattern "<.*>|$.*";
             }
             type uint32 {
               range "32 .. 1048559";
             }
           }
           //mandatory true;
         }
       }
       leaf mapping-server {
         description "Mapping server name";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
       leaf strict-asla-based-flex-algorithm {
         description "Flex-Algorithm to ignore links not having ASLA sub-TLVs";
         type empty;
       }
       container sensor-based-stats {
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                   mandatory true;
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
       }
       list sham-link-remote {
         key name;
         ordered-by user;
         description "Configure parameters for remote sham link endpoint";
         leaf name {
           description "Remote sham link endpoint address";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf keychain {
           description "Key chain name";
           type string {
             length "1 .. 128";
           }
         }
       }
       list interface {
         key name;
         ordered-by user;
         description "Include an interface in this area";
         leaf name {
           description "Interface name";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               type jt:ipv4addr;
             }
           }
         }
         leaf secondary {
           description "Treat interface as secondary";
           type empty;
         }
         leaf own-router-lsa {
           description "Generate a separate router LSA for this interface";
           type empty;
         }
         container bandwidth-based-metrics {
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
               mandatory true;
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           type empty;
         }
         leaf no-advertise-adjacency-segment {
           description "Do not advertise an adjacency segment for this interface";
           type empty;
         }
         list neighbor {
           key name;
           ordered-by user;
           description "NBMA neighbor";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           type empty;
         }
         container post-convergence-lfa {
           presence "enable post-convergence-lfa";
           description "Protect interface using post-convergence backup path";
           uses apply-advanced;
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           description "Configure ipv4 adjacency segment";
           uses apply-advanced;
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           leaf name {
             description "Address of neighbor";
             type jt:ipaddr;
           }
           uses apply-advanced;
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               type union {
                 type string {
                   pattern "<.*>|$.*";
                 }
                 type uint32 {
                   range "1 .. 4294967295";
                 }
               }
             }
             leaf-list admin-group {
               ordered-by user;
               description "Administrative groups for this attribute-group";
               type string;
               max-elements 16;
             }
             leaf delay-metric {
               description "Delay metric for this attribute-group";
               units "microseconds";
               type union {
                 type string {
                   pattern "<.*>|$.*";
                 }
                 type uint32 {
                   range "0 .. 16777215";
                 }
               }
             }
             leaf advertise-interface-delay {
               description "Use interface specific static/dynamic delay values as applicable in ASLA Sub-TLVs";
               type empty;
             }
             container application {
               description "Standard Applications part of this attribute-group";
               uses apply-advanced;
               leaf flex-algorithm {
                 description "Set X flag in standard application bit mask";
                 type empty;
               }
             }
           }
         }
       }
       leaf no-source-packet-routing {
         description "Disable SPRING in this area";
         type empty;
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "traffic-statistics" {
               description "Trace Segment Routing Traffic Statistics";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         type string;
       }
       leaf inet3 {
         description "Name of the IPv4/v6 inet.3 routing table group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
         mandatory true;
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-protocols-router-discovery {
     uses apply-advanced;
     choice enable-disable {
       case case_1 {
         leaf disable {
           description "Disable router discovery";
           type empty;
         }
       }
     }
     container traceoptions {
       description "Trace options for router discovery";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     list interface {
       key name;
       ordered-by user;
       description "Interfaces on which to configure router discovery";
       leaf name {
         description "Interface name";
         type union {
           type jt:interface-name;
           type string {
             pattern "<.*>|$.*";
           }
         }
       }
       uses apply-advanced;
       leaf max-advertisement-interval {
         description "Maximum time before sending advertisements";
         units "seconds";
         type union {
           type string {
             pattern "<.*>|$.*";
           }
           type uint32 {
             range "4 .. 1800";
           }
         }
       }
       leaf min-advertisement-interval {
         description "Minimum time before sending advertisements";
         units "seconds";
         type union {
           type string {
             pattern "<.*>|$.*";
           }
           type uint32 {
             range "3 .. 1800";
           }
         }
       }
       leaf lifetime {
         description "How long addresses in advertisements are valid";
         units "seconds";
         type union {
           type string {
             pattern "<.*>|$.*";
           }
           type uint32 {
             range "3 .. 9000";
           }
         }
       }
     }
     list address {
       key name;
       ordered-by user;
       description "IP addresses to include in advertisements";
       leaf name {
         description "IP addresses to include in router advertisements";
         type jt:ipv4addr;
       }
       uses apply-advanced;
       leaf advertise {
         description "Advertise the IP address in advertisements";
         type empty;
       }
       leaf ignore {
         description "Do not advertise the IP address in advertisements";
         type empty;
       }
       leaf broadcast {
         description "Include IP address only in broadcast advertisements";
         type empty;
       }
       leaf multicast {
         description "Include IP address only in multicast advertisements";
         type empty;
       }
       leaf ineligible {
         description "IP address can never become a default router";
         type empty;
       }
       leaf priority {
         description "Preference of the address to become a default router";
         type union {
           type int32;
           type string {
             pattern "<.*>|$.*";
           }
         }
       }
     }
   }
   grouping juniper-routing-instance {
     description "Routing instance";
     leaf name {
       description "Routing instance name";
       type string {
       }
     }
     uses apply-advanced;
     leaf instance-type {
       description "Type of routing instance";
       type enumeration {
         enum "mac-vrf" {
           description "MAC-VRF routing instance";
         }
         enum "virtual-switch" {
           description "Virtual switch routing instance";
         }
         enum "forwarding" {
           description "Forwarding instance";
         }
         enum "no-forwarding" {
           description "Nonforwarding instance";
         }
         enum "l2vpn" {
           description "Layer 2 VPN routing instance";
         }
         enum "vpls" {
           description "VPLS routing instance";
         }
         enum "virtual-router" {
           description "Virtual routing instance";
         }
         enum "l2backhaul-vpn" {
           description "L2Backhaul/L2Wholesale routing instance";
         }
         enum "mpls-internet-multicast" {
           description "Internet Multicast over MPLS routing instance";
         }
         enum "evpn" {
           description "EVPN routing instance";
         }
         enum "mpls-forwarding" {
           description "Routing instance provides a MPLS forwarding-context";
         }
         enum "evpn-vpws" {
           description "EVPN VPWS routing instance";
         }
         enum "vrf" {
           description "Virtual routing forwarding instance";
         }
       }
     }
     container routing-options {
       description "Protocol-independent routing option configuration";
       uses juniper-routing-options;
     }
     container protocols {
       description "Routing protocol configuration";
       uses apply-advanced;
       container bfd {
         presence "enable bfd";
         uses juniper-ri-protocols-bfd;
       }
       container bgp {
         description "BGP options";
         uses juniper-protocols-bgp;
       }
       container evpn {
         description "EVPN configuration";
         presence "enable evpn";
         uses juniper-protocols-l2vpn;
       }
       container router-discovery {
         description "ICMP router discovery options";
         uses juniper-protocols-router-discovery;
       }
       container isis {
         description "IS-IS configuration";
         uses juniper-protocols-isis;
       }
       container ldp {
         description "LDP configuration";
         uses juniper-protocols-ldp;
       }
       container mpls {
         description "MPLS configuration";
         uses juniper-protocols-mpls;
       }
       container ospf {
         description "OSPF configuration";
         uses juniper-protocols-ospf;
       }
       container ospf3 {
         description "OSPF3 configuration";
         uses juniper-protocols-ospf3;
       }
       container mvrp {
         description "MVRP configuration";
         uses juniper-protocols-mvrp;
       }
     }
     container forwarding-options {
       description "Forwarding options configuration";
       uses juniper-forwarding-options;
     }
     leaf service-type {
       description "Sevice type";
       type enumeration {
         enum "vlan-bundle" {
           description "Instance service type vlan-bundle";
         }
         enum "vlan-aware" {
           description "Instance service type vlan-aware";
         }
       }
     }
     container vtep-source-interface {
       description "Source layer-3 IFL for VXLAN";
       leaf interface-name {
         type union {
           type jt:interface-name;
           type string {
             pattern "<.*>|$.*";
           }
         }
         //mandatory true;
       }
       container inet {
         presence "enable inet";
         description "IPv4 source";
         uses apply-advanced;
       }
       container inet6 {
         presence "enable inet6";
         description "IPv6 source";
         uses apply-advanced;
       }
     }
     container bridge-options {
       description "Bridge options";
       uses apply-advanced;
       container traceoptions {
         description "Bridge trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "kernel" {
                 description "Log configuration IPC messages to kernel";
               }
               enum "error" {
                 description "Log error events";
               }
               enum "warning" {
                 description "Log warning events";
               }
               enum "notice" {
                 description "Log notification events";
               }
               enum "info" {
                 description "Log informations";
               }
               enum "debugging" {
                 description "Log debug events";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
         }
       }
     }
     container bridge-domains {
       description "Bridge domain configuration";
       uses apply-advanced;
       list domain {
         key name;
         uses juniper-bridge-domains;
       }
     }
     list interface {
       key name;
       description "Interface name for this routing instance";
       leaf name {
         type string;
       }
       uses apply-advanced;
       choice mode {
         case case_1 {
           leaf any {
             description "Interface used for both unicast and multicast traffic";
             type empty;
           }
         }
         case case_2 {
           leaf unicast {
             description "Interface used for unicast traffic only";
             type empty;
           }
         }
         case case_3 {
           leaf multicast {
             description "Interface used for multicast traffic only";
             type empty;
           }
         }
       }
       leaf primary {
         description "Preferred multicast vt interface for the routing-instance";
         type empty;
       }
       leaf protect-interface {
         description "Name of protect interface";
         type union {
           type jt:interface-name;
           type string {
             pattern "<.*>|$.*";
           }
         }
       }
     }
     container route-distinguisher {
       description "Route distinguisher for this instance";
       leaf rd-type {
         description "Number in (16 bit:32 bit) or (32 bit 'L':16 bit) or (IP address:16 bit) format";
         type string {
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     leaf export-default-action {
       description "Default action for export in routing-instance";
       type enumeration {
         enum "accept" {
           description "Default action is accept";
         }
         enum "reject" {
           description "Default action is reject";
         }
       }
     }
     leaf import-default-action {
       description "Default action for import in routing-instance";
       type enumeration {
         enum "accept" {
           description "Default action is accept";
         }
         enum "reject" {
           description "Default action is reject";
         }
       }
     }
     container vrf-target {
       description "VRF target community configuration";
       uses apply-advanced;
       leaf community {
         description "Target community to use in import and export";
         type string {
         }
       }
       leaf import {
         description "Target community to use when filtering on import";
         type string {
         }
       }
       leaf export {
         description "Target community to use when marking routes on export";
         type string {
         }
       }
       leaf auto {
         description "Auto derive import and export target community from BGP AS & L2";
         type empty;
       }
     }
     leaf no-vrf-advertise {
       description "Don't advertise this instance to remote PEs";
       type empty;
     }
     container vrf-table-label {
       presence "enable vrf-table-label";
       description "Advertise a single VPN label for all routes in the VRF";
       leaf static {
         description "Specify label value to be used";
         type union {
           type string {
             pattern "<.*>|$.*";
           }
           type uint32 {
             range "16 .. 1048575";
           }
         }
       }
       leaf source-class-usage {
         description "Enable source class usage";
         type empty;
       }
     }
     choice vrf-propagate-ttl-or-no-vrf-propagate-ttl {
       case case_1 {
       }
       case case_2 {
       }
     }
   }
   grouping juniper-bridge-domains {
     description "Bridge domains";
     leaf name {
       description "Bridge domain name";
       type string {
       }
     }
     uses apply-advanced;
     leaf description {
       description "Text description of bridge domain";
       type string {
       }
     }
     choice vlan_choice {
       case case_1 {
         leaf vlan-id {
           description "IEEE 802.1q VLAN identifier for bridging domain";
           type string;
         }
       }
     }
     leaf no-local-switching {
       description "Disable local switching within CE-facing interfaces";
       type empty;
     }
     list interface {
       key name;
       ordered-by user;
       description "Interface name for this bridge domain";
       leaf name {
         type string;
       }
       uses apply-advanced;
     }
     leaf routing-interface {
       description "Routing interface name for this bridge-domain";
       type union {
         type jt:interface-unit;
         type string {
           pattern "<.*>|$.*";
         }
       }
     }
     container bridge-options {
       description "Bridge options configuration";
       uses apply-advanced;
       list interface {
         key name;
         ordered-by user;
         description "Interface name";
         leaf name {
           description "Interface name";
           type union {
             type jt:interface-name;
             type string {
               pattern "<.*>|$.*";
             }
           }
         }
         uses apply-advanced;
         list static-mac {
           key name;
           ordered-by user;
           description "Static MAC addresses assigned to this interface";
           leaf name {
             description "MAC address";
             type jt:mac-addr;
           }
           uses apply-advanced;
           list vlan-id {
             key name;
             ordered-by user;
             description "VLAN ID of learning VLAN";
             leaf name {
               description "Learning VLAN";
               type union {
                 type string {
                   pattern "<.*>|$.*";
                 }
                 type uint32 {
                   range "0 .. 4094";
                 }
               }
             }
             uses apply-advanced;
           }
         }
         leaf no-mac-learning {
           description "Disable dynamic MAC address learning";
           type empty;
         }
       }
     }
     container vxlan {
       description "VXLAN options";
       uses apply-advanced;
       leaf vni {
         description "VXLAN identifier";
         type union {
           type string {
             pattern "<.*>|$.*";
           }
           type uint32 {
             range "0 .. 16777214";
           }
         }
         mandatory true;
       }
       leaf destination-udp-port {
         description "VXLAN destination UDP port";
         default "4789";
         type union {
           type string {
             pattern "<.*>|$.*";
           }
           type uint16 {
             range "4789 .. 65535";
           }
         }
       }
       leaf mtu {
         description "Maximum transmit packet size";
         default "9216";
         type union {
           type string {
             pattern "<.*>|$.*";
           }
           type uint16 {
             range "100 .. 65535";
           }
         }
       }
     }
     container forwarding-options {
       presence "enable forwarding-options";
       description "Forwarding options configuration";
       uses apply-advanced;
       container filter {
         description "Filtering for bridge forwarding table";
         uses apply-advanced;
         leaf input {
           type string;
         }
       }
     }
   }
   grouping juniper-protocols-l2vpn {
     description "Layer 2 VPN, VPLS or EVPN configuration";
     uses apply-advanced;
     list interface {
       key name;
       description "Interface that connect this site to the VPN";
       leaf name {
         description "Interface name";
         type union {
           type jt:interface-name;
           type string {
             pattern "<.*>|$.*";
           }
         }
       }
       uses apply-advanced;
       container vpws-service-id {
         presence "enable vpws-service-id";
         description "Service-id for EVPN VPWS routing instance";
         uses apply-advanced;
         leaf local {
           description "Local EVPN VPWS service id";
           type union {
             type string {
               pattern "<.*>|$.*";
             }
             type uint32 {
               range "1 .. 16777215";
             }
           }
           mandatory true;
         }
         leaf remote {
           description "Remote EVPN VPWS service id";
           type union {
             type string {
               pattern "<.*>|$.*";
             }
             type uint32 {
               range "1 .. 16777215";
             }
           }
           mandatory true;
         }
         container source-packet-routing {
           presence "enable source-packet-routing";
           uses apply-advanced;
           container srv6 {
             description "Enable IPv6 segment routing (SRv6)";
             container locator {
               description "SRv6 locator";
               leaf loc-name {
                 description "Locator name";
                 type string;
                 mandatory true;
               }
               choice mode {
                 case case_1 {
                   leaf end-dx2-sid {
                     description "Segment routing header based end dx2 sid";
                     type jt:ipv6addr;
                   }
                 }
                 case case_2 {
                   container micro-dx2-sid {
                     presence "enable micro-dx2-sid";
                     description "Micro dx2 sid";
                     uses apply-advanced;
                     leaf micro-sid-value {
                       description "Static micro sid value 16-bit or 32-bit";
                       type union {
                         type uint32;
                         type string {
                           pattern "<.*>|$.*";
                         }
                       }
                       mandatory true;
                     }
                   }
                 }
               }
             }
           }
         }
       }
       leaf flow-label-transmit-static {
         description "Push Flow Label on PW packets sent to remote PE";
         type empty;
       }
       leaf flow-label-receive-static {
         description "Pop Flow Label from PW packets received from remote PE";
         type empty;
       }
       leaf remote-site-id {
         description "Site identifier associated with this interface";
         type union {
           type string {
             pattern "<.*>|$.*";
           }
           type uint32 {
             range "1 .. 65534";
           }
         }
       }
       leaf target-attachment-identifier {
         description "FEC 129 VPWS target attachment identifier";
         type string {
         }
       }
       leaf flow-label-transmit {
         description "Advertise capability to push Flow Label in transmit direction to remote PE";
         type empty;
       }
       leaf flow-label-receive {
         description "Advertise capability to pop Flow Label in receive direction to remote PE";
         type empty;
       }
       choice cword {
         case case_1 {
           leaf control-word {
             description "Add control word to the Layer 2 encapsulation";
             type empty;
           }
         }
         case case_2 {
           leaf no-control-word {
             description "Disables control word on the Layer 2 encapsulation";
             type empty;
           }
         }
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       leaf pseudowire-status-tlv {
         description "Send pseudowire status TLV";
         type empty;
       }
       leaf community {
         description "Community associated with this interface";
         type string;
       }
       leaf description {
         description "Text description";
         type string;
       }
     }
     leaf designated-forwarder-election-hold-time {
       description "Time to wait before electing a DF(seconds)";
       units "seconds";
       type union {
         type string {
           pattern "<.*>|$.*";
         }
         type uint32 {
           range "1 .. 1800";
         }
       }
     }
     choice df-preference-alg {
       case case_1 {
         leaf designated-forwarder-preference-least {
           description "Use least preference in DF election";
           type empty;
         }
       }
       case case_2 {
         leaf designated-forwarder-preference-highest {
           description "Use highest preference in DF election";
           type empty;
         }
       }
     }
     leaf encapsulation {
       description "Encapsulation type for EVPN";
       default "mpls";
       type enumeration {
         enum "mpls" {
           description "MPLS encapsulation";
         }
         enum "vxlan" {
           description "VXLAN encapsulation";
         }
         enum "mpls-inet6" {
           description "MPLS over IPv6 encapsulation";
         }
         enum "srv6" {
           description "SRv6 encapsulation";
         }
       }
     }
     leaf default-gateway {
       description "Default gateway mode";
       type enumeration {
         enum "advertise" {
           description "Advertise IRB MACs with default gateway community";
         }
         enum "no-gateway-community" {
           description "Advertise IRB MACs without default gateway community";
         }
         enum "do-not-advertise" {
           description "Do not advertise IRB MACs";
         }
       }
     }
     container duplicate-mac-detection {
       description "Duplicate MAC detection settings";
       uses apply-advanced;
       leaf detection-threshold {
         description "Number of moves to trigger duplicate MAC detection";
         type union {
           type string {
             pattern "<.*>|$.*";
           }
           type uint32 {
             range "2 .. 20";
           }
         }
       }
       leaf detection-window {
         description "Time window for detection of duplicate MACs";
         units "seconds";
         type union {
           type string {
             pattern "<.*>|$.*";
           }
           type uint32 {
             range "5 .. 600";
           }
         }
       }
       leaf auto-recovery-time {
         description "Automatically unblock duplicate MACs after a time delay";
         units "minutes";
         type union {
           type string {
             pattern "<.*>|$.*";
           }
           type uint32 {
             range "1 .. 360";
           }
         }
       }
       leaf auto-recovery-time-seconds {
         description "Automatically unblock duplicate MACs after a time delay";
         units "seconds";
         type union {
           type string {
             pattern "<.*>|$.*";
           }
           type uint32 {
             range "1 .. 21600";
           }
         }
       }
       leaf include-local-moves {
         description "Include local moves in duplicate MAC detection";
         type empty;
       }
       leaf action {
         description "Loop protection action";
         type enumeration {
           enum "block" {
             description "Drop packet with duplicate MAC as source or destination";
           }
           enum "shutdown" {
             description "Shutdown the port to prevent loop";
           }
           enum "no-mac-suppression" {
             description "Disable MAC suppression for duplicate MACs";
           }
         }
       }
     }
     container irb-symmetric-routing {
       presence "enable irb-symmetric-routing";
       description "Enable EVPN T-2 symmetric routing";
       uses apply-advanced;
       leaf vni {
         description "VXLAN network identifier used for T-2 symmetric routing IP prefixes";
         type union {
           type string {
             pattern "<.*>|$.*";
           }
           type uint32 {
             range "1 .. 16777214";
           }
         }
       }
     }
     container source-packet-routing {
       presence "enable source-packet-routing";
       uses apply-advanced;
       container srv6 {
         description "Enable IPv6 segment routing (SRv6)";
         container locator {
           description "SRv6 locator";
           leaf loc-name {
             description "Locator name";
             type string;
             mandatory true;
           }
           choice mode {
             case case_1 {
               leaf end-dt2-sid {
                 description "Segment Routing Header-based End.DT2 SIDs";
                 type empty;
               }
             }
             case case_2 {
               leaf micro-dt2-sid {
                 description "Micro-SID based End.DT2 SIDs";
                 type empty;
               }
             }
           }
         }
       }
     }
     container ip-prefix-routes {
       presence "enable ip-prefix-routes";
       description "Advertise IP prefixes through EVPN";
       uses apply-advanced;
       leaf advertise {
         description "Advertisement attributes for IP prefixes";
         type enumeration {
           enum "gateway-address" {
             description "Advertise a gateway address in exported IP prefix routes";
           }
           enum "direct-nexthop" {
             description "Advertise a direct nexthop in exported IP prefix routes";
           }
         }
         mandatory true;
       }
       leaf encapsulation {
         description "Encapsulation used for IP prefixes";
         type enumeration {
           enum "mpls" {
             description "MPLS encapsulation";
           }
           enum "vxlan" {
             description "VXLAN encapsulation";
           }
           enum "srv6" {
             description "SRV6 encapsulation";
           }
         }
       }
       leaf reject-asymmetric-vni {
         description "Disable Type-5 asymmetric-vni";
         type empty;
       }
       leaf vni {
         description "VXLAN network identifier used for IP prefixes";
         type union {
           type string {
             pattern "<.*>|$.*";
           }
           type uint32 {
             range "1 .. 16777214";
           }
         }
       }
       leaf-list import {
         ordered-by user;
         description "Policy to control import of IP prefixes from EVPN";
         type jt:policy-algebra;
       }
       leaf-list export {
         ordered-by user;
         description "Policy to control export of IP prefixes through EVPN";
         type jt:policy-algebra;
       }
       container route-attributes {
         description "Route Attribute Import Export Option";
         uses apply-advanced;
         container as-path {
           description "AS-PATH Attribute";
           uses apply-advanced;
           leaf import-action {
             description "AS-PATH Attribute Inherit Option on Import";
             type enumeration {
               enum "allow" {
                 description "Inherit as-path from EVPN routes to IP routes";
               }
               enum "skip" {
                 description "Donot inehrit as-path from EVPN routes to IP routes";
               }
             }
           }
           leaf export-action {
             description "AS-PATH Attribute Inherit Option on Export";
             type enumeration {
               enum "allow" {
                 description "Inherit as-path from IP routes to EVPN routes";
               }
               enum "skip" {
                 description "Donot inherit as-path from IP routes to EVPN routes";
               }
             }
           }
         }
         container preference {
           description "Preference Attribute";
           uses apply-advanced;
           leaf import-action {
             description "Preference Attribute Inerit Option on Import";
             type enumeration {
               enum "allow" {
                 description "Inherit preference from EVPN routes to IP routes";
               }
               enum "skip" {
                 description "Donot inherit preference from EVPN routes to EVPN routes";
               }
             }
           }
           leaf export-action {
             description "Preference Attribute Inherit Option on Export";
             type enumeration {
               enum "allow" {
                 description "Inherit preference from IP routes to EVPN routes";
               }
               enum "skip" {
                 description "Donot inherit preference from IP routes to EVPN routes";
               }
             }
           }
         }
         container community {
           description "Community Attribute";
           uses apply-advanced;
           leaf import-action {
             description "Community Attribute Inherit Option on Import";
             type enumeration {
               enum "allow" {
                 description "Inherit community from EVPN routes to IP routes";
               }
               enum "skip" {
                 description "Donot inherit community from EVPN routes to IP routes";
               }
             }
           }
           leaf export-action {
             description "Community Attribute Inherit Option on Export";
             type enumeration {
               enum "allow" {
                 description "Inherit community from IP routes to EVPN routes";
               }
               enum "skip" {
                 description "Donot inherit community from IP route to EVPN routes";
               }
             }
           }
         }
       }
       container source-packet-routing {
         description "Enable source packet routing";
         uses apply-advanced;
         container srv6 {
           description "Enable IPv6 segment souting (SRv6)";
           uses apply-advanced;
           list locator {
             key name;
             ordered-by user;
             description "SRv6 locator";
             leaf name {
               description "Locator name";
               type string;
             }
             uses apply-advanced;
             container end-dt4-sid {
               presence "enable end-dt4-sid";
               description "End dt4 sid";
             }
             container end-dt6-sid {
               presence "enable end-dt6-sid";
               description "End dt6 sid";
             }
             container end-dt46-sid {
               presence "enable end-dt46-sid";
               description "End dt46 sid";
             }
             container micro-dt4-sid {
               presence "enable micro-dt4-sid";
               description "Micro dt4 sid";
             }
             container micro-dt6-sid {
               presence "enable micro-dt6-sid";
               description "Micro dt6 sid";
             }
             container micro-dt46-sid {
               presence "enable micro-dt46-sid";
               description "Micro dt46 sid";
             }
           }
         }
       }
     }
     choice flexible-cross-connect-type {
       case case_1 {
       }
       case case_2 {
       }
     }
     container traceoptions {
       description "Trace options for Layer 2 VPNs";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "topology" {
               description "Trace Layer 2 VPN, VPLS and EVPN topology changes";
             }
             enum "nlri" {
               description "Trace Layer 2 VPN, VPLS and EVPN remote site advertisements";
             }
             enum "connections" {
               description "Trace Layer 2 VPN and VPLS connections";
             }
             enum "automatic-site" {
               description "Trace VPLS automatic site state";
             }
             enum "oam" {
               description "Trace OAM messages";
             }
             enum "mac-database" {
               description "Trace MAC route database in a EVPN instance";
             }
             enum "nsr" {
               description "Trace NSR in a EVPN instance";
             }
             enum "egress-protection" {
               description "Trace Edge Protection messages";
             }
             enum "instance" {
               description "Evpn instance related messages";
             }
             enum "interface" {
               description "Interface related messages";
             }
             enum "l2aldsync" {
               description "Messages related to EVPN-L2ALD communication";
             }
             enum "p2mp" {
               description "P2MP messages";
             }
             enum "esi" {
               description "Evpn ethernet segment related messages";
             }
             enum "mcsn" {
               description "Evpn multicast snooping related messages";
             }
             enum "vpws" {
               description "VPWS messages";
             }
             enum "irb" {
               description "Integrated routing bridging messages";
             }
             enum "ar" {
               description "Assisted-replication messages";
             }
             enum "etree" {
               description "Evpn etree messages";
             }
             enum "kernel" {
               description "Messages related to rpd-kernel communication";
             }
             enum "bd" {
               description "Evpn bridge domain messages";
             }
             enum "pbb" {
               description "Evpn provider backbone bridging messages";
             }
             enum "infra" {
               description "Messages related to infrastructure in evpn";
             }
             enum "pfxdb" {
               description "Type-5 related messages";
             }
             enum "peg-df" {
               description "PIM EVPN Gateway DF-Election related messages";
             }
             enum "gbptagdb" {
               description "Trace message related to gbptagdb";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf encapsulation-type {
       description "Encapsulation type for VPN";
       type enumeration {
         enum "atm-aal5" {
           description "ATM AAL/5 encapsulation";
         }
         enum "atm-cell" {
           description "ATM port promiscuous mode cell encapsulation";
         }
         enum "atm-cell-port-mode" {
           description "ATM port promiscuous mode cell encapsulation";
         }
         enum "atm-cell-vp-mode" {
           description "ATM VP promiscuous mode cell encapsulation";
         }
         enum "atm-cell-vc-mode" {
           description "ATM non-promiscuous cell encapsulation";
         }
         enum "frame-relay" {
           description "Frame Relay encapsulation";
         }
         enum "ppp" {
           description "PPP encapsulation";
         }
         enum "cisco-hdlc" {
           description "Cisco-compatible HDLC encapsulation";
         }
         enum "ethernet-vlan" {
           description "Ethernet VLAN encapsulation";
         }
         enum "ethernet" {
           description "Ethernet encapsulation";
         }
         enum "interworking" {
           description "Layer 2.5 interworking VPN";
         }
         enum "frame-relay-port-mode" {
           description "Frame Relay port mode encapsulation";
         }
         enum "satop-t1" {
           description "SATOP-T1 based Layer 2 VPN";
         }
         enum "satop-e1" {
           description "SATOP-E1 based Layer 2 VPN";
         }
         enum "satop-t3" {
           description "SATOP-T3 based Layer 2 VPN";
         }
         enum "satop-e3" {
           description "SATOP-E3 based Layer 2 VPN";
         }
         enum "cesop" {
           description "CESOP based Layer 2 VPN";
         }
       }
     }
     leaf control-word {
       description "Add control word to the Layer 2 encapsulation";
       type empty;
     }
     leaf no-control-word {
       description "Disables control word on the Layer 2 encapsulation";
       type empty;
     }
     leaf site-range {
       description "Maximum site identifier in this VPLS domain";
       type union {
         type string {
           pattern "<.*>|$.*";
         }
         type uint32 {
           range "1 .. 65534";
         }
       }
     }
     leaf label-block-size {
       description "Label block size for this VPLS instance";
       type enumeration {
         enum "2" {
           description "Label block size of 2";
         }
         enum "4" {
           description "Label block size of 4";
         }
         enum "8" {
           description "Label block size of 8";
         }
         enum "16" {
           description "Label block size of 16";
         }
       }
     }
     choice tunnel-services-choice {
       case case_1 {
         container tunnel-services {
           description "Use tunnel services for this VPLS instance";
           uses apply-advanced;
           leaf-list devices {
             ordered-by user;
             description "Tunnel services devices to use for this VPLS instance";
             type union {
               type jt:interface-device;
               type string {
                 pattern "<.*>|$.*";
               }
             }
           }
           leaf primary {
             description "Primary tunnel services device to use for VPLS instance";
             type union {
               type jt:interface-device;
               type string {
                 pattern "<.*>|$.*";
               }
             }
           }
         }
       }
       case case_2 {
         leaf no-tunnel-services {
           description "Do not use tunnel services for this VPLS instance";
           type empty;
         }
       }
     }
     list site {
       key name;
       description "Sites connected to this provider equipment";
       leaf name {
         description "Name of Layer 2 VPN or VPLS site";
         type string;
       }
       uses apply-advanced;
       choice site-identifier-mode {
         case case_1 {
           leaf site-identifier {
             description "Layer 2 VPN or VPLS site identifier (unique in the VPN)";
             type union {
               type string {
                 pattern "<.*>|$.*";
               }
               type uint32 {
                 range "1 .. 65534";
               }
             }
           }
         }
         case case_2 {
           container automatic-site-id {
             presence "enable automatic-site-id";
             description "Enable automatic assignment of site identifier";
             uses apply-advanced;
             leaf startup-wait-time {
               description "Time to wait at startup before claming a site identifier (seconds)";
               units "seconds";
               type union {
                 type string {
                   pattern "<.*>|$.*";
                 }
                 type uint32 {
                   range "1 .. 3600";
                 }
               }
             }
             leaf new-site-wait-time {
               description "Time to wait before claiming a site identifier";
               units "seconds";
               type union {
                 type string {
                   pattern "<.*>|$.*";
                 }
                 type uint32 {
                   range "1 .. 3600";
                 }
               }
             }
             leaf collision-detect-time {
               description "Time to wait for detecting a collision";
               units "seconds";
               type union {
                 type string {
                   pattern "<.*>|$.*";
                 }
                 type uint32 {
                   range "1 .. 3600";
                 }
               }
             }
             container reclaim-wait-time {
               presence "enable reclaim-wait-time";
               description "Time to wait for reclaiming a site identifier";
               leaf minimum {
                 description "Minimum wait time";
                 units "milliseconds";
                 type union {
                   type uint32;
                   type string {
                     pattern "<.*>|$.*";
                   }
                 }
                 mandatory true;
               }
               leaf maximum {
                 description "Maximum wait time";
                 units "milliseconds";
                 type union {
                   type uint32;
                   type string {
                     pattern "<.*>|$.*";
                   }
                 }
                 mandatory true;
               }
             }
           }
         }
       }
       leaf source-attachment-identifier {
         description "FEC 129 VPWS source attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       leaf community {
         description "Community associated with this site";
         type string;
       }
       container multi-homing {
         presence "enable multi-homing";
         description "Enable multi-homing functionality for this site";
         uses apply-advanced;
         leaf hold-time {
           description "Enable multi-homing non-designated forwarder hold time (seconds)";
           units "seconds";
           type union {
             type string {
               pattern "<.*>|$.*";
             }
             type uint32 {
               range "1 .. 18000";
             }
           }
         }
       }
       leaf site-preference {
         description "Layer 2 VPN or VPLS site preference";
         type string;
       }
       leaf hot-standby {
         description "Keep backup pseudowire in continuous standby mode and ready for traffic forwarding";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       list mesh-group {
         key name;
         ordered-by user;
         description "Mesh-groups that are part of this site";
         leaf name {
           description "Mesh-group name";
           type string;
         }
         uses apply-advanced;
       }
       container active-interface {
         description "Configure interface to designate as active";
         choice interface_name {
           case case_1 {
             leaf any {
               description "One configured interface is designated active at random";
               type empty;
             }
           }
           case case_2 {
             leaf primary {
               description "Interface to designate as active if it is operational";
               type union {
                 type jt:interface-name;
                 type string {
                   pattern "<.*>|$.*";
                 }
               }
             }
           }
         }
       }
       leaf best-site {
         description "Activates best-site functionality for this instance";
         type empty;
       }
       list interface {
         key name;
         description "Interface that connect this site to the VPN";
         leaf name {
           description "Interface name";
           type union {
             type jt:interface-name;
             type string {
               pattern "<.*>|$.*";
             }
           }
         }
         uses apply-advanced;
         leaf remote-site-id {
           description "Site identifier associated with this interface";
           type union {
             type string {
               pattern "<.*>|$.*";
             }
             type uint32 {
               range "1 .. 65534";
             }
           }
         }
         leaf target-attachment-identifier {
           description "FEC 129 VPWS target attachment identifier";
           type string {
           }
         }
         leaf flow-label-transmit {
           description "Advertise capability to push Flow Label in transmit direction to remote PE";
           type empty;
         }
         leaf flow-label-receive {
           description "Advertise capability to pop Flow Label in receive direction to remote PE";
           type empty;
         }
         choice cword {
           case case_1 {
             leaf control-word {
               description "Add control word to the Layer 2 encapsulation";
               type empty;
             }
           }
           case case_2 {
             leaf no-control-word {
               description "Disables control word on the Layer 2 encapsulation";
               type empty;
             }
           }
         }
         leaf encapsulation-type {
           description "Encapsulation type for VPN";
           type enumeration {
             enum "atm-aal5" {
               description "ATM AAL/5 encapsulation";
             }
             enum "atm-cell" {
               description "ATM port promiscuous mode cell encapsulation";
             }
             enum "atm-cell-port-mode" {
               description "ATM port promiscuous mode cell encapsulation";
             }
             enum "atm-cell-vp-mode" {
               description "ATM VP promiscuous mode cell encapsulation";
             }
             enum "atm-cell-vc-mode" {
               description "ATM non-promiscuous cell encapsulation";
             }
             enum "frame-relay" {
               description "Frame Relay encapsulation";
             }
             enum "ppp" {
               description "PPP encapsulation";
             }
             enum "cisco-hdlc" {
               description "Cisco-compatible HDLC encapsulation";
             }
             enum "ethernet-vlan" {
               description "Ethernet VLAN encapsulation";
             }
             enum "ethernet" {
               description "Ethernet encapsulation";
             }
             enum "interworking" {
               description "Layer 2.5 interworking VPN";
             }
             enum "frame-relay-port-mode" {
               description "Frame Relay port mode encapsulation";
             }
             enum "satop-t1" {
               description "SATOP-T1 based Layer 2 VPN";
             }
             enum "satop-e1" {
               description "SATOP-E1 based Layer 2 VPN";
             }
             enum "satop-t3" {
               description "SATOP-T3 based Layer 2 VPN";
             }
             enum "satop-e3" {
               description "SATOP-E3 based Layer 2 VPN";
             }
             enum "cesop" {
               description "CESOP based Layer 2 VPN";
             }
           }
         }
         leaf ignore-encapsulation-mismatch {
           description "Allow different encapsulation types on local and remote end";
           type empty;
         }
         leaf mtu {
           description "MTU to be advertised to the remote end";
           type union {
             type string {
               pattern "<.*>|$.*";
             }
             type uint16 {
               range "512 .. 65535";
             }
           }
         }
         leaf ignore-mtu-mismatch {
           description "Allow different MTU values on local and remote end";
           type empty;
         }
         leaf pseudowire-status-tlv {
           description "Send pseudowire status TLV";
           type empty;
         }
         leaf community {
           description "Community associated with this interface";
           type string;
         }
         leaf description {
           description "Text description";
           type string;
         }
       }
     }
     leaf community {
       description "Community associated with this VPLS instance";
       type string;
     }
     leaf vpls-id {
       description "Identifier for this VPLS instance";
       type string;
     }
     leaf mtu {
       description "MTU to be advertised to the remote end";
       type union {
         type string {
           pattern "<.*>|$.*";
         }
         type uint16 {
           range "512 .. 65535";
         }
       }
     }
     leaf ignore-mtu-mismatch {
       description "Allow different MTU values on local and remote end";
       type empty;
     }
     container mac-flush {
       presence "enable mac-flush";
       description "Enables mac-flush processing";
       uses apply-advanced;
       leaf any-interface {
         description "Send mac-flush when any AC interface goes down";
         type empty;
       }
       leaf any-spoke {
         description "Send mac-flush when any spoke pseudo wire goes down";
         type empty;
       }
       leaf propagate {
         description "Propagate mac-flush to the core";
         type empty;
       }
     }
     leaf ignore-encapsulation-mismatch {
       description "Allow different encapsulation types on local and remote end";
       type empty;
     }
     leaf pseudowire-status-tlv {
       description "Send pseudowire status TLV";
       type empty;
     }
     list neighbor {
       key name;
       ordered-by user;
       description "Neighbor for this VPLS instance";
       leaf name {
         description "Neighbor ID";
         type jt:ipv4addr;
       }
       uses apply-advanced;
       container static {
         presence "enable static";
         description "Configuration of static vpls";
         uses apply-advanced;
         leaf incoming-label {
           description "VPLS incoming static label [1000000 - 1048575] or [29696 - 41983]";
           type union {
             type uint32;
             type string {
               pattern "<.*>|$.*";
             }
           }
           mandatory true;
         }
         leaf outgoing-label {
           description "VPLS outgoing static label";
           type union {
             type string {
               pattern "<.*>|$.*";
             }
             type uint32 {
               range "16 .. 1048575";
             }
           }
           mandatory true;
         }
         choice cword {
           case case_1 {
             leaf control-word {
               description "Adds control-word to the Layer 2 encapsulation";
               type empty;
             }
           }
           case case_2 {
             leaf no-control-word {
               description "Disables control-word to the Layer 2 encapsulation";
               type empty;
             }
           }
         }
       }
       leaf psn-tunnel-endpoint {
         description "Endpoint of the transport tunnel on the remote PE";
         type jt:ipv4addr;
       }
       leaf community {
         description "Community associated with this neighbor";
         type string;
       }
       leaf encapsulation-type {
         description "Encapsulation type for VPN";
         type enumeration {
           enum "ethernet-vlan" {
             description "Ethernet VLAN encapsulation";
           }
           enum "ethernet" {
             description "Ethernet encapsulation";
           }
         }
       }
       leaf ignore-encapsulation-mismatch {
         description "Allow different encapsulation types on local and remote end";
         type empty;
       }
       container pseudowire-status-tlv {
         presence "enable pseudowire-status-tlv";
         description "Send pseudowire status TLV";
         uses apply-advanced;
         leaf hot-standby-vc-on {
           description "Activate pseudowire upon arrival of 'hot-standby' status TLV message";
           type empty;
         }
       }
       leaf switchover-delay {
         description "Pseudowire switchover delay ";
         default "10000";
         units "milliseconds";
         type union {
           type string {
             pattern "<.*>|$.*";
           }
           type uint32 {
             range "0 .. 180000";
           }
         }
       }
       container revert-time {
         presence "enable revert-time";
         description "Enable pseudowire redundancy reversion (seconds)";
         leaf delay {
           description "Reversion timer (seconds)";
           units "seconds";
           type union {
             type string {
               pattern "<.*>|$.*";
             }
             type uint32 {
               range "0 .. 3600";
             }
           }
           mandatory true;
         }
         leaf maximum {
           description "Maximum reversion interval to add over revert-time delay";
           units "seconds";
           type union {
             type string {
               pattern "<.*>|$.*";
             }
             type uint32 {
               range "0 .. 7200";
             }
           }
         }
       }
       leaf connection-protection {
         description "End-2-end protection via OAM failure detection";
         type empty;
       }
       list backup-neighbor {
         key name;
         ordered-by user;
         description "Configuration of redundant l2circuit";
         leaf name {
           description "Neighbor ID";
           type jt:ipv4addr;
         }
         uses apply-advanced;
         container static {
           presence "enable static";
           description "Configuration of static vpls";
           uses apply-advanced;
           leaf incoming-label {
             description "VPLS incoming static label [1000000 - 1048575] or [29696 - 41983]";
             type union {
               type uint32;
               type string {
                 pattern "<.*>|$.*";
               }
             }
             mandatory true;
           }
           leaf outgoing-label {
             description "VPLS outgoing static label";
             type union {
               type string {
                 pattern "<.*>|$.*";
               }
               type uint32 {
                 range "16 .. 1048575";
               }
             }
             mandatory true;
           }
         }
         leaf community {
           description "Community associated with this Layer 2 circuit";
           type string;
         }
         leaf psn-tunnel-endpoint {
           description "Endpoint of the transport tunnel on the remote PE";
           type jt:ipv4addr;
         }
         leaf standby {
           description "Keep backup pseudowire in continuous standby";
           type empty;
         }
         leaf hot-standby {
           description "Keep backup pseudowire in continuous standby mode and ready for traffic forwarding";
           type empty;
         }
       }
     }
     leaf flow-label-transmit {
       description "Advertise capability to push Flow Label in transmit direction to remote PE";
       type empty;
     }
     leaf flow-label-receive {
       description "Advertise capability to pop Flow Label in receive direction to remote PE";
       type empty;
     }
     leaf flow-label-transmit-static {
       description "Push Flow Label on PW packets sent to remote PE";
       type empty;
     }
     leaf flow-label-receive-static {
       description "Pop Flow Label from PW packets received from remote PE";
       type empty;
     }
     leaf flow-label {
       description "Advertise flow-label capability";
       type empty;
     }
     leaf flow-label-static {
       description "Static flow-label";
       type empty;
     }
     list mesh-group {
       key name;
       description "Mesh-group under this VPLS instance";
       leaf name {
         description "Mesh-group name";
         type string {
         }
       }
       uses apply-advanced;
       choice peer-as-choice {
         case case_1 {
           container peer-as {
             description "Autonomous system of the peer";
             uses apply-advanced;
             leaf all {
               description "Include peers from all autonomous systems";
               type empty;
             }
           }
         }
       }
       leaf vpls-id {
         description "LDP VPLS Identifier for this mesh-group";
         type string;
       }
       leaf-list vrf-import {
         ordered-by user;
         description "Import policy for VPLS instance mesh-group";
         type jt:policy-algebra;
       }
       leaf-list vrf-export {
         ordered-by user;
         description "Export policy for VPLS instance mesh-group";
         type jt:policy-algebra;
       }
       container vrf-target {
         description "VPLS mesh-group target community configuration";
         uses apply-advanced;
         leaf community {
           description "Target community to use in import and export";
           type string {
           }
         }
         leaf import {
           description "Target community to use when filtering on import";
           type string {
           }
         }
         leaf export {
           description "Target community to use when marking routes on export";
           type string {
           }
         }
       }
       container mac-flush {
         presence "enable mac-flush";
         description "Enables mac-flush processing";
         uses apply-advanced;
         leaf any-interface {
           description "Send mac-flush when any AC interface goes down";
           type empty;
         }
         leaf any-spoke {
           description "Send mac-flush when any spoke pseudo wire goes down";
           type empty;
         }
         leaf propagate {
           description "Propagate mac-flush to the core";
           type empty;
         }
       }
       list neighbor {
         key name;
         ordered-by user;
         description "Neighbor belonging to this mesh-group";
         leaf name {
           description "Neighbor ID";
           type jt:ipv4addr;
         }
         uses apply-advanced;
         container static {
           presence "enable static";
           description "Configuration of static vpls";
           uses apply-advanced;
           leaf incoming-label {
             description "VPLS incoming static label [1000000 - 1048575] or [29696 - 41983]";
             type union {
               type uint32;
               type string {
                 pattern "<.*>|$.*";
               }
             }
             mandatory true;
           }
           leaf outgoing-label {
             description "VPLS outgoing static label";
             type union {
               type string {
                 pattern "<.*>|$.*";
               }
               type uint32 {
                 range "16 .. 1048575";
               }
             }
             mandatory true;
           }
           choice cword {
             case case_1 {
               leaf control-word {
                 description "Adds control-word to the Layer 2 encapsulation";
                 type empty;
               }
             }
             case case_2 {
               leaf no-control-word {
                 description "Disables control-word to the Layer 2 encapsulation";
                 type empty;
               }
             }
           }
         }
         leaf psn-tunnel-endpoint {
           description "Endpoint of the transport tunnel on the remote PE";
           type jt:ipv4addr;
         }
         leaf community {
           description "Community associated with this neighbor";
           type string;
         }
         leaf encapsulation-type {
           description "Encapsulation type for VPN";
           type enumeration {
             enum "ethernet-vlan" {
               description "Ethernet VLAN encapsulation";
             }
             enum "ethernet" {
               description "Ethernet encapsulation";
             }
           }
         }
         leaf ignore-encapsulation-mismatch {
           description "Allow different encapsulation types on local and remote end";
           type empty;
         }
         container pseudowire-status-tlv {
           presence "enable pseudowire-status-tlv";
           description "Send pseudowire status TLV";
           uses apply-advanced;
           leaf hot-standby-vc-on {
             description "Activate pseudowire upon arrival of 'hot-standby' status TLV message";
             type empty;
           }
         }
         leaf switchover-delay {
           description "Pseudowire switchover delay ";
           default "10000";
           units "milliseconds";
           type union {
             type string {
               pattern "<.*>|$.*";
             }
             type uint32 {
               range "0 .. 180000";
             }
           }
         }
         container revert-time {
           presence "enable revert-time";
           description "Enable pseudowire redundancy reversion (seconds)";
           leaf delay {
             description "Reversion timer (seconds)";
             units "seconds";
             type union {
               type string {
                 pattern "<.*>|$.*";
               }
               type uint32 {
                 range "0 .. 3600";
               }
             }
             mandatory true;
           }
           leaf maximum {
             description "Maximum reversion interval to add over revert-time delay";
             units "seconds";
             type union {
               type string {
                 pattern "<.*>|$.*";
               }
               type uint32 {
                 range "0 .. 7200";
               }
             }
           }
         }
         leaf connection-protection {
           description "End-2-end protection via OAM failure detection";
           type empty;
         }
         list backup-neighbor {
           key name;
           ordered-by user;
           description "Configuration of redundant l2circuit";
           leaf name {
             description "Neighbor ID";
             type jt:ipv4addr;
           }
           uses apply-advanced;
           container static {
             presence "enable static";
             description "Configuration of static vpls";
             uses apply-advanced;
             leaf incoming-label {
               description "VPLS incoming static label [1000000 - 1048575] or [29696 - 41983]";
               type union {
                 type uint32;
                 type string {
                   pattern "<.*>|$.*";
                 }
               }
               mandatory true;
             }
             leaf outgoing-label {
               description "VPLS outgoing static label";
               type union {
                 type string {
                   pattern "<.*>|$.*";
                 }
                 type uint32 {
                   range "16 .. 1048575";
                 }
               }
               mandatory true;
             }
           }
           leaf community {
             description "Community associated with this Layer 2 circuit";
             type string;
           }
           leaf psn-tunnel-endpoint {
             description "Endpoint of the transport tunnel on the remote PE";
             type jt:ipv4addr;
           }
           leaf standby {
             description "Keep backup pseudowire in continuous standby";
             type empty;
           }
           leaf hot-standby {
             description "Keep backup pseudowire in continuous standby mode and ready for traffic forwarding";
             type empty;
           }
         }
         leaf-list vpls-id-list {
           ordered-by user;
           description "LDP VPLS Identifier list for this neighbor";
           type union {
             type string {
               pattern "<.*>|$.*";
             }
             type uint32 {
               range "1 .. 4294967295";
             }
           }
         }
       }
       container route-distinguisher {
         description "Route distinguisher for this mesh-group";
         leaf rd-type {
           description "Number in (16 bit:32 bit) or (32 bit 'L':16 bit) or (IP address:16 bit) format";
           type string {
           }
         }
       }
     }
     leaf connectivity-type {
       description "Specify type of interface sufficient to bring vpls connection up";
       type enumeration {
         enum "ce" {
           description "CE interface is required";
         }
         enum "irb" {
           description "IRB interface is sufficient";
         }
         enum "permanent" {
           description "Pseudowire permanently up";
         }
       }
     }
     list import-labeled-routes {
       key name;
       ordered-by user;
       description "Import ingress label route to instance.mpls.0 from mpls.0";
       leaf name {
         description "Routing instance name where label route has to be imported";
         type string;
       }
     }
     container multi-homing {
       description "Multi-homing configuration for FEC129 VPLS";
       uses apply-advanced;
       leaf peer-active {
         description "Keep CE interfaces in up state when all BGP peers go down";
         type empty;
       }
       list site {
         key name;
         description "Sites connected to this provider equipment";
         leaf name {
           description "Name of Layer 2 VPN or VPLS site";
           type string;
         }
         uses apply-advanced;
         leaf identifier {
           description "Layer 2 VPN or VPLS multi-homing identifier";
           type union {
             type string {
               pattern "<.*>|$.*";
             }
             type uint16 {
               range "1 .. 65534";
             }
           }
         }
         leaf preference {
           description "Layer 2 VPN or VPLS multi-homing preference";
           type string;
         }
         container active-interface {
           description "Configure interface to designate as active";
           uses apply-advanced;
           choice interface_name {
             case case_1 {
               leaf any {
                 description "One configured interface is designated active at random";
                 type empty;
               }
             }
             case case_2 {
               leaf primary {
                 description "Interface to designate as active if it is operational";
                 type union {
                   type jt:interface-name;
                   type string {
                     pattern "<.*>|$.*";
                   }
                 }
               }
             }
           }
         }
         list interface {
           key name;
           ordered-by user;
           description "Interface that connects this site to the VPN";
           leaf name {
             description "Interface name";
             type union {
               type jt:interface-name;
               type string {
                 pattern "<.*>|$.*";
               }
             }
           }
           uses apply-advanced;
           leaf preference {
             description "Layer 2 VPN or VPLS multi-homing preference for the interface";
             type union {
               type string {
                 pattern "<.*>|$.*";
               }
               type uint16 {
                 range "1 .. 65535";
               }
             }
           }
         }
         leaf peer-active {
           description "Keep CE interfaces in up state when all BGP peers go down";
           type empty;
         }
       }
     }
     leaf service-type {
       description "Specify service type for vpls";
       type enumeration {
         enum "single" {
           description "Only one service for the virtual-switch";
         }
       }
     }
   }
   grouping juniper-ri-protocols-bfd {
     uses apply-advanced;
     container sbfd {
       description "Seamless BFD parameters";
       uses apply-advanced;
       leaf-list pool {
         description "List of seamless BFD endpoints";
         type union {
           type uint32;
           type string {
             pattern "<.*>|$.*";
           }
         }
       }
       list local-discriminator {
         key name;
         ordered-by user;
         description "Local discriminator for seamless BFD responder";
         leaf name {
           description "Local discriminator for seamless BFD responder";
           type union {
             type string {
               pattern "<.*>|$.*";
             }
             type uint32 {
               range "1 .. 4294967295";
             }
           }
         }
         uses apply-advanced;
         leaf minimum-receive-interval {
           description "Minimum receive interval for seamless BFD responder";
           units "milliseconds";
           type union {
             type string {
               pattern "<.*>|$.*";
             }
             type uint32 {
               range "10 .. 255000";
             }
           }
         }
         leaf local-ip-address {
           description "IPv4 source address";
           type jt:ipv4addr;
         }
         leaf local-ipv6-address {
           description "IPv6 source address";
           type jt:ipv6addr;
         }
       }
       list local-discriminator-ip {
         key name;
         ordered-by user;
         description "Local discriminator IP address for sBFD responder";
         leaf name {
           description "Local discriminator IP address for sBFD responder";
           type jt:ipv4addr;
         }
         uses apply-advanced;
         leaf minimum-receive-interval {
           description "Minimum receive interval for seamless BFD responder";
           units "milliseconds";
           type union {
             type string {
               pattern "<.*>|$.*";
             }
             type uint32 {
               range "10 .. 255000";
             }
           }
         }
         leaf local-ip-address {
           description "IPv4 source address";
           type jt:ipv4addr;
         }
       }
     }
   }
   grouping juniper-routing-options {
     uses apply-advanced;
     list flex-algorithm {
       key name;
       description "Configure flex-algorithms supported by this node.";
       leaf name {
         description "Algorithm id";
         type union {
           type string {
             pattern "<.*>|$.*";
           }
           type uint32 {
             range "128 .. 255";
           }
         }
       }
       uses apply-advanced;
       container definition {
         description "Configure flex-algorithm definition.";
         uses apply-advanced;
         leaf metric-type {
           type enumeration {
             enum "igp-metric" {
               description "Metric configured to be used for IGP";
             }
             enum "te-metric" {
               description "Traffic-engineering metric";
             }
             enum "delay-metric" {
               description "Min unidirectional link delay metric";
             }
           }
         }
         choice calculation-type {
           case case_1 {
             leaf spf {
               description "Normal SPF of type 0";
               type empty;
             }
           }
           case case_2 {
             leaf strict-spf {
               description "Strict SPF";
               type empty;
             }
           }
         }
         leaf use-flex-algorithm-prefix-metric {
           description "Set M flag in the flex-algorithm definition flags";
           type empty;
         }
         leaf priority {
           description "Priority of the flex-algorithm advertisement.";
           type union {
             type string {
               pattern "<.*>|$.*";
             }
             type uint32 {
               range "0 .. 255";
             }
           }
         }
         leaf-list exclude-srlg {
           ordered-by user;
           description "SRLG Name";
           type string;
           max-elements 16;
         }
         container admin-group {
           description "Administrative group policy";
           uses admin_group_include_exclude;
         }
       }
       leaf color {
         description "Color to be associated with this flex-algorithm";
         type union {
           type uint32;
           type string {
             pattern "<.*>|$.*";
           }
         }
       }
       container use-transport-class {
         presence "enable use-transport-class";
         description "Install ingress routes via transport class RIBs";
         uses apply-advanced;
         leaf inet3-install {
           description "Install flex-algo routes in inet{6}.3 table";
           type empty;
         }
       }
     }
     container source-packet-routing {
       description "Source packet routing (SPRING)";
       uses apply-advanced;
       list mapping-server-entry {
         key name;
         ordered-by user;
         description "Mapping server entry";
         leaf name {
           description "Mapping server entry name";
           type string {
             length "1 .. 64";
           }
         }
         uses apply-advanced;
         list prefix-segment {
           key name;
           ordered-by user;
           description "Prefix segment";
           max-elements 256;
           leaf name {
             description "Prefix segment prefix";
             type jt:ipprefix;
           }
           uses apply-advanced;
           leaf index {
             description "Prefix segment index";
             type union {
               type string {
                 pattern "<.*>|$.*";
               }
               type uint32 {
                 range "0 .. 199999";
               }
             }
             mandatory true;
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
         list prefix-segment-range {
           key name;
           ordered-by user;
           description "Prefix segment range";
           max-elements 256;
           leaf name {
             description "Prefix segment range name";
             type string {
               length "1 .. 64";
             }
           }
           uses apply-advanced;
           leaf start-prefix {
             description "Start prefix";
             type jt:ipprefix;
             mandatory true;
           }
           leaf start-index {
             description "Start index";
             type union {
               type string {
                 pattern "<.*>|$.*";
               }
               type uint32 {
                 range "0 .. 199999";
               }
             }
             mandatory true;
           }
           leaf size {
             description "Size of prefix segment range";
             type union {
               type string {
                 pattern "<.*>|$.*";
               }
               type uint32 {
                 range "1 .. 1024";
               }
             }
             mandatory true;
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
       }
       container srv6 {
         description "SRv6 source-packet-routing";
         uses apply-advanced;
         list block {
           key name;
           ordered-by user;
           description "Block configuration options";
           leaf name {
             description "Block name";
             type string {
               length "1 .. 63";
             }
           }
           uses apply-advanced;
           leaf address {
             description "Block prefix for SRv6";
             type jt:ipv6prefix-mandatory;
             mandatory true;
           }
           container global-micro-sid {
             description "Global micro SID block range parameters";
             uses apply-advanced;
             leaf maximum-sids {
               description "Maximum number of SIDs used for global block";
               type union {
                 type string {
                   pattern "<.*>|$.*";
                 }
                 type uint32 {
                   range "0 .. 65536";
                 }
               }
             }
             leaf maximum-static-sids {
               description "Maximum number of static SIDs used for global block";
               type union {
                 type string {
                   pattern "<.*>|$.*";
                 }
                 type uint32 {
                   range "0 .. 65536";
                 }
               }
             }
           }
           container local-micro-sid {
             description "Local micro SID block range parameters";
             uses apply-advanced;
             leaf maximum-static-sids {
               description "Maximum number of static SIDs used for local block";
               type union {
                 type string {
                   pattern "<.*>|$.*";
                 }
                 type uint32 {
                   range "0 .. 65536";
                 }
               }
             }
           }
         }
         list locator {
           key name;
           ordered-by user;
           leaf name {
             description "Locator entry name";
             type string {
               length "1 .. 64";
             }
           }
           uses apply-advanced;
           leaf algorithm {
             description "Algorithm associated with this locator";
             type union {
               type string {
                 pattern "<.*>|$.*";
               }
               type uint32 {
                 range "0 .. 255";
               }
             }
           }
           leaf address {
             description "Configure Locator Service for SRv6";
             type jt:ipv6prefix;
             mandatory true;
           }
           leaf block-length {
             description "Block length associated with this locator";
             type union {
               type string {
                 pattern "<.*>|$.*";
               }
               type uint32 {
                 range "0 .. 112";
               }
             }
           }
           leaf function-length {
             description "Function length associated with this locator";
             type union {
               type string {
                 pattern "<.*>|$.*";
               }
               type uint32 {
                 range "16 .. 32";
               }
             }
           }
           leaf static-function-max-entries {
             description "Static function maximum entries";
             type union {
               type string {
                 pattern "<.*>|$.*";
               }
               type uint32 {
                 range "0 .. 4294967295";
               }
             }
           }
           container micro-sid {
             presence "enable micro-sid";
             description "Enable micro SID locator";
             uses apply-advanced;
             leaf block-name {
               description "Block name of micro SID locator";
               type string {
                 length "1 .. 63";
               }
             }
             container flavor {
               description "Flavor of micro SID locator";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
               leaf none {
                 description "No flavor";
                 type empty;
               }
             }
             leaf anycast {
               description "Anycast locator";
               type empty;
             }
           }
         }
         container traceoptions {
           presence "enable traceoptions";
           description "Trace options for SRv6 process";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "srv6-oam-recv" {
                   description "Trace recv activity";
                 }
                 enum "srv6-oam-err" {
                   description "Trace error activity";
                 }
               }
             }
           }
         }
       }
     }
     leaf route-distinguisher-id {
       description "Identifier used in route distinguishers for routing instances";
       type jt:ipv4addr;
     }
     list domain-path-id {
       key name;
       ordered-by user;
       description "VRF domain id path configuration";
       max-elements 2;
       uses domain-id-type;
     }
     list rib {
       key name;
       description "Routing table options";
       leaf name {
         description "Routing table name";
         type string;
       }
       uses apply-advanced;
       container static {
         description "Static routes";
         uses apply-advanced;
         leaf rib-group {
           description "Routing table group";
           type string;
         }
         container defaults {
           description "Global route options";
           uses apply-advanced;
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           leaf explicit-null {
             description "Allows service label to be popped and will lookup nexthop-table inet6.0";
             type empty;
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         list route {
           key name;
           description "Static route";
           leaf name {
             type jt:ipprefix;
           }
           uses apply-advanced;
           leaf priority {
             description "Static route priority high/medium/low";
             type enumeration {
               enum "medium" {
                 description "Static route medium priority";
               }
               enum "low" {
                 description "Static route low priority";
               }
               enum "high" {
                 description "Static route high priority";
               }
             }
           }
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           leaf description {
             description "Static route description";
             type string {
             }
           }
           list qualified-next-hop {
             key name;
             ordered-by user;
             description "Next hop with qualifiers";
             uses qualified_nh_obj;
           }
           leaf backup-pe-group {
             description "Multicast source redundancy group";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "100 .. 255000";
                   }
                 }
                 //mandatory true;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           leaf explicit-null {
             description "Allows service label to be popped and will lookup nexthop-table inet6.0";
             type empty;
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
           list lsp-next-hop {
             key name;
             ordered-by user;
             description "LSP next hop";
             uses lsp_nh_obj;
           }
           list p2mp-lsp-next-hop {
             key name;
             ordered-by user;
             description "Point-to-multipoint LSP next hop";
             max-elements 1;
             uses lsp_nh_obj;
           }
           container spring-te-lsp-next-hop {
             description "SPRING-TE LSP next hop";
             uses springte_lsp_nh_obj;
           }
           container p2mp-ldp-next-hop {
             description "Point-to-multipoint LDP LSP next hop";
             uses p2mp_ldp_lsp_nh_obj;
           }
           list static-lsp-next-hop {
             key name;
             ordered-by user;
             description "Static LSP next hop";
             uses lsp_nh_obj;
           }
         }
         leaf protocol-instance-name {
           description "Name of protocol instance under routing instance";
           type string;
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list route-target-filter {
           key name;
           ordered-by user;
           description "Route-target-filter route";
           leaf name {
             type string {
               length "1 .. 47";
             }
           }
           uses apply-advanced;
           leaf-list neighbor {
             ordered-by user;
             description "BGP peers for filter";
             type jt:ipaddr-scoped;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
               //mandatory true;
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
               //mandatory true;
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
           //mandatory true;
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
         leaf preserve-nexthop-hierarchy {
           description "Force multipath to create List nexthop";
           type empty;
         }
       }
       container policy-multipath {
         description "Policy based multipath";
         uses apply-advanced;
         leaf-list policy {
           ordered-by user;
           description "Import policy to create policy based multipath";
           type jt:policy-algebra;
         }
         container traceoptions {
           description "Trace options";
           uses apply-advanced;
           container file {
             description "Trace file options";
             leaf filename {
               description "Name of file in which to write trace information";
               type string {
                 length "1 .. 1024";
               }
               //mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Policy-multipath route tracing.";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf preserve-nexthop-hierarchy {
           description "Enable preserved nexthop hierarchy";
           type empty;
         }
       }
       container protect {
         description "Protocol-independent protection";
         leaf core {
           description "Protect against unreachability to service-edge router";
           type empty;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container bgp-static {
         description "Routes for BGP static advertisements";
         uses apply-advanced;
         list route {
           key name;
           ordered-by user;
           description "BGP-static route";
           leaf name {
             description "IP address and optional prefix length of destination";
             type jt:ipprefix;
           }
           uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
       }
       container flow {
         description "Locally defined flow routing information";
         uses apply-advanced;
         container validation {
           description "Flow route validation options";
           presence "enable validation";
           uses flow-validation;
         }
         list route {
           key name;
           ordered-by user;
           description "Flow route";
           uses flow-route-inet6;
         }
         list security-group {
           key name;
           ordered-by user;
           description "Security groups";
           leaf name {
             description "Name of the security group";
             type string {
               length "1 .. 16";
             }
           }
           uses apply-advanced;
           list rule {
             key name;
             ordered-by user;
             description "Flow route";
             uses flow-rule-inet6;
           }
         }
         container interface-group {
           description "Interface-group for applying flow-spec filter";
           uses flow-interface-group;
         }
         leaf discard-action-for-unresolved-redir-addr {
           description "For action redirect IP if redirect address is unresolved install discard action filter";
           type empty;
         }
         choice per-route-accounting-choice {
           leaf per-route-accounting {
             description "Enable traffic accounting per flowspec route";
             type empty;
           }
           leaf no-per-route-accounting {
             description "Don't enable traffic accounting per flowspec route";
             type empty;
           }
         }
       }
       container label {
         presence "enable label";
         description "Label processing";
         uses apply-advanced;
         leaf-list allocation {
           ordered-by user;
           description "Label allocation policy";
           type jt:policy-algebra;
         }
         leaf-list substitution {
           ordered-by user;
           description "Label substitution policy";
           type jt:policy-algebra;
         }
       }
       leaf-list vpn-global-import {
         ordered-by user;
         description "Import policy for L3VPN routes to global RIB";
         type jt:policy-algebra;
       }
     }
     container label {
       presence "enable label";
       description "Label processing";
       uses apply-advanced;
       leaf-list allocation {
         ordered-by user;
         description "Label allocation policy";
         type jt:policy-algebra;
       }
       leaf-list substitution {
         ordered-by user;
         description "Label substitution policy";
         type jt:policy-algebra;
       }
     }
     leaf-list vpn-global-import {
       ordered-by user;
       description "Import policy for L3VPN routes to global RIB";
       type jt:policy-algebra;
     }
     container options {
       description "Miscellaneous options";
       uses apply-advanced;
       leaf no-send {
         description "Listen only; do not send protocol packets";
         status deprecated;
         type empty;
       }
       leaf no-resolve {
         description "Do not use DNS name resolution";
         status deprecated;
         type empty;
       }
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container resolution {
       presence "enable resolution";
       description "Route next-hop resolution options";
       uses apply-advanced;
       leaf-list tracefilter {
         ordered-by user;
         description "Filter policy";
         type jt:policy-algebra;
       }
       container traceoptions {
         description "Trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       choice preserve-nexthop-hierarchy-choice {
         leaf preserve-nexthop-hierarchy {
           description "Preserve nexthop hierarchy when installing nexthop to forwarding plane";
           type empty;
         }
         leaf no-preserve-nexthop-hierarchy {
           description "Don't preserve nexthop hierarchy when installing nexthop to forwarding plane";
           type empty;
         }
       }
       list rib {
         key name;
         ordered-by user;
         description "Routing table resolution options";
         leaf name {
           description "Routing table name";
           type string;
         }
         uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
         leaf preserve-nexthop-hierarchy {
           description "Preserve nexthop hierarchy when installing nexthop to forwarding plane";
           type empty;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
       leaf disable-auto-resolve-on-scheme-changes {
         description "Manually trigger route re-resolution on Resolution Scheme changes.";
         type empty;
       }
       list scheme {
         key name;
         ordered-by user;
         description "Nexthop resolution fallback";
         leaf name {
           description "Name the resolution scheme";
           type string;
         }
         uses apply-advanced;
         leaf-list resolution-ribs {
           ordered-by user;
           description "Routing tables to use for nexthop resolution, in fallback order";
           type string;
         }
         leaf mapping-community {
           description "Community on route that maps to this resolution scheme";
           type string;
           mandatory true;
         }
       }
     }
     container interface-routes {
       description "Define routing table groups for interface routes";
       uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         uses apply-advanced;
         leaf-list import {
           ordered-by user;
           description "Import policy";
           type jt:policy-algebra;
         }
         container export {
           description "Control exportability of local routes";
           uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     container traceoptions {
       description "Global routing protocol trace options";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "read-route" {
               description "Read route events tracing";
             }
             enum "events" {
               description "Trace-events events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container topologies {
       description "Define routing topologies";
       uses apply-advanced;
       list family {
         key name;
         ordered-by user;
         description "Address family";
         leaf name {
           type enumeration {
             enum "inet" {
               description "IPv4 family";
             }
             enum "inet6" {
               description "IPv6 family";
             }
           }
         }
         uses apply-advanced;
         list topology {
           key name;
           ordered-by user;
           description "Topology information";
           leaf name {
             description "Topology name";
             type string {
             }
           }
           uses apply-advanced;
           leaf table-id {
             description "Table-id";
             type union {
               type uint16;
               type string {
                 pattern "<.*>|$.*";
               }
             }
           }
         }
       }
     }
     leaf router-id {
       description "Router identifier";
       type jt:ipv4addr;
     }
     leaf route-distinguisher-id-use-router-id {
       description "Use Master instance Router-ID as route-distinguisher-id";
       type empty;
     }
     container autonomous-system {
       description "Autonomous system number";
       uses apply-advanced;
       leaf as-number {
         description " Autonomous system number in plain number or 'higher 16bits'.'Lower 16 bits' (asdot notation) format";
         type string {
         }
         //mandatory true;
       }
       leaf loops {
         description "Maximum number of times this AS can be in an AS path";
         type union {
           type string {
             pattern "<.*>|$.*";
           }
           type int32 {
             range "1 .. 10";
           }
         }
       }
       leaf asdot-notation {
         description "Use AS-Dot notation to display true 4 byte AS numbers";
         type empty;
       }
       container independent-domain {
         presence "enable independent-domain";
         description "Independent autonomous-system domain from master instance";
         uses apply-advanced;
         container no-attrset {
           presence "enable no-attrset";
           description "Do not tunnel ce bgp attributes across provider network";
         }
       }
     }
     container confederation {
       description "Confederation autonomous system number";
       leaf confederation-as {
         description " Autonomous system number in plain number or 'higher 16bits'.'Lower 16 bits' (asdot notation) format";
         type string {
         }
         //mandatory true;
       }
       leaf-list members {
         ordered-by user;
         description " Autonomous system number in plain number or 'higher 16bits'.'Lower 16 bits' (asdot notation) format";
         type string;
       }
     }
     leaf ipv6-router-id {
       description "IPv6 router identifier";
       type string;
     }
     container graceful-restart {
       presence "enable graceful-restart";
       description "Graceful or hitless routing restart options";
       uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
     container flow {
       description "Locally defined flow routing information";
       uses apply-advanced;
       leaf firewall-install-disable {
         description "Disable installing flowspec firewall filters in dfwd ";
         type empty;
       }
       choice per-route-accounting-choice {
         leaf per-route-accounting {
           description "Enable traffic accounting per flowspec route";
           type empty;
         }
         leaf no-per-route-accounting {
           description "Don't enable traffic accounting per flowspec route";
           type empty;
         }
       }
       container validation {
         description "Flow route validation options";
         presence "enable validation";
         uses flow-validation;
       }
       container interface-group {
         description "Interface-group for applying flow-spec filter";
         uses flow-interface-group;
       }
       list route {
         key name;
         ordered-by user;
         description "Flow route";
         uses flow-route-inet;
       }
       leaf term-order {
         description "Term evaluation order for flow routes";
         type enumeration {
           enum "legacy" {
             description "Legacy term order (default)";
           }
           enum "standard" {
             description "RFC compliant term order";
           }
         }
       }
       leaf discard-action-for-unresolved-redir-addr {
         description "For action redirect IP if redirect address is unresolved install discard action filter";
         type empty;
       }
       list security-group {
         key name;
         ordered-by user;
         description "Security groups";
         leaf name {
           description "Name of the security group";
           type string {
             length "1 .. 16";
           }
         }
         uses apply-advanced;
         list rule {
           key name;
           ordered-by user;
           description "Flow route";
           uses flow-rule-inet;
         }
       }
     }
     leaf no-soft-core {
       description "Disable soft assert to generate core and just log the event";
       type empty;
     }
     leaf med-igp-update-interval {
       description "Delay (in minutes) in updating MED IGP for bgp groups with 'delay-med-update' ";
       type union {
         type string {
           pattern "<.*>|$.*";
         }
         type uint32 {
           range "10 .. 600";
         }
       }
     }
     container bmp {
       presence "enable bmp";
       description "BGP Monitoring Protocol (BMP) configuration";
       uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         type enumeration {
           enum "allow-without-tcpao" {
             description "Allow the connection establishment without TCP-AO";
           }
         }
       }
       leaf authentication-key-chain {
         description "Key chain name";
         type string {
           length "1 .. 128";
         }
       }
       container hold-down {
         presence "enable hold-down";
         leaf hold-down-time {
           description "Prevent re-establishment for this time";
           units "seconds";
           type union {
             type string {
               pattern "<.*>|$.*";
             }
             type uint32 {
               range "30 .. 65535";
             }
           }
           mandatory true;
         }
         leaf flaps {
           description "Number of flaps before damping";
           type union {
             type string {
               pattern "<.*>|$.*";
             }
             type uint32 {
               range "2 .. 10";
             }
           }
           mandatory true;
         }
         leaf period {
           description "Time period for flaps";
           units "seconds";
           type union {
             type string {
               pattern "<.*>|$.*";
             }
             type uint32 {
               range "30 .. 65535";
             }
           }
           mandatory true;
         }
       }
       leaf initiation-message {
         description "User string sent with the initiation message";
         type string {
           length "1 .. 255";
         }
       }
       leaf local-address {
         description "Address of local end of BMP session";
         type jt:ipaddr;
       }
       leaf local-port {
         description "Local port for listening";
         type union {
           type string {
             pattern "<.*>|$.*";
           }
           type uint32 {
             range "1024 .. 65535";
           }
         }
       }
       leaf connection-mode {
         description "Specify active or passive";
         type enumeration {
           enum "active" {
             description "Initiate the connection";
           }
           enum "passive" {
             description "Listen for the connection";
           }
         }
       }
       leaf priority {
         description "Relative dispatch priority";
         type enumeration {
           enum "low" {
             description "Lowest priority";
           }
           enum "medium" {
             description "Medium priority";
           }
           enum "high" {
             description "Highest priority";
           }
         }
       }
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           type empty;
         }
         container loc-rib {
           presence "enable loc-rib";
           description "Send local-rib route monitoring messages";
           uses apply-advanced;
           leaf-list rib-filter {
             ordered-by user;
             description "Policy for RIB filtering";
             type jt:policy-algebra;
           }
           leaf-list route-filter {
             ordered-by user;
             description "Policy for route filtering";
             type jt:policy-algebra;
           }
         }
         container pre-policy {
           presence "enable pre-policy";
           description "Send pre policy route monitoring messages";
           leaf exclude-non-feasible {
             description "Exclude looped routes, etc";
             type empty;
           }
         }
         container post-policy {
           presence "enable post-policy";
           description "Send post policy route monitoring messages";
           leaf exclude-non-eligible {
             description "Exclude unresolved routes, etc.";
             type empty;
           }
         }
         container rib-out {
           presence "enable rib-out";
           description "Send adj-ribs-out route monitoring messages";
           leaf pre-policy {
             description "Send pre-policy adj-ribs-out route monitoring messages";
             type empty;
           }
           leaf post-policy {
             description "Send post-policy adj-ribs-out route monitoring messages";
             type empty;
           }
         }
       }
       leaf max-loc-rib-buffer-count {
         description "Max number of loc-rib outstanding buffers before blocking";
         type union {
           type string {
             pattern "<.*>|$.*";
           }
           type uint32 {
             range "1 .. 50";
           }
         }
       }
       leaf station-address {
         description "Address/name of monitoring station";
         type jt:ipaddr;
       }
       leaf routing-instance {
         description "Routing-instance through which BMP station is reachable";
         type string;
       }
       leaf station-port {
         description "Port of monitoring station";
         type union {
           type string {
             pattern "<.*>|$.*";
           }
           type uint32 {
             range "1 .. 65535";
           }
         }
       }
       leaf statistics-timeout {
         description "Statistics message timer, 15-65535, or 0 for no messages";
         units "seconds";
         type union {
           type string {
             pattern "<.*>|$.*";
           }
           type uint32 {
             range "0 .. 65535";
           }
         }
       }
       leaf keep-advertisement-state {
         description "Keep BMP advertisement state";
         type empty;
       }
       leaf in-memory-profiling {
         description "Turn on in-memory profiling to collect time-series data";
         type empty;
       }
       leaf bmp-server {
         description "BMP server";
         type empty;
       }
       leaf max-clients {
         description "Max number of BMP server clients";
         type union {
           type string {
             pattern "<.*>|$.*";
           }
           type uint32 {
             range "1 .. 500";
           }
         }
       }
       container traceoptions {
         description "Trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Trace flag information";
           leaf name {
             type enumeration {
               enum "packets" {
                 description "Trace all messages";
               }
               enum "up" {
                 description "Trace up messages";
               }
               enum "down" {
                 description "Trace down messages";
               }
               enum "statistics" {
                 description "Trace statistics messages";
               }
               enum "route-monitoring" {
                 description "Trace route monitoring messages";
               }
               enum "event" {
                 description "Trace major events, station establishment, errors, events";
               }
               enum "error" {
                 description "Trace error conditions";
               }
               enum "write" {
                 description "Trace writing of messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container bmp-loc-rib-add-path {
         description "Advertise multiple paths for a prefix";
         presence "enable bmp-loc-rib-add-path";
         uses bmp-loc-rib-apath-options;
       }
       container kafka {
         presence "enable kafka";
         description "Kafka broker configuration";
         uses apply-advanced;
         leaf broker-address {
           description "Kafka broker address";
           type string;
           mandatory true;
         }
         container producer {
           presence "enable producer";
           description "Producer of a topic";
           uses apply-advanced;
           leaf topic-metadata {
             description "Metadata string for all messages";
             type string {
               length "1 .. 255";
             }
           }
         }
       }
       list station {
         key name;
         description "Define a BMP station";
         leaf name {
           description "Station name";
           type string;
         }
         uses apply-advanced;
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         container hold-down {
           presence "enable hold-down";
           leaf hold-down-time {
             description "Prevent re-establishment for this time";
             units "seconds";
             type union {
               type string {
                 pattern "<.*>|$.*";
               }
               type uint32 {
                 range "30 .. 65535";
               }
             }
             mandatory true;
           }
           leaf flaps {
             description "Number of flaps before damping";
             type union {
               type string {
                 pattern "<.*>|$.*";
               }
               type uint32 {
                 range "2 .. 10";
               }
             }
             mandatory true;
           }
           leaf period {
             description "Time period for flaps";
             units "seconds";
             type union {
               type string {
                 pattern "<.*>|$.*";
               }
               type uint32 {
                 range "30 .. 65535";
               }
             }
             mandatory true;
           }
         }
         leaf initiation-message {
           description "User string sent with the initiation message";
           type string {
             length "1 .. 255";
           }
         }
         leaf local-address {
           description "Address of local end of BMP session";
           type jt:ipaddr;
         }
         leaf local-port {
           description "Local port for listening";
           type union {
             type string {
               pattern "<.*>|$.*";
             }
             type uint32 {
               range "1024 .. 65535";
             }
           }
         }
         leaf connection-mode {
           description "Specify active or passive";
           type enumeration {
             enum "active" {
               description "Initiate the connection";
             }
             enum "passive" {
               description "Listen for the connection";
             }
           }
         }
         leaf priority {
           description "Relative dispatch priority";
           type enumeration {
             enum "low" {
               description "Lowest priority";
             }
             enum "medium" {
               description "Medium priority";
             }
             enum "high" {
               description "Highest priority";
             }
           }
         }
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             type empty;
           }
           container loc-rib {
             presence "enable loc-rib";
             description "Send local-rib route monitoring messages";
             uses apply-advanced;
             leaf-list rib-filter {
               ordered-by user;
               description "Policy for RIB filtering";
               type jt:policy-algebra;
             }
             leaf-list route-filter {
               ordered-by user;
               description "Policy for route filtering";
               type jt:policy-algebra;
             }
           }
           container pre-policy {
             presence "enable pre-policy";
             description "Send pre policy route monitoring messages";
             leaf exclude-non-feasible {
               description "Exclude looped routes, etc";
               type empty;
             }
           }
           container post-policy {
             presence "enable post-policy";
             description "Send post policy route monitoring messages";
             leaf exclude-non-eligible {
               description "Exclude unresolved routes, etc.";
               type empty;
             }
           }
           container rib-out {
             presence "enable rib-out";
             description "Send adj-ribs-out route monitoring messages";
             leaf pre-policy {
               description "Send pre-policy adj-ribs-out route monitoring messages";
               type empty;
             }
             leaf post-policy {
               description "Send post-policy adj-ribs-out route monitoring messages";
               type empty;
             }
           }
         }
         leaf max-loc-rib-buffer-count {
           description "Max number of loc-rib outstanding buffers before blocking";
           type union {
             type string {
               pattern "<.*>|$.*";
             }
             type uint32 {
               range "1 .. 50";
             }
           }
         }
         leaf station-address {
           description "Address/name of monitoring station";
           type jt:ipaddr;
         }
         leaf routing-instance {
           description "Routing-instance through which BMP station is reachable";
           type string;
         }
         leaf station-port {
           description "Port of monitoring station";
           type union {
             type string {
               pattern "<.*>|$.*";
             }
             type uint32 {
               range "1 .. 65535";
             }
           }
         }
         leaf statistics-timeout {
           description "Statistics message timer, 15-65535, or 0 for no messages";
           units "seconds";
           type union {
             type string {
               pattern "<.*>|$.*";
             }
             type uint32 {
               range "0 .. 65535";
             }
           }
         }
         leaf keep-advertisement-state {
           description "Keep BMP advertisement state";
           type empty;
         }
         leaf in-memory-profiling {
           description "Turn on in-memory profiling to collect time-series data";
           type empty;
         }
         leaf bmp-server {
           description "BMP server";
           type empty;
         }
         leaf max-clients {
           description "Max number of BMP server clients";
           type union {
             type string {
               pattern "<.*>|$.*";
             }
             type uint32 {
               range "1 .. 500";
             }
           }
         }
         container traceoptions {
           description "Trace options";
           uses apply-advanced;
           container file {
             description "Trace file options";
             leaf filename {
               description "Name of file in which to write trace information";
               type string {
                 length "1 .. 1024";
               }
               //mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Trace flag information";
             leaf name {
               type enumeration {
                 enum "packets" {
                   description "Trace all messages";
                 }
                 enum "up" {
                   description "Trace up messages";
                 }
                 enum "down" {
                   description "Trace down messages";
                 }
                 enum "statistics" {
                   description "Trace statistics messages";
                 }
                 enum "route-monitoring" {
                   description "Trace route monitoring messages";
                 }
                 enum "event" {
                   description "Trace major events, station establishment, errors, events";
                 }
                 enum "error" {
                   description "Trace error conditions";
                 }
                 enum "write" {
                   description "Trace writing of messages";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         container bmp-loc-rib-add-path {
           description "Advertise multiple paths for a prefix";
           presence "enable bmp-loc-rib-add-path";
           uses bmp-loc-rib-apath-options;
         }
         container kafka {
           presence "enable kafka";
           description "Kafka broker configuration";
           uses apply-advanced;
           leaf broker-address {
             description "Kafka broker address";
             type string;
             mandatory true;
           }
           container producer {
             presence "enable producer";
             description "Producer of a topic";
             uses apply-advanced;
             leaf topic-metadata {
               description "Metadata string for all messages";
               type string {
                 length "1 .. 255";
               }
             }
           }
         }
       }
     }
     leaf bgp-orf-cisco-mode {
       description "Using BGP ORF capability code 130 and Prefix ORF type 128";
       type empty;
     }
     leaf highwatermark-log-interval {
       description "High watermark log interval (default 30 seconds)";
       units "seconds";
       type union {
         type string {
           pattern "<.*>|$.*";
         }
         type uint32 {
           range "5 .. 1200";
         }
       }
     }
     leaf time-averaged-watermark-interval {
       description "For calculating average watermark";
       units "days";
       type union {
         type string {
           pattern "<.*>|$.*";
         }
         type uint32 {
           range "1 .. 15";
         }
       }
     }
     container ppm {
       presence "enable ppm";
       description "Set periodic packet management properties";
       uses apply-advanced;
       leaf delegate-processing {
         description "Enable distribution of PPM sessions";
         status deprecated;
         type empty;
       }
       leaf no-delegate-processing {
         description "Disable PPM sessions distribution";
         type empty;
       }
       leaf bfd-redirect-rule-delay {
         description "Time to wait after installing redirect rule for BFD sessions";
         type union {
           type string {
             pattern "<.*>|$.*";
           }
           type uint32 {
             range "1 .. 120";
           }
         }
       }
       leaf redistribution-timer {
         description "Time to wait after switchover before starting timers";
         type union {
           type string {
             pattern "<.*>|$.*";
           }
           type uint32 {
             range "1 .. 120";
           }
         }
       }
     }
     leaf no-bfd-triggered-local-repair {
       description "Disable bfd triggered local repair";
       type empty;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container static {
       description "Static routes";
       uses apply-advanced;
       leaf rib-group {
         description "Routing table group";
         type string;
       }
       container defaults {
         description "Global route options";
         uses apply-advanced;
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         leaf explicit-null {
           description "Allows service label to be popped and will lookup nexthop-table inet6.0";
           type empty;
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       list route {
         key name;
         description "Static route";
         leaf name {
           type jt:ipprefix;
         }
         uses apply-advanced;
         leaf priority {
           description "Static route priority high/medium/low";
           type enumeration {
             enum "medium" {
               description "Static route medium priority";
             }
             enum "low" {
               description "Static route low priority";
             }
             enum "high" {
               description "Static route high priority";
             }
           }
         }
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         leaf description {
           description "Static route description";
           type string {
           }
         }
         list qualified-next-hop {
           key name;
           ordered-by user;
           description "Next hop with qualifiers";
           uses qualified_nh_obj;
         }
         leaf backup-pe-group {
           description "Multicast source redundancy group";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "100 .. 255000";
                 }
               }
               //mandatory true;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         leaf explicit-null {
           description "Allows service label to be popped and will lookup nexthop-table inet6.0";
           type empty;
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
         list lsp-next-hop {
           key name;
           ordered-by user;
           description "LSP next hop";
           uses lsp_nh_obj;
         }
         list p2mp-lsp-next-hop {
           key name;
           ordered-by user;
           description "Point-to-multipoint LSP next hop";
           max-elements 1;
           uses lsp_nh_obj;
         }
         container spring-te-lsp-next-hop {
           description "SPRING-TE LSP next hop";
           uses springte_lsp_nh_obj;
         }
         container p2mp-ldp-next-hop {
           description "Point-to-multipoint LDP LSP next hop";
           uses p2mp_ldp_lsp_nh_obj;
         }
         list static-lsp-next-hop {
           key name;
           ordered-by user;
           description "Static LSP next hop";
           uses lsp_nh_obj;
         }
       }
       leaf protocol-instance-name {
         description "Name of protocol instance under routing instance";
         type string;
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
       list route-target-filter {
         key name;
         ordered-by user;
         description "Route-target-filter route";
         leaf name {
           type string {
             length "1 .. 47";
           }
         }
         uses apply-advanced;
         leaf-list neighbor {
           ordered-by user;
           description "BGP peers for filter";
           type jt:ipaddr-scoped;
         }
         leaf-list group {
           ordered-by user;
           description "BGP groups for filter";
           type string;
         }
         leaf local {
           description "Locally originated filter";
           type empty;
         }
       }
     }
     list martians {
       key "address choice-ident choice-value";
       ordered-by user;
       description "Invalid routes";
       uses martian_type;
     }
     container aggregate {
       description "Coalesced routes";
       uses rib_aggregate_type;
     }
     container generate {
       description "Route of last resort";
       uses rib_aggregate_type;
     }
     choice maximum-paths-type {
       case case_1 {
         container maximum-routes {
           description "Maximum number of routes";
           status deprecated;
           leaf limit {
             description "Maximum number of routes";
             type union {
               type string {
                 pattern "<.*>|$.*";
               }
               type uint32 {
                 range "1 .. 4294967295";
               }
             }
             //mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       case case_2 {
         container maximum-paths {
           description "Maximum number of paths";
           leaf limit {
             description "Maximum number of paths";
             type union {
               type string {
                 pattern "<.*>|$.*";
               }
               type uint32 {
                 range "1 .. 4294967295";
               }
             }
             //mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     container maximum-prefixes {
       description "Maximum number of prefixes";
       leaf limit {
         description "Maximum number of prefixes";
         type union {
           type string {
             pattern "<.*>|$.*";
           }
           type uint32 {
             range "1 .. 4294967295";
           }
         }
         //mandatory true;
       }
       choice log_type {
         case case_1 {
           leaf threshold {
             description "Percentage of limit at which to start generating warnings";
             type union {
               type string {
                 pattern "<.*>|$.*";
               }
               type uint32 {
                 range "1 .. 100";
               }
             }
           }
         }
         case case_2 {
           leaf log-only {
             description "Generate warning messages only";
             type empty;
           }
         }
       }
       leaf log-interval {
         description "Minimum interval between log messages";
         units "seconds";
         type union {
           type string {
             pattern "<.*>|$.*";
           }
           type uint32 {
             range "5 .. 86400";
           }
         }
       }
     }
     container multipath {
       presence "enable multipath";
       description "Protocol-independent load balancing";
       uses apply-advanced;
       container vpn-unequal-cost {
         presence "enable vpn-unequal-cost";
         description "Include VPN routes with unequal IGP metrics";
         leaf equal-external-internal {
           description "Include external and internal VPN routes";
           type empty;
         }
       }
       leaf as-path-compare {
         description "Compare AS path sequences in addition to AS path length";
         type empty;
       }
       leaf preserve-nexthop-hierarchy {
         description "Force multipath to create List nexthop";
         type empty;
       }
     }
     container policy-multipath {
       description "Policy based multipath";
       uses apply-advanced;
       leaf-list policy {
         ordered-by user;
         description "Import policy to create policy based multipath";
         type jt:policy-algebra;
       }
       container traceoptions {
         description "Trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Policy-multipath route tracing.";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf preserve-nexthop-hierarchy {
         description "Enable preserved nexthop hierarchy";
         type empty;
       }
     }
     container access {
       description "Access routes";
       uses apply-advanced;
       list route {
         key name;
         ordered-by user;
         description "Access route";
         leaf name {
           description "IP address of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
         leaf metric {
           description "Metric value";
           type union {
             type string {
               pattern "<.*>|$.*";
             }
             type uint32 {
               range "1 .. 255";
             }
           }
         }
         leaf preference {
           description "Preference value";
           type union {
             type uint32;
             type string {
               pattern "<.*>|$.*";
             }
           }
         }
         leaf tag {
           description "Tag string";
           type union {
             type uint32;
             type string {
               pattern "<.*>|$.*";
             }
           }
         }
         leaf tag2 {
           description "Tag2 string";
           type union {
             type uint32;
             type string {
               pattern "<.*>|$.*";
             }
           }
         }
       }
     }
     container access-internal {
       description "Access-internal routes";
       uses apply-advanced;
       list route {
         key name;
         ordered-by user;
         description "Access-internal route";
         leaf name {
           description "IP address and optional prefix length of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
       }
     }
     container bgp-static {
       description "Routes for BGP static advertisements";
       uses apply-advanced;
       list route {
         key name;
         ordered-by user;
         description "BGP-static route";
         leaf name {
           description "IP address and optional prefix length of destination";
           type jt:ipprefix;
         }
         uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
     }
     list rib-groups {
       key name;
       ordered-by user;
       description "Group of routing tables";
       uses rpd_rib_group_type;
     }
     leaf-list instance-import {
       ordered-by user;
       description "Import policy for instance RIBs";
       type jt:policy-algebra;
     }
     leaf-list instance-export {
       ordered-by user;
       description "Export policy for instance RIBs";
       type jt:policy-algebra;
     }
     leaf-list pre-export-filter {
       ordered-by user;
       description "Pre-export filter for protocol export-policy";
       type jt:policy-algebra;
     }
     container auto-export {
       presence "enable auto-export";
       description "Export routes between routing instances";
       uses apply-advanced;
       choice enable-disable {
         case case_1 {
           leaf disable {
             description "Disable auto-export";
             type empty;
           }
         }
       }
       container traceoptions {
         description "Trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "export" {
                 description "Export processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container family {
         container inet {
           description "IPv4 parameters";
           uses export-af-obj;
         }
         container inet6 {
           description "IPv6 parameters";
           uses export-af-obj;
         }
         container iso {
           description "ISO parameters";
           uses export-af-obj;
         }
       }
     }
     container transport-class {
       presence "enable transport-class";
       description "Transport layer options";
       uses apply-advanced;
       leaf auto-create {
         description "Auto create on color discovery";
         type empty;
       }
       container fallback {
         description "Service routes resolution fallback";
         uses apply-advanced;
         leaf none {
           description "Resolve associated service-routes using this transport-class tunnels only";
           type empty;
         }
       }
       list name {
         key name;
         ordered-by user;
         description "Transport layer collecting Tunnels with similar characteristics";
         leaf name {
           description "Transport class name";
           type string;
         }
         uses apply-advanced;
         leaf color {
           description "Color(0..4294967295). This auto derives the Mapping Community and Route Target";
           type union {
             type uint32;
             type string {
               pattern "<.*>|$.*";
             }
           }
         }
         container fallback {
           description "Service routes resolution fallback";
           uses apply-advanced;
           leaf none {
             description "Resolve associated service-routes using this transport-class tunnels only";
             type empty;
           }
         }
         container tunnel-egress {
           description "Tunnel-Egress endpoint origination";
           uses apply-advanced;
           list end-point {
             key name;
             ordered-by user;
             description "Configure Tunnel-Egress endpoints";
             leaf name {
               description "Address of Tunnel egress endpoint";
               type jt:ipaddr;
             }
             uses apply-advanced;
             leaf-list import {
               ordered-by user;
               description "Import policy to set attributes";
               type jt:policy-algebra;
             }
           }
         }
       }
       container any-class {
         description "Predefined transport class collecting Tunnels of all transport classes";
         uses apply-advanced;
         leaf color {
           description "Color 32bit value. This auto derives the Mapping Community.";
           type union {
             type uint32;
             type string {
               pattern "<.*>|$.*";
             }
           }
         }
         container fallback {
           description "Service routes resolution fallback";
           uses apply-advanced;
           leaf none {
             description "Resolve associated service-routes using this transport-class tunnels only";
             type empty;
           }
         }
       }
       container best-effort {
         description "Best effort transport class";
         uses apply-advanced;
         leaf color {
           description "Color 32 bit value";
           type union {
             type uint32;
             type string {
               pattern "<.*>|$.*";
             }
           }
         }
         container fallback {
           description "Service routes resolution fallback";
           uses apply-advanced;
           leaf none {
             description "Resolve associated service-routes using this transport-class tunnels only";
             type empty;
           }
         }
       }
     }
     container dynamic-tunnels {
       description "Dynamic tunnel definitions";
       uses apply-advanced;
       list tunnel-attributes {
         key name;
         ordered-by user;
         description "Dynamic tunnel attributes definition";
         leaf name {
           description "Dynamic Tunnel attribute name";
           type string {
           }
         }
         uses apply-advanced;
         leaf dynamic-tunnel-source-prefix {
           description "Tunnel source address";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
             enum "IPIP" {
               description "Tunnel type IPIP";
             }
           }
           mandatory true;
         }
         leaf dynamic-tunnel-mtu {
           description "Dynamic Tunnel MTU value";
           type union {
             type string {
               pattern "<.*>|$.*";
             }
             type uint32 {
               range "296 .. 9232";
             }
           }
         }
         leaf dynamic-tunnel-gre-key {
           description "RFC 2890 Dynamic Tunnel GRE Key";
           type union {
             type string {
               pattern "<.*>|$.*";
             }
             type uint32 {
               range "1 .. 4294967295";
             }
           }
         }
         leaf dynamic-tunnel-anchor-pfe {
           description "Dynamic Tunnel anchor PFE name of format pfe-x/y/z";
           type string {
           }
         }
         leaf dynamic-tunnel-anti-spoof {
           type enumeration {
             enum "on" {
               description "Enable antispoofing check. Default is enabled";
             }
             enum "off" {
               description "Disable antispoofing check";
             }
           }
         }
         leaf dynamic-tunnel-reassembly {
           type enumeration {
             enum "on" {
               description "Enable reassembly check. Default is disabled";
             }
             enum "off" {
               description "Disable reassembly check";
             }
           }
         }
         leaf dynamic-tunnel-ttl {
           description "Dynamic Tunnel TTL value";
           type union {
             type string {
               pattern "<.*>|$.*";
             }
             type uint32 {
               range "1 .. 255";
             }
           }
         }
         leaf dynamic-tunnel-forwarding-class {
           description "Dynamic Tunnel forwarding class name";
           type string {
             length "1 .. 64";
           }
         }
         leaf dynamic-tunnel-payload-port-profile {
           description "Dynamic Tunnel UDP payload port profile";
           type string;
         }
         leaf dynamic-tunnel-propagate-dscp {
           description "Dynamic Tunnel Propagate DSCP";
           type empty;
         }
         leaf dynamic-tunnel-propagate-ecn {
           description "Dynamic Tunnel Propagate ECN";
           type empty;
         }
       }
       container forwarding-rib {
         presence "enable forwarding-rib";
         description "Forwarding routing table for dynamic-tunnel";
         uses apply-advanced;
         container inet.0 {
           presence "enable inet.0";
           description "Rib table inet.0";
           uses apply-advanced;
           leaf-list inet-import {
             ordered-by user;
             description "Import policy for V4 dynamic-tunnel";
             type jt:policy-algebra;
           }
         }
         container inet6.0 {
           presence "enable inet6.0";
           description "Rib table inet6.0";
           uses apply-advanced;
           leaf-list inet6-import {
             ordered-by user;
             description "Import policy for V6 dynamic-tunnel";
             type jt:policy-algebra;
           }
         }
       }
       container statistics {
         description "Fetch traffic statistics for  dynamic tunnels";
         uses apply-advanced;
         leaf interval {
           description "Time after which statistics has to be fetched";
           units "seconds";
           type union {
             type string {
               pattern "<.*>|$.*";
             }
             type uint16 {
               range "1 .. 65535";
             }
           }
           //mandatory true;
         }
       }
       container traceoptions {
         description "Trace options";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "tunnel-event" {
                 description "Trace create, delete, up, down event for nh based tunnel";
               }
               enum "flash-event" {
                 description "Trace flash event for tunnel forwarding route";
               }
               enum "stats-job" {
                 description "Trace taffic statistics job related stuff";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf v4ov6 {
         description "Enable dynamic tunnel V4oV6 mode";
         type enumeration {
           enum "ipv6-anycast-source-duplication" {
             description "Enable full resolved nh base source-tunnel";
           }
         }
       }
       list gre {
         key name;
         ordered-by user;
         description "Enable dynamic gre tunnel mode";
         leaf name {
           description "Enable dynamic tunnel gre mode";
           type enumeration {
             enum "next-hop-based-tunnel" {
               description "Enable nh base dynamic-tunnel";
             }
             enum "full-resolved-next-hop-based-tunnel" {
               description "Enable full resolved nh base dynamic-tunnel";
             }
             enum "chain-full-resolve-next-hop-based-tunnel" {
               description "Enable chain full resolved nh base dynamic-tunnel";
             }
           }
         }
         uses apply-advanced;
       }
       container signal-tunnel-preference {
         presence "enable signal-tunnel-preference";
         description "Set tunnel preference for signalled tunnels";
         uses apply-advanced;
         leaf gre {
           description "Preference of GRE signalled tunnels";
           type union {
             type string {
               pattern "<.*>|$.*";
             }
             type uint32 {
               range "1 .. 10";
             }
           }
         }
         leaf udp {
           description "Preference of UDP signalled tunnels";
           type union {
             type string {
               pattern "<.*>|$.*";
             }
             type uint32 {
               range "1 .. 10";
             }
           }
         }
         leaf ipip {
           description "Preference of IPIP signalled tunnels";
           type union {
             type string {
               pattern "<.*>|$.*";
             }
             type uint32 {
               range "1 .. 10";
             }
           }
         }
       }
       list dynamic-tunnel {
         key name;
         ordered-by user;
         uses dynamic_tunnel_type;
       }
     }
     container forwarding-table {
       uses forwarding-table-type;
     }
     container fate-sharing {
       description "Fate-sharing links or nodes database";
       uses apply-advanced;
       list group {
         key name;
         ordered-by user;
         description "Group of objects sharing common characteristics";
         leaf name {
           description "Name of object groups sharing the same fate";
           type string {
           }
         }
         uses apply-advanced;
         leaf cost {
           description "Cost value";
           type union {
             type string {
               pattern "<.*>|$.*";
             }
             type uint32 {
               range "1 .. 65535";
             }
           }
         }
         leaf use-for-post-convergence-lfa {
           description "Use this fate-sharing group as a constraint for post-convergence-lfa";
           type empty;
         }
         list from {
           key name;
           uses fate_sharing_links;
         }
       }
     }
     container programmable-rpd {
       description "RPD Server module management options";
       uses programmable-rpd-type;
     }
     container validation {
       description "Define Route validation";
       uses apply-advanced;
       container traceoptions {
         description "Trace options for route validation";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errored packets";
               }
               enum "packets" {
                 description "Trace all I/O packets";
               }
               enum "keepalive" {
                 description "Trace keepalive packets";
               }
               enum "update" {
                 description "Trace update packets";
               }
               enum "nsr-synchronization" {
                 description "Trace NSR synchronization events";
               }
               enum "state" {
                 description "Trace state transitions";
               }
               enum "policy" {
                 description "Trace policy processing";
               }
               enum "task" {
                 description "Trace routing protocol task processing";
               }
               enum "timer" {
                 description "Trace routing protocol timer processing";
               }
               enum "client" {
                 description "Trace route validation client events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf source-file {
         description "Specify a local file to read data set";
         type string;
       }
       leaf-list notification-rib {
         ordered-by user;
         description "Define routing tables that get notified upon validation state change";
         type string;
       }
       list group {
         key name;
         description "Define a group of sessions";
         leaf name {
           description "Group name";
           type string;
         }
         uses apply-advanced;
         leaf authentication-algorithm {
           description "Authentication algorithm name";
           type enumeration {
             enum "ao" {
               description "TCP authentication option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         leaf max-sessions {
           description "Maximum connected session in this group";
           type union {
             type string {
               pattern "<.*>|$.*";
             }
             type uint32 {
               range "1 .. 63";
             }
           }
         }
         list session {
           key name;
           description "Configure a session";
           leaf name {
             type jt:ipaddr;
           }
           uses apply-advanced;
           container traceoptions {
             description "Trace options for route validation";
             uses apply-advanced;
             container file {
               description "Trace file options";
               leaf filename {
                 description "Name of file in which to write trace information";
                 type string {
                   length "1 .. 1024";
                 }
                 //mandatory true;
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "error" {
                     description "Trace errored packets";
                   }
                   enum "packets" {
                     description "Trace all I/O packets";
                   }
                   enum "keepalive" {
                     description "Trace keepalive packets";
                   }
                   enum "update" {
                     description "Trace update packets";
                   }
                   enum "state" {
                     description "Trace state transitions";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf authentication-algorithm {
             description "Authentication algorithm name";
             type enumeration {
               enum "ao" {
                 description "TCP authentication option";
               }
             }
           }
           leaf tcpao-auth-mismatch {
             description "Continue without TCP-AO if any one TCP endpoint does not have TCP-AO configured";
             type enumeration {
               enum "allow-without-tcpao" {
                 description "Allow the connection establishment without TCP-AO";
               }
             }
           }
           leaf authentication-key-chain {
             description "Key chain name";
             type string {
               length "1 .. 128";
             }
           }
           leaf database {
             description "Named database in this instance to install validation entries";
             type string;
           }
           leaf refresh-time {
             description "Interval between keepalive packet transmissions";
             units "seconds";
             type union {
               type string {
                 pattern "<.*>|$.*";
               }
               type uint32 {
                 range "1 .. 1800";
               }
             }
           }
           leaf hold-time {
             description "Time after which the session is declared down.";
             units "seconds";
             type union {
               type string {
                 pattern "<.*>|$.*";
               }
               type uint32 {
                 range "10 .. 3600";
               }
             }
           }
           leaf record-lifetime {
             description "Lifetime of route validation records";
             units "seconds";
             type union {
               type string {
                 pattern "<.*>|$.*";
               }
               type uint32 {
                 range "60 .. 604800";
               }
             }
           }
           leaf preference {
             description "Preference for session establishment";
             type union {
               type string {
                 pattern "<.*>|$.*";
               }
               type uint32 {
                 range "1 .. 255";
               }
             }
           }
           leaf port {
             description "Portnumber to connect";
             type union {
               type string {
                 pattern "<.*>|$.*";
               }
               type uint16 {
                 range "1 .. 65535";
               }
             }
           }
           leaf local-address {
             type jt:ipaddr;
           }
         }
       }
       container static {
         description "Define static route validation record";
         uses apply-advanced;
         list record {
           key name;
           description "Static route validation record";
           leaf name {
             type jt:ipprefix;
           }
           uses apply-advanced;
           list maximum-length {
             key name;
             ordered-by user;
             leaf name {
               description "Maximum prefix-length for route validation record";
               type union {
                 type string {
                   pattern "<.*>|$.*";
                 }
                 type uint32 {
                   range "1 .. 128";
                 }
               }
             }
             uses apply-advanced;
             list origin-autonomous-system {
               key name;
               ordered-by user;
               leaf name {
                 description "Legitimate Origin Autonomous System";
                 type union {
                   type uint32;
                   type string {
                     pattern "<.*>|$.*";
                   }
                 }
               }
               uses apply-advanced;
               leaf validation-state {
                 description "Validation state for route validation record";
                 type enumeration {
                   enum "invalid" {
                     description "Invalid route validation state";
                   }
                   enum "valid" {
                     description "Valid route validation state";
                   }
                 }
               }
             }
           }
         }
       }
       list database {
         key name;
         description "Specify a named validation database";
         leaf name {
           description "Name of validation database";
           type string;
         }
         uses apply-advanced;
         container static {
           description "Define static route validation record";
           uses apply-advanced;
           list record {
             key name;
             description "Static route validation record";
             leaf name {
               type jt:ipprefix;
             }
             uses apply-advanced;
             list maximum-length {
               key name;
               ordered-by user;
               leaf name {
                 description "Maximum prefix-length for route validation record";
                 type union {
                   type string {
                     pattern "<.*>|$.*";
                   }
                   type uint32 {
                     range "1 .. 128";
                   }
                 }
               }
               uses apply-advanced;
               list origin-autonomous-system {
                 key name;
                 ordered-by user;
                 leaf name {
                   description "Legitimate Origin Autonomous System";
                   type union {
                     type uint32;
                     type string {
                       pattern "<.*>|$.*";
                     }
                   }
                 }
                 uses apply-advanced;
                 leaf validation-state {
                   description "Validation state for route validation record";
                   type enumeration {
                     enum "invalid" {
                       description "Invalid route validation state";
                     }
                     enum "valid" {
                       description "Valid route validation state";
                     }
                   }
                 }
               }
             }
           }
         }
       }
     }
   }
   grouping bmp-loc-rib-apath-options {
     description "Number of paths to advertise";
     uses apply-advanced;
     container path-selection-mode {
       description "Configure how to select add-path routes";
       uses apply-advanced;
       choice mode {
         case case_1 {
           leaf all-paths {
             description "Advertise all paths allowed by path count";
             type empty;
           }
         }
         case case_2 {
           leaf equal-cost-paths {
             description "Advertise equal cost paths";
             type empty;
           }
         }
       }
     }
     leaf path-count {
       description "Number of paths to advertise";
       type union {
         type string {
           pattern "<.*>|$.*";
         }
         type int32 {
           range "2 .. 64";
         }
       }
       mandatory true;
     }
     leaf multipath {
       description "Include multipath contributor routes";
       type empty;
     }
   }
   grouping domain-id-type {
     leaf name {
       description "Domain id for type 5 evpn DCI";
       type string {
       }
     }
     uses apply-advanced;
   }
   grouping dynamic_tunnel_type {
     description "Dynamic tunnel definition";
     leaf name {
       description "Tunnel name";
       type string {
       }
     }
     uses apply-advanced;
     leaf source-address {
       description "Tunnel source address";
       type jt:ipaddr;
     }
     choice tunnel-type {
       case case_1 {
         list rsvp-te {
           key name;
           ordered-by user;
           description "RSVP-TE point-to-point LSP";
           leaf name {
             description "Configure multiple entries for RSVP tunnel";
             type string;
           }
           uses apply-advanced;
           container label-switched-path-template {
             description "Template for dynamic point-to-point LSP parameters";
             uses apply-advanced;
             choice dynamic-template {
               case case_1 {
                 leaf template-name {
                   description "Name of point-to-point LSP template";
                   type string {
                   }
                 }
               }
               case case_2 {
                 leaf default-template {
                   description "Use default parameters";
                   type empty;
                 }
               }
             }
           }
           list destination-networks {
             key name;
             ordered-by user;
             description "Create tunnels for routes in these destination networks";
             uses app_network_type;
           }
         }
       }
       case case_2 {
         container spring-te {
           description "SPRING-TE LSP's";
           uses apply-advanced;
           leaf use-transport-class {
             description "Install dynamic-tunnel routes via transport class RIBs";
             type empty;
           }
           list source-routing-path-template {
             key name;
             ordered-by user;
             description "Template color mapping for SPRING-TE dynamic LSP parameters";
             uses spring-te-template-map;
           }
           list destination-networks {
             key name;
             ordered-by user;
             description "Create tunnels for routes in these destination networks";
             uses app_network_type;
           }
         }
       }
       case case_3 {
         leaf gre {
           description "Generic routing encapsulation type for IPv4";
           type empty;
         }
       }
       case case_4 {
         leaf udp {
           description "UDP encapsulation type for IPv4";
           type empty;
         }
       }
       case case_5 {
         leaf bgp-signal {
           description "BGP signals the encapsulation type for IPv4";
           type empty;
         }
       }
       case case_6 {
         leaf ipip {
           description "IPIP encapsulation type for IPv4";
           type empty;
         }
       }
       case case_7 {
         leaf srv6 {
           description "SRv6 encapsulation type for IPv6";
           type empty;
         }
       }
     }
     leaf use-transport-class {
       description "Install dynamic-tunnel routes via transport class RIBs";
       type empty;
     }
     list destination-networks {
       key name;
       ordered-by user;
       description "Create tunnels for routes in these destination networks";
       uses network_type;
     }
   }
   grouping app_network_type {
     leaf name {
       description "Network prefix";
       type jt:ipprefix;
     }
     uses apply-advanced;
   }
   grouping export-af-obj {
     uses apply-advanced;
     choice enable-disable {
       case case_1 {
         leaf disable {
           description "Disable auto-export for address family";
           type empty;
         }
       }
     }
     container unicast {
       description "Unicast routing information";
       presence "enable unicast";
       uses export-subaf-obj;
     }
     container multicast {
       description "Multicast routing information";
       presence "enable multicast";
       uses export-subaf-obj;
     }
     container flow {
       description "Flow routing information";
       presence "enable flow";
       uses export-subaf-obj;
     }
   }
   grouping export-subaf-obj {
     uses apply-advanced;
     choice enable-disable {
       case case_1 {
         leaf disable {
           description "Disable instance export";
           type empty;
         }
       }
     }
     leaf rib-group {
       description "Auxiliary rib-group of additional RIBs to consider";
       type string;
     }
   }
   grouping fate_sharing_links {
     leaf name {
       description "Router ID or LAN interface address";
       type jt:ipv4addr;
     }
     leaf to {
       description "Point-to-point links";
       type jt:ipv4addr;
     }
   }
   grouping flow-interface-group {
     leaf group {
       description "Interface group ID to match traffic";
       type union {
         type string {
           pattern "<.*>|$.*";
         }
         type uint32 {
           range "1 .. 255";
         }
       }
       //mandatory true;
     }
     leaf exclude {
       description "Don't apply flow-spec filter to traffic on this group";
       type empty;
     }
   }
   grouping flow-route-inet {
     leaf name {
       type string;
     }
     uses apply-advanced;
     leaf no-install {
       description "Don't install firewall filter in forwarding";
       type empty;
     }
     container match {
       description "Flow definition";
       uses flow-route-qualifier-inet;
     }
     container then {
       description "Actions to take for this flow";
       uses flow-route-op;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     leaf destination {
       description "Destination prefix for this traffic flow";
       type jt:ipv4prefix;
     }
     leaf source {
       description "Source prefix for this traffic flow";
       type jt:ipv4prefix;
     }
     leaf-list icmp-code {
       ordered-by user;
       description "ICMP message code";
       type string;
     }
     leaf-list icmp-type {
       ordered-by user;
       description "ICMP message type";
       type string;
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
       mandatory true;
     }
     leaf prefix-offset {
       description "Offset from where prefix match will start";
       type union {
         type uint32;
         type string {
           pattern "<.*>|$.*";
         }
       }
     }
   }
   grouping flow-rule-inet {
     leaf name {
       type string;
     }
     uses apply-advanced;
     leaf no-install {
       description "Don't install firewall filter in forwarding";
       type empty;
     }
     container match {
       description "Flow definition";
       uses flow-rule-qualifier-inet;
     }
     container then {
       description "Actions to take for this flow";
       uses flow-rule-op;
     }
   }
   grouping flow-rule-inet6 {
     leaf name {
       type string;
     }
     uses apply-advanced;
     leaf no-install {
       description "Don't install firewall filter in forwarding";
       type empty;
     }
     container match {
       description "Flow definition";
       uses flow-rule-qualifier-inet6;
     }
     container then {
       description "Actions to take for this flow";
       uses flow-rule-op;
     }
   }
   grouping flow-rule-op {
     uses apply-advanced;
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
   }
   grouping flow-rule-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf destination {
       description "Destination prefix for this traffic flow";
       type jt:ipv4prefix;
     }
     leaf source {
       description "Source prefix for this traffic flow";
       type jt:ipv4prefix;
     }
   }
   grouping flow-rule-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     container destination {
       description "Destination prefix for this traffic flow";
       presence "enable destination";
       uses flow-prefix-with-offset;
     }
     container source {
       description "Source prefix for this traffic flow";
       presence "enable source";
       uses flow-prefix-with-offset;
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
         }
         //mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
           mandatory true;
         }
         leaf-list policy {
           ordered-by user;
           description "Filter policy";
           type jt:policy-algebra;
         }
       }
     }
   }
   grouping forwarding-table-type {
     description "Forwarding table management options";
     uses apply-advanced;
     leaf oc-tlv-support {
       description "Send origin protocol and network-instance for route and stream next-hop origin protocol";
       type empty;
     }
     leaf remnant-holdtime {
       description "Time to hold inherited routes from FIB";
       type union {
         type string {
           pattern "<.*>|$.*";
         }
         type uint32 {
           range "0 .. 10000";
         }
       }
     }
     leaf send-gr-issu-message {
       description "Simulate gr-issu message reception from rpd-agent";
       type union {
         type string {
           pattern "<.*>|$.*";
         }
         type uint32 {
           range "1 .. 65535";
         }
       }
     }
     leaf chain-composite-max-label-count {
       description "Maximum labels inside chain composite for the platform.";
       type union {
         type string {
           pattern "<.*>|$.*";
         }
         type uint32 {
           range "1 .. 16";
         }
       }
     }
     leaf krt-nexthop-ack {
       description "Enable kernel nexthop ack";
       type empty;
     }
     leaf krt-nexthop-ack-timeout {
       description "Kernel nexthop ack timeout interval";
       type union {
         type string {
           pattern "<.*>|$.*";
         }
         type uint32 {
           range "1 .. 400";
         }
       }
     }
     leaf srv6-chain-merge {
       description "Enable merging of srv6 chain nexthops";
       type empty;
     }
     choice session-id-change-limiter-indirect-choice {
       leaf session-id-change-limiter-indirect {
         description "Enable indirect nexthop to limit session-id change propagation";
         type empty;
       }
       leaf no-session-id-change-limiter-indirect {
         description "Don't enable indirect nexthop to limit session-id change propagation";
         type empty;
       }
     }
     container consistency-checking {
       description "RIB/FIB consistency checking";
       status deprecated;
       uses apply-advanced;
       choice enable-disable {
         case case_1 {
           leaf enable {
             description "Enable consistency checking";
             type empty;
           }
         }
         case case_2 {
           leaf disable {
             description "Disable consistency checking";
             type empty;
           }
         }
       }
       leaf period {
         description "Periodicity of scan in seconds";
         type union {
           type string {
             pattern "<.*>|$.*";
           }
           type uint32 {
             range "30 .. 4294967295";
           }
         }
       }
       leaf threshold {
         description "Mismatch threshold until complaint";
         type union {
           type uint32;
           type string {
             pattern "<.*>|$.*";
           }
         }
       }
     }
     leaf-list export {
       ordered-by user;
       description "Export policy";
       type jt:policy-algebra;
     }
     leaf dynamic-list-next-hop {
       description "Dynamic next-hop mode for EVPN";
       type empty;
     }
     container evpn-egress-link-protection {
       presence "enable evpn-egress-link-protection";
       description "EVPN PE-CE egress link failure protection";
       uses apply-advanced;
     }
     leaf vpls-hotstandby-convergence {
       description "Enable convergence improvements for VPLS hot-standby";
       type empty;
     }
     container egress-chaining {
       description "Enable egress-chaining";
       uses apply-advanced;
       leaf spring-te {
         description "Enable egress-chaining for SPRING-TE routes";
         type empty;
       }
     }
     leaf evpn-aliasing-optimize {
       description "EVPN Aliasing convergence improvement";
       type empty;
     }
     choice indirect-next-hop-choice {
       leaf indirect-next-hop {
         description "Install indirect next hops in Packet Forwarding Engine";
         type empty;
       }
       leaf no-indirect-next-hop {
         description "Don't install indirect next hops in Packet Forwarding Engine";
         type empty;
       }
     }
     choice route-ack-converge-choice {
       leaf route-ack-converge {
         description "Enable the route ack convergence feature";
         type empty;
       }
       leaf no-route-ack-converge {
         description "Don't enable the route ack convergence feature";
         type empty;
       }
     }
     leaf long-live-ack-timer-val {
       description "Set default long live acknowledgement timer value";
       type union {
         type string {
           pattern "<.*>|$.*";
         }
         type uint32 {
           range "1 .. 65535";
         }
       }
     }
     choice pfe-install-error-choice {
       leaf pfe-install-error {
         description "Enable processing error from PFE for objects installed";
         type empty;
       }
       leaf no-pfe-install-error {
         description "Don't enable processing error from PFE for objects installed";
         type empty;
       }
     }
     list rib {
       key name;
       ordered-by user;
       status deprecated;
       leaf name {
         type string;
       }
     }
     leaf unicast-reverse-path {
       description "Unicast reverse path (RP) verification";
       type enumeration {
         enum "active-paths" {
           description "Consider active paths when performing RP verification";
         }
         enum "feasible-paths" {
           description "Consider all feasible paths for RP verification";
         }
       }
     }
     container ip-tunnel-rpf-check {
       presence "enable ip-tunnel-rpf-check";
       description "IP tunnel Reverse Path Forwarding Check";
       uses apply-advanced;
       leaf mode {
         default "strict";
         type enumeration {
           enum "strict" {
             description "Strict mode for rpf-check(Default)";
           }
           enum "loose" {
             description "Loose mode for rpf-check";
           }
         }
       }
       leaf fail-filter {
         description "Fail filter name for RPF check(family inet|inet6|any)";
         type string {
         }
       }
     }
     container fib-next-hop-split {
       description "Split nexthop to chain nexthop when installing fom rib to fib";
       uses apply-advanced;
       leaf labeled-isis {
         description "Create composite-chained nexthops for labeled ISIS routes";
         type empty;
       }
     }
     container fib-agent {
       presence "enable fib-agent";
       description "Configure fib-agent parameters";
       uses apply-advanced;
       leaf address {
         description "IP address of the FIB agent";
         default "127.0.0.1";
         type jt:ipaddr;
       }
       leaf port {
         description "TCP port of the FIB agent";
         default "2620";
         type union {
           type string {
             pattern "<.*>|$.*";
           }
           type uint32 {
             range "1 .. 65535";
           }
         }
       }
       leaf protocol-id {
         description "Protocol ID to be used for programming routes";
         default "22";
         type union {
           type string {
             pattern "<.*>|$.*";
           }
           type uint32 {
             range "0 .. 255";
           }
         }
       }
     }
     list channel {
       key name;
       ordered-by user;
       description "Configure fib-channel parameters";
       leaf name {
         description "FIB Channel Name";
         type string;
       }
       uses apply-advanced;
       container protocol {
         presence "enable protocol";
         description "Configure fib-channel protocol";
         uses apply-advanced;
         leaf protocol-type {
           type enumeration {
             enum "netlink-fpm" {
               description "Configure SONiC FIB Channel";
             }
             enum "gRPC" {
               description "Configure vRouter FIB channel.";
             }
           }
           mandatory true;
         }
         leaf destination {
           description "Destination of the FIB";
           type string;
         }
         leaf source-id {
           description "Source ID to be used for programming routes";
           default "22";
           type union {
             type string {
               pattern "<.*>|$.*";
             }
             type uint32 {
               range "0 .. 255";
             }
           }
         }
       }
       leaf-list export {
         ordered-by user;
         description "Export policy";
         type jt:policy-algebra;
       }
     }
     leaf multicast-composite-delete-defer-timeout {
       description "Time to defer multicast composite NH delete operation into FIB";
       type union {
         type string {
           pattern "<.*>|$.*";
         }
         type uint32 {
           range "1 .. 3600";
         }
       }
     }
   }
   grouping juniper-system {
     uses apply-advanced;
     leaf host-name {
       description "Hostname for this router";
       type string {
         length "1 .. 255";
       }
     }
     container root-authentication {
       description "Authentication information for the root login";
       uses authentication-object;
     }
     container scripts {
       description "Scripting mechanisms";
       uses scripts_type;
     }
     container login {
       description "Names, login classes, and passwords for users";
       uses apply-advanced;
       container retry-options {
         description "Configure password retry options";
         uses apply-advanced;
         leaf tries-before-disconnect {
           description "Number of times user is allowed to try password";
           default "3";
           type union {
             type string {
               pattern "<.*>|$.*";
             }
             type uint32 {
               range "2 .. 10";
             }
           }
         }
         leaf backoff-threshold {
           description "Number of password failures before delay is introduced";
           default "2";
           type union {
             type string {
               pattern "<.*>|$.*";
             }
             type uint32 {
               range "1 .. 3";
             }
           }
         }
         leaf backoff-factor {
           description "Delay factor after 'backoff-threshold' password failures";
           default "5";
           type union {
             type string {
               pattern "<.*>|$.*";
             }
             type uint32 {
               range "5 .. 10";
             }
           }
         }
         leaf minimum-time {
           description "Minimum total connection time if all attempts fail";
           default "20";
           type union {
             type string {
               pattern "<.*>|$.*";
             }
             type uint32 {
               range "20 .. 60";
             }
           }
         }
         leaf maximum-time {
           description "Maximum time the connection will remain for user to enter username and password";
           default "120";
           type union {
             type string {
               pattern "<.*>|$.*";
             }
             type uint32 {
               range "20 .. 300";
             }
           }
         }
         leaf lockout-period {
           description "Amount of time user account is locked after 'tries-before-disconnect' failures";
           units "minutes";
           type union {
             type string {
               pattern "<.*>|$.*";
             }
             type uint32 {
               range "1 .. 43200";
             }
           }
         }
       }
       leaf idle-timeout {
         description "Maximum idle time before logout";
         units "minutes";
         type union {
           type string {
             pattern "<.*>|$.*";
           }
           type uint32 {
             range "1 .. 60";
           }
         }
       }
       list class {
         key name;
         description "Login class";
         uses login-class-object;
       }
       list user {
         key name;
         description "Username";
         uses login-user-object;
       }
       container password {
         description "Password configuration";
         uses apply-advanced;
         leaf minimum-character-changes {
           description "Minimum number of character changes between old and new passwords";
           type union {
             type string {
               pattern "<.*>|$.*";
             }
             type int32 {
               range "4 .. 15";
             }
           }
         }
         leaf minimum-reuse {
           description "Minimum number of old passwords which should not be same as the new password";
           type union {
             type string {
               pattern "<.*>|$.*";
             }
             type int32 {
               range "1 .. 20";
             }
           }
         }
         leaf maximum-lifetime {
           description "Maximum password lifetime in days";
           type union {
             type string {
               pattern "<.*>|$.*";
             }
             type int32 {
               range "30 .. 365";
             }
           }
         }
         leaf minimum-lifetime {
           description "Minimum password lifetime in days";
           type union {
             type string {
               pattern "<.*>|$.*";
             }
             type int32 {
               range "1 .. 30";
             }
           }
         }
         leaf minimum-length {
           description "Minimum password length for all users";
           type union {
             type string {
               pattern "<.*>|$.*";
             }
             type int32 {
               range "6 .. 20";
             }
           }
         }
         leaf maximum-length {
           description "Maximum password length for all users";
           type union {
             type string {
               pattern "<.*>|$.*";
             }
             type int32 {
               range "20 .. 128";
             }
           }
         }
         leaf change-type {
           description "Password change type";
           type enumeration {
             enum "character-sets" {
               description "Count number of character type";
             }
             enum "set-transitions" {
               description "Count changes in character type";
             }
           }
         }
         leaf minimum-changes {
           description "Minimum number of changes in password";
           type union {
             type int32;
             type string {
               pattern "<.*>|$.*";
             }
           }
         }
         leaf minimum-numerics {
           description "Minimum number of numeric class characters in password";
           type union {
             type string {
               pattern "<.*>|$.*";
             }
             type int32 {
               range "1 .. 128";
             }
           }
         }
         leaf minimum-upper-cases {
           description "Minimum number of upper-case class characters in password";
           type union {
             type string {
               pattern "<.*>|$.*";
             }
             type int32 {
               range "1 .. 128";
             }
           }
         }
         leaf minimum-lower-cases {
           description "Minimum number of lower-case class characters in password";
           type union {
             type string {
               pattern "<.*>|$.*";
             }
             type int32 {
               range "1 .. 128";
             }
           }
         }
         leaf minimum-punctuations {
           description "Minimum number of punctuation class characters in password";
           type union {
             type string {
               pattern "<.*>|$.*";
             }
             type int32 {
               range "1 .. 128";
             }
           }
         }
         leaf format {
           description "Encryption method to use for password";
           type enumeration {
             enum "sha256" {
               description "Secure Hash Algorithm 256 ($5$)";
             }
             enum "sha512" {
               description "Secure Hash Algorithm 512 ($6$)";
             }
             enum "md5" {
               description "Message Digest 5";
             }
             enum "des" {
               description "Digital Encryption Standard";
             }
           }
         }
       }
       container deny-sources {
         description "Sources from which logins are denied";
         uses apply-advanced;
         leaf-list address {
           ordered-by user;
           description "IPv4/IPv6 addresses, prefix length optional, or hostnames";
           type jt:ipprefix-optional;
         }
       }
       leaf announcement {
         description "System announcement message (displayed after login)";
         type string {
           length "1 .. 2048";
         }
       }
       leaf message {
         description "System login message";
         type string {
           length "1 .. 2048";
         }
       }
     }
     container configuration {
       description "Set the configuration processing related parameters";
       uses apply-advanced;
       container input {
         description "Set the input configuration processing related parameters";
         uses apply-advanced;
         container format {
           description "Specify the format";
           uses apply-advanced;
           container json {
             description "JSON format related parameters";
             uses apply-advanced;
             leaf reorder-list-keys {
               description "Reorder list keys as per JUNOS style";
               type empty;
             }
           }
         }
       }
     }
     leaf max-cli-sessions {
       description "Maximum number of cli sessions";
       type union {
         type uint32;
         type string {
           pattern "<.*>|$.*";
         }
       }
     }
     container services {
       presence "enable services";
       description "System services";
       uses apply-advanced;
       container netconf {
         description "Allow NETCONF connections";
         uses apply-advanced;
         container yang-modules {
           description "Tweak settings for YANG modules served on this device";
           uses apply-advanced;
           leaf emit-family-ns-and-module-name {
             description "Emit family specific namespace and module name in Yang modules";
             type empty;
           }
           leaf device-specific {
             description "Serve YANG modules specific to this device";
             type empty;
           }
           leaf emit-extensions {
             description "Enable serving of Junos YANG extension modules";
             type empty;
           }
           leaf rpc-output-verbose {
             description "Emit verbose rpc output";
             status deprecated;
             type empty;
           }
           leaf emit-anyxml-in-rpc-output {
             description "Emit anyxml stanza in RPC output/response block";
             type empty;
           }
         }
         container ssh {
           presence "enable ssh";
           description "Allow NETCONF over SSH";
           uses apply-advanced;
           leaf client-alive-count-max {
             description "Threshold of missing client-alive responses that triggers a disconnect";
             default "3";
             type union {
               type string {
                 pattern "<.*>|$.*";
               }
               type uint32 {
                 range "0 .. 255";
               }
             }
           }
           leaf client-alive-interval {
             description "Frequency of client-alive requests";
             default "0";
             units "seconds";
             type union {
               type string {
                 pattern "<.*>|$.*";
               }
               type uint32 {
                 range "0 .. 65535";
               }
             }
           }
           leaf port {
             description "Service port number";
             default "830";
             type union {
               type string {
                 pattern "<.*>|$.*";
               }
               type int32 {
                 range "1 .. 65535";
               }
             }
           }
         }
         container tls {
           description "Allow NETCONF over TLS";
           uses apply-advanced;
           leaf local-certificate {
             description "Local Certificate ID";
             type string {
             }
             //mandatory true;
           }
           list client-identity {
             key name;
             ordered-by user;
             description "Individual TLS/NETCONF client information";
             leaf name {
               description "Client ID";
               type string {
                 length "1 .. 31";
               }
             }
             uses apply-advanced;
             leaf fingerprint {
               description "Client certificate fingerprint in x509c2n:tls-fingerprint format";
               type string {
               }
               //mandatory true;
             }
             leaf map-type {
               description "Map Type";
               type enumeration {
                 enum "specified" {
                   description "Use the specified username as NETCONF username";
                 }
                 enum "san-dirname-cn" {
                   description "Use the common name (CN) field of SAN DirName as NETCONF username";
                 }
               }
               //mandatory true;
             }
             leaf username {
               description "NETCONF username if the map-type is specified";
               type string {
               }
             }
           }
           container default-client-identity {
             description "Default TLS/NETCONF client information";
             uses apply-advanced;
             leaf map-type {
               description "Map Type";
               type enumeration {
                 enum "specified" {
                   description "Use the specified username as NETCONF username";
                 }
                 enum "san-dirname-cn" {
                   description "Use the common name (CN) field of SAN DirName as NETCONF username";
                 }
               }
               //mandatory true;
             }
             leaf username {
               description "NETCONF username if the map-type is specified";
               type string {
               }
             }
           }
           container traceoptions {
             description "NETCONF over TLS trace options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               default "error";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "general" {
                     description "Log the tls-proxyd infra related messages";
                   }
                   enum "pki" {
                     description "Log the PKI related messages";
                   }
                   enum "plugin" {
                     description "Log the plugin messages";
                   }
                   enum "app" {
                     description "Log the application data in plain text";
                   }
                   enum "all" {
                     description "Log the entire communication";
                   }
                 }
               }
             }
           }
         }
         container unified {
           description "Schema options for unified netconf";
           uses apply-advanced;
           leaf unhide {
             description "Unhide unified netconf get from CLI";
             type empty;
           }
         }
         container hello-message {
           description "Configuration for NETCONF 'hello' message";
           uses apply-advanced;
           container yang-module-capabilities {
             description "Advertise YANG module capabilities of the device";
             uses apply-advanced;
             leaf advertise-native-yang-modules {
               description "Advertise Junos native YANG modules";
               type empty;
             }
             leaf advertise-custom-yang-modules {
               description "Advertise custom YANG modules installed on the device";
               type empty;
             }
             leaf advertise-standard-yang-modules {
               description "Advertise standard YANG modules supported by the device";
               type empty;
             }
           }
         }
         container netconf-monitoring {
           description "NETCONF monitoring feature (RFC 6022) related configuration";
           uses apply-advanced;
           container netconf-state-schemas {
             description "Configuration to retrieve the schemas supported by the NETCONF server";
             uses apply-advanced;
             leaf retrieve-custom-yang-modules {
               description "Retrieve the custom YANG modules installed on the device";
               type empty;
             }
             leaf retrieve-standard-yang-modules {
               description "Retrieve the standard YANG modules supported by the device";
               type empty;
             }
           }
         }
         leaf rfc-compliant {
           description "Make the NETCONF sessions compliant to RFC 4741";
           type empty;
         }
         leaf yang-compliant {
           description "Make the NETCONF sessions compliant to yang schemas";
           type empty;
         }
         leaf flatten-commit-results {
           description "Suppress the 'commit-results' XML subtree in 'commit' rpc response";
           type empty;
         }
         container traceoptions {
           description "NETCONF trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Log the entire communication";
                 }
                 enum "incoming" {
                   description "Log all incoming data";
                 }
                 enum "outgoing" {
                   description "Log all outgoing data";
                 }
                 enum "debug" {
                   description "Log debug level information";
                 }
               }
             }
           }
           leaf on-demand {
             description "Enable on-demand tracing";
             type empty;
           }
         }
         container notification {
           presence "enable notification";
           description "Enable Netconf notification service";
           uses apply-advanced;
           leaf interleave {
             description "Enable interleaving";
             type empty;
           }
         }
         container version-1.1 {
           presence "enable version-1.1";
           description "Make the NETCONF sessions compliant to RFC 6242";
         }
       }
       container ssh {
         presence "enable ssh";
         description "Allow ssh access";
         uses apply-advanced;
         leaf-list authentication-order {
           ordered-by user;
           type enumeration {
             enum "radius" {
               description "Remote Authentication Dial-In User Service";
             }
             enum "tacplus" {
               description "TACACS+ authentication services";
             }
             enum "password" {
               description "Traditional password authentication";
             }
           }
         }
         container cert-based-auth {
           description "Certificates for user authentication";
           uses apply-advanced;
           list trusted-user-ca-keys {
             key name;
             ordered-by user;
             description "Trusted User CA Keys";
             leaf name {
               description "SSH public key for validating user certificates";
               type string {
                 length "1 .. 4096";
               }
             }
             uses apply-advanced;
           }
           leaf host-certificate {
             description "SSH host certificate";
             type string {
               length "1 .. 8000";
             }
           }
         }
         leaf host-certificate-file {
           description "File containing the host certificate";
           type string;
         }
         leaf trusted-user-ca-key-file {
           description "File containing public keys for validating user certificates";
           type string;
         }
         leaf-list authorized-principals {
           ordered-by user;
           description "List of authorized principals";
           type string;
         }
         leaf authorized-principals-file {
           description "File containing list of authorized principals";
           type string;
         }
         leaf authorized-principals-command {
           description "Command to generate AuthorizedPrincipals file";
           type string;
         }
         leaf root-login {
           description "Configure root access via ssh";
           type enumeration {
             enum "allow" {
               description "Allow root access via ssh";
             }
             enum "deny" {
               description "Do not allow root access via ssh";
             }
             enum "deny-password" {
               description "Allow for non-password-based authentication methods only";
             }
           }
         }
         leaf no-challenge-response {
           description "Disables ssh challenge-response based authentication methods";
           type empty;
         }
         leaf no-password-authentication {
           description "Disables ssh password based authentication methods";
           type empty;
         }
         leaf no-passwords {
           description "Disables ssh password and challenge-response based authentication";
           type empty;
         }
         leaf no-public-keys {
           description "Disables ssh public key based authentication";
           type empty;
         }
         leaf allow-tcp-forwarding {
           description "Allow forwarding TCP connections via SSH";
           type empty;
         }
         leaf-list protocol-version {
           ordered-by user;
           description "Specify ssh protocol versions supported";
           type enumeration {
             enum "v2" {
               description "Version 2 ssh protocol";
             }
           }
         }
         leaf max-sessions-per-connection {
           description "Maximum number of sessions per single SSH connection";
           type union {
             type string {
               pattern "<.*>|$.*";
             }
             type int32 {
               range "1 .. 65535";
             }
           }
         }
         leaf max-pre-authentication-packets {
           description "Maximum number of pre-authentication SSH packets per single SSH connection";
           type union {
             type string {
               pattern "<.*>|$.*";
             }
             type int32 {
               range "20 .. 2147483647";
             }
           }
         }
         leaf sftp-server {
           description "Globally enable incoming SFTP connections";
           type empty;
         }
         leaf-list ciphers {
           ordered-by user;
           description "Specify the ciphers allowed for protocol version 2";
           type enumeration {
             enum "3des-cbc" {
               description "Triple DES in CBC mode";
             }
             enum "aes128-cbc" {
               description "128-bit AES with Cipher Block Chaining";
             }
             enum "aes192-cbc" {
               description "192-bit AES with Cipher Block Chaining";
             }
             enum "aes256-cbc" {
               description "256-bit AES with Cipher Block Chaining";
             }
             enum "aes128-ctr" {
               description "128-bit AES with Counter Mode";
             }
             enum "aes192-ctr" {
               description "192-bit AES with Counter Mode";
             }
             enum "aes256-ctr" {
               description "256-bit AES with Counter Mode";
             }
             enum "aes128-gcm@openssh.com" {
               description "128-bit AES with Galois/Counter Mode";
             }
             enum "aes256-gcm@openssh.com" {
               description "256-bit AES with Galois/Counter Mode";
             }
             enum "chacha20-poly1305@openssh.com" {
               description "ChaCha20 stream cipher and Poly1305 MAC";
             }
           }
         }
         leaf-list macs {
           ordered-by user;
           description "Message Authentication Code algorithms allowed (SSHv2)";
           type enumeration {
             enum "hmac-md5" {
               description "Hash-based MAC using Message-Digest 5 (MD5)";
             }
             enum "hmac-md5-etm@openssh.com" {
               description "Hash-based Encrypt-then-MAC using Message-Digest 5 (MD5)";
             }
             enum "hmac-sha1" {
               description "Hash-based MAC using Secure Hash Algorithm (SHA1)";
             }
             enum "hmac-sha1-etm@openssh.com" {
               description "Hash-based Encrypt-then-MAC using Secure Hash Algorithm (SHA1)";
             }
             enum "umac-64@openssh.com" {
               description "UMAC-64 algorithm specified in RFC4418";
             }
             enum "umac-128@openssh.com" {
               description "UMAC-128 algorithm specified in RFC4418";
             }
             enum "umac-64-etm@openssh.com" {
               description "Encrypt-then-MAC using UMAC-64 algorithm specified in RFC4418";
             }
             enum "umac-128-etm@openssh.com" {
               description "Encrypt-then-MAC using UMAC-128 algorithm specified in RFC4418";
             }
             enum "hmac-sha2-256" {
               description "Hash-based MAC using Secure Hash Algorithm (SHA2)";
             }
             enum "hmac-sha2-256-etm@openssh.com" {
               description "Hash-based Encrypt-then-Mac using Secure Hash Algorithm (SHA2)";
             }
             enum "hmac-sha2-512" {
               description "Hash-based MAC using Secure Hash Algorithm (SHA2)";
             }
             enum "hmac-sha2-512-etm@openssh.com" {
               description "Hash-based Encrypt-then-Mac using Secure Hash Algorithm (SHA2)";
             }
             enum "hmac-sha1-96" {
               description "96-bits of Hash-based MAC using SHA1";
             }
             enum "hmac-sha1-96-etm@openssh.com" {
               description "96-bits of Hash-based Encrypt-then-MAC using SHA1";
             }
             enum "hmac-md5-96" {
               description "96-bits of Hash-based MAC using MD5";
             }
             enum "hmac-md5-96-etm@openssh.com" {
               description "96-bits of Hash-based Encrypt-then-MAC using MD5";
             }
           }
         }
         leaf-list key-exchange {
           ordered-by user;
           description "Specify ssh key-exchange for Diffie-Hellman keys";
           type enumeration {
             enum "curve25519-sha256" {
               description "The EC Diffie-Hellman on Curve25519 with SHA2-256 hash";
             }
             enum "ecdh-sha2-nistp256" {
               description "The EC Diffie-Hellman on nistp256 with SHA2-256";
             }
             enum "ecdh-sha2-nistp384" {
               description "The EC Diffie-Hellman on nistp384 with SHA2-384";
             }
             enum "ecdh-sha2-nistp521" {
               description "The EC Diffie-Hellman on nistp521 with SHA2-512";
             }
             enum "group-exchange-sha2" {
               description "The RFC 4419 group exchange with SHA2-256 hash";
             }
             enum "group-exchange-sha1" {
               description "The RFC 4419 group exchange with SHA1 hash";
             }
             enum "dh-group14-sha1" {
               description "The RFC 4253 mandated group14 with SHA1 hash";
             }
             enum "dh-group1-sha1" {
               description "The RFC 4253 mandated group1 with SHA1 hash";
             }
           }
         }
         leaf client-alive-count-max {
           description "Threshold of missing client-alive responses that triggers a disconnect";
           default "3";
           type union {
             type string {
               pattern "<.*>|$.*";
             }
             type uint32 {
               range "0 .. 255";
             }
           }
         }
         leaf client-alive-interval {
           description "Frequency of client-alive requests";
           default "0";
           units "seconds";
           type union {
             type string {
               pattern "<.*>|$.*";
             }
             type uint32 {
               range "0 .. 65535";
             }
           }
         }
         container hostkey-algorithm-list {
           presence "enable hostkey-algorithm-list";
           description "Specify permissible SSH host-key algorithms";
           uses apply-advanced;
           leaf rsa {
             description "Allow generation of RSA host-key";
             type empty;
           }
           leaf ecdsa-sha2-nistp256 {
             description "Allow generation of ECDSA host-key with NIST P-256 curve";
             type empty;
           }
           leaf ecdsa-sha2-nistp384 {
             description "Allow generation of ECDSA host-key with NIST P-384 curve";
             type empty;
           }
           leaf ecdsa-sha2-nistp521 {
             description "Allow generation of ECDSA host-key with NIST P-521 curve";
             type empty;
           }
           leaf ed25519 {
             description "Allow generation of EdDSA host-key with curve25519";
             type empty;
           }
         }
         leaf fingerprint-hash {
           description "Configure hash algorithm used when displaying key fingerprints";
           type enumeration {
             enum "sha2-256" {
               description "Enable use of SHA2-256";
             }
             enum "md5" {
               description "Enable use of MD5";
             }
           }
         }
         leaf authorized-keys-command {
           description "Specifies a command string to be used to look up the user's public keys";
           type string {
             length "1 .. 1024";
           }
         }
         leaf authorized-keys-command-user {
           description "Specifies the user under whose account the authorized-keys-command is run";
           type string {
             length "1 .. 256";
           }
         }
         container rekey {
           description "Limits before session keys are renegotiated";
           uses apply-advanced;
           leaf data-limit {
             description "Data limit before renegotiating session keys";
             units "bytes";
             type string;
           }
           leaf time-limit {
             description "Time limit before renegotiating session keys";
             units "minutes";
             type union {
               type string {
                 pattern "<.*>|$.*";
               }
               type uint32 {
                 range "1 .. 1440";
               }
             }
           }
         }
         leaf port {
           description "Port number to accept incoming connections";
           default "22";
           type union {
             type string {
               pattern "<.*>|$.*";
             }
             type uint32 {
               range "1 .. 65535";
             }
           }
         }
         leaf log-key-changes {
           description "Log changes to authorized keys to syslog";
           type empty;
         }
       }
       container xnm-clear-text {
         presence "enable xnm-clear-text";
         description "Allow clear text-based JUNOScript connections";
         uses apply-advanced;
       }
       container xnm-ssl {
         presence "enable xnm-ssl";
         description "Allow SSL-based JUNOScript connections";
         uses apply-advanced;
         leaf local-certificate {
           description "Name of local X.509 certificate to use";
           type string;
           mandatory true;
         }
         choice ssl-renegotiation-choice {
           leaf ssl-renegotiation {
             description "Allow SSL renegotiation";
             type empty;
           }
           leaf no-ssl-renegotiation {
             description "Don't allow SSL renegotiation";
             type empty;
           }
         }
       }
       container jeb {
         presence "enable jeb";
         description "Configure the Juniper Juniper Entropy Beacon service";
         uses apply-advanced;
         leaf port {
           description "JEB Service port";
           default "57005";
           type union {
             type string {
               pattern "<.*>|$.*";
             }
             type uint32 {
               range "1025 .. 65535";
             }
           }
         }
         leaf rbg {
           description "Random Bit Generator";
           type enumeration {
             enum "default-rng" {
               description "Default CSPRNG";
             }
             enum "hmac-drbg" {
               description "HMAC DRBG, NIST SP800-90A";
             }
             enum "jrbc" {
               description "Juniper Random Bit Conditioner";
             }
           }
           mandatory true;
         }
         leaf max-seed-size {
           description "Maximum allowed size for a requested seed";
           default "4096";
           type union {
             type string {
               pattern "<.*>|$.*";
             }
             type uint32 {
               range "1 .. 65536";
             }
           }
         }
         container tls {
           presence "enable tls";
           description "Configure TLS Attributes for JEB Service";
           uses apply-advanced;
           leaf cert-bundle {
             description "Certificate Bundle File";
             type string;
             mandatory true;
           }
           leaf certificate {
             description "TLS Server Certificate";
             type string;
             mandatory true;
           }
           leaf key {
             description "Private Key File";
             type string;
             mandatory true;
           }
         }
       }
       container extension-service {
         description "Enable JUNOS extension services";
         uses apply-advanced;
         container request-response {
           description "Allow request-response API execution";
           uses apply-advanced;
           container grpc {
             description "Grpc server configuration";
             uses apply-advanced;
             choice request-response-type {
               case case_1 {
                 container ssl {
                   description "SSL based API connection settings";
                   uses apply-advanced;
                   leaf address {
                     description "Address to listen for incoming connections";
                     default "::";
                     type jt:ipaddr;
                   }
                   leaf port {
                     description "Port number to accept incoming connections";
                     default "32767";
                     type union {
                       type string {
                         pattern "<.*>|$.*";
                       }
                       type uint32 {
                         range "1 .. 65535";
                       }
                     }
                   }
                   leaf-list local-certificate {
                     ordered-by user;
                     description "Name of local X.509 certificate to use";
                     type string;
                   }
                   container mutual-authentication {
                     description "Enable TLS mutual authentication";
                     uses apply-advanced;
                     leaf certificate-authority {
                       description "Certificate authority profile";
                       type string {
                       }
                       mandatory true;
                     }
                     leaf client-certificate-request {
                       description "Specify requirements for client certificate";
                       default "require-certificate-and-verify";
                       type enumeration {
                         enum "no-certificate" {
                           description "Client certificate is not requested";
                         }
                         enum "request-certificate" {
                           description "Request certificate from client, do not verify";
                         }
                         enum "request-certificate-and-verify" {
                           description "Request certificate from client, verify if provided";
                         }
                         enum "require-certificate" {
                           description "Client certificate is mandatory, do not verify";
                         }
                         enum "require-certificate-and-verify" {
                           description "Client certificate is mandatory, certificate is verified";
                         }
                       }
                     }
                   }
                   leaf hot-reloading {
                     description "Enable certificate reload without terminating existing gRPC sessions";
                     type empty;
                   }
                   leaf use-pki {
                     description "Use local-certificate loaded via pki hierarchy";
                     type empty;
                   }
                 }
               }
             }
             leaf max-connections {
               description "Maximum number of connections";
               default "5";
               type union {
                 type string {
                   pattern "<.*>|$.*";
                 }
                 type uint32 {
                   range "1 .. 30";
                 }
               }
             }
             leaf routing-instance {
               description "Routing instance for grpc";
               type string {
               }
             }
             leaf grpc-keep-alive {
               description "GRPC keep alive duration in seconds";
               default "300";
               units "seconds";
               type union {
                 type string {
                   pattern "<.*>|$.*";
                 }
                 type uint32 {
                   range "0 .. 4294967295";
                 }
               }
             }
           }
         }
         container traceoptions {
           description "Trace options for JSD";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "10";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           container level {
             description "Trace verbosity level";
             choice level-name {
               case case_1 {
                 leaf error {
                   description "Only trace error events";
                   type empty;
                 }
               }
             }
           }
           list flag {
             key name;
             ordered-by user;
             description "Tracing parameters";
             leaf name {
               type enumeration {
                 enum "timer" {
                   description "Trace internal timer events";
                 }
                 enum "timeouts" {
                   description "Trace timeouts ";
                 }
                 enum "routing-socket" {
                   description "Trace routing socket calls";
                 }
                 enum "general" {
                   description "Trace general events";
                 }
                 enum "config" {
                   description "Trace config events";
                 }
                 enum "grpc" {
                   description "Trace grpc related events";
                 }
                 enum "libgrpc-debug" {
                   description "Trace all lib grpc related events";
                 }
                 enum "libgrpc-errors" {
                   description "Trace lib grpc errors";
                 }
                 enum "libgrpc-info" {
                   description "Trace lib grpc info and errors";
                 }
                 enum "notification" {
                   description "Trace notification events";
                 }
                 enum "all" {
                   description "Trace everything";
                 }
               }
             }
           }
         }
       }
       container grpc-tunnel {
         description "GRPC tunnel configuration for outbound TCP over gRPC";
         uses apply-advanced;
         container servers {
           description "GRPC tunnel servers configuration";
           uses apply-advanced;
           leaf retry-interval {
             description "Retry interval for unreachable targets";
             default "30";
             units "seconds";
             type union {
               type string {
                 pattern "<.*>|$.*";
               }
               type uint32 {
                 range "10 .. 300";
               }
             }
           }
           list server {
             key name;
             ordered-by user;
             description "List of tunnel servers to be dialled";
             max-elements 10;
             leaf name {
               description "Name of the tunnel server";
               type string {
                 length "1 .. 31";
               }
             }
             uses apply-advanced;
             leaf address {
               description "IP address or hostname of the tunnel server";
               type jt:hostname;
               mandatory true;
             }
             leaf port {
               description "Port number where gRPC tunnel server is listening";
               type union {
                 type string {
                   pattern "<.*>|$.*";
                 }
                 type uint32 {
                   range "1 .. 65535";
                 }
               }
               mandatory true;
             }
             leaf-list targets {
               ordered-by user;
               description "Targets to be registered with the tunnel server";
               type enumeration {
                 enum "ssh" {
                   description "Configure SSH to be registered";
                 }
                 enum "netconf-ssh" {
                   description "Configure NETCONF over SSH to be registered";
                 }
                 enum "gnmi-gnoi" {
                   description "Configure gNMI and gNOI to be registered";
                 }
               }
             }
             leaf routing-instance {
               description "Routing instance to be used for tunnel server dial-out";
               type string {
               }
             }
             leaf source-address {
               description "Source address to be used for tunnel server dial-out";
               type jt:ipaddr;
             }
             container credentials {
               description "Credentials to use for gRPC connection";
               uses apply-advanced;
               choice credential-type {
                 case case_1 {
                   container tls {
                     presence "enable tls";
                     description "Configure secure TLS credentials";
                     uses apply-advanced;
                     leaf certificate-id {
                       description "Local certificate ID to be used for gRPC tunnel target";
                       type string {
                       }
                     }
                     leaf-list ca-profiles {
                       ordered-by user;
                       description "List of CA profiles to be used to verify tunnel server";
                       type string;
                     }
                   }
                 }
               }
             }
           }
         }
         container target-string-option {
           description "Option to configure target string for this device";
           uses apply-advanced;
           leaf-list pattern {
             ordered-by user;
             description "Ordered list to build customised target string";
             type enumeration {
               enum "hostname" {
                 description "Hostname of this device";
               }
               enum "vendor" {
                 description "Vendor name";
               }
               enum "model" {
                 description "Hardware model";
               }
               enum "version" {
                 description "Software version";
               }
               enum "custom" {
                 description "Custom string to be used as target string";
               }
             }
           }
           leaf custom-string {
             description "Custom string to be used when 'custom' option is chosen";
             type string {
               length "1 .. 31";
             }
           }
           leaf delimiter {
             description "Delimiter to separate the options under pattern";
             type string {
               length "1 .. 3";
             }
           }
         }
         container traceoptions {
           description "GRPC tunnel trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "general" {
                   description "Log general messages";
                 }
                 enum "grpc-events" {
                   description "Log grpc events with tunnel server";
                 }
                 enum "timer" {
                   description "Log timer events";
                 }
                 enum "config" {
                   description "Log configuration messages";
                 }
                 enum "all" {
                   description "Log all the messages";
                 }
               }
             }
           }
         }
       }
       container service-deployment {
         description "Configuration for Service Deployment (SDXD) management application";
         uses apply-advanced;
         leaf local-certificate {
           description "Name of local X.509 certificate to use";
           type string {
             length "1 .. 1024";
           }
         }
         leaf source-address {
           description "Local IPv4 address to be used as source address for traffic to SDX";
           type jt:ipv4addr;
         }
         list servers {
           key name;
           ordered-by user;
           description "Service deployment system configuration";
           max-elements 3;
           leaf name {
             description "IPv4 address of SDX server";
             type jt:ipv4addr;
           }
           uses apply-advanced;
           leaf port {
             description "TCP port of SDX server";
             type union {
               type uint16;
               type string {
                 pattern "<.*>|$.*";
               }
             }
           }
           leaf user {
             description "Username used by SDX when logging into the router";
             type string;
           }
           container security-options {
             description "Specify mechanism to secure the connection";
             uses apply-advanced;
             choice protocol {
               case case_1 {
                 leaf tls {
                   description "Use TLS for transport layer security";
                   type empty;
                 }
               }
               case case_2 {
                 leaf ssl3 {
                   description "Use SSLv3 for transport layer security";
                   type empty;
                 }
               }
             }
           }
         }
         container traceoptions {
           description "Service deployment daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing options";
             leaf name {
               type enumeration {
                 enum "beep" {
                   description "Trace BEEP protocol events";
                 }
                 enum "profile" {
                   description "Trace BEEP profile events";
                 }
                 enum "application" {
                   description "Trace application events";
                 }
                 enum "io" {
                   description "Trace I/O activities";
                 }
                 enum "all" {
                   description "Trace everything";
                 }
               }
             }
           }
         }
       }
       container outbound-ssh {
         description "Initiate outbound SSH connection";
         uses apply-advanced;
         leaf routing-instance {
           description "Routing instance through which client is reachable";
           type string {
           }
         }
         container traceoptions {
           description "Outbound SSH trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "connectivity" {
                   description "Trace TCP connection handling";
                 }
                 enum "all" {
                   description "Trace everything";
                 }
               }
             }
           }
         }
         list client {
           key name;
           ordered-by user;
           description "Define a device initiated SSH connection";
           leaf name {
             description "Client application identifier";
             type string;
           }
           uses apply-advanced;
           leaf disable-ssh-security-settings {
             description "Disable ssh security parameter defined under [system services ssh]";
             status deprecated;
             type empty;
           }
           leaf device-id {
             description "Unique ID used by client to identify this device";
             type string;
             mandatory true;
           }
           leaf secret {
             description "Shared secret between client and this device";
             type jt:unreadable;
           }
           container keep-alive {
             presence "enable keep-alive";
             uses apply-advanced;
             leaf retry {
               description "Maximum number of connection attempts";
               default "3";
               type union {
                 type uint32;
                 type string {
                   pattern "<.*>|$.*";
                 }
               }
             }
             leaf timeout {
               description "Timeout value for conection attempts";
               default "15";
               type union {
                 type uint32;
                 type string {
                   pattern "<.*>|$.*";
                 }
               }
             }
           }
           leaf reconnect-strategy {
             description "Strategy used to reconnect to a server";
             default "in-order";
             type enumeration {
               enum "sticky" {
                 description "Attempt to reconnect to the server last connected to";
               }
               enum "in-order" {
                 description "Attempt to reconnect to the first server configured";
               }
             }
           }
           leaf services {
             description "The subsystem(s) that can be invoked";
             type enumeration {
               enum "netconf" {
                 description "Enable invoking NETCONF sub-system";
               }
             }
           }
           list servers {
             key name;
             ordered-by user;
             description "Client application servers";
             leaf name {
               description "Client address to connect to";
               type string;
             }
             uses apply-advanced;
             leaf port {
               description "Client port to connect to";
               type union {
                 type uint16;
                 type string {
                   pattern "<.*>|$.*";
                 }
               }
             }
             leaf retry {
               description "Maximum number of connection attempts";
               default "3";
               type union {
                 type uint32;
                 type string {
                   pattern "<.*>|$.*";
                 }
               }
             }
             leaf timeout {
               description "Timeout value for conection attempts";
               default "15";
               type union {
                 type uint32;
                 type string {
                   pattern "<.*>|$.*";
                 }
               }
             }
           }
           container proxy-server {
             description "Proxy server to reach the application server";
             uses apply-advanced;
             choice proxy-type {
               case case_1 {
                 leaf dhcp {
                   description "Read proxy server information from DHCP generated file";
                   type empty;
                 }
               }
               case case_2 {
                 container static {
                   description "Proxy server details";
                   uses apply-advanced;
                   leaf host {
                     description "Host name or address";
                     type string;
                     mandatory true;
                   }
                   leaf port {
                     description "Port number";
                     default "8080";
                     type union {
                       type uint16;
                       type string {
                         pattern "<.*>|$.*";
                       }
                     }
                   }
                   container proxy-authorization {
                     description "Credentials for proxy authorization with basic authentication type";
                     uses apply-advanced;
                     leaf user {
                       description "User name";
                       type string {
                         length "1 .. 255";
                       }
                       mandatory true;
                     }
                     leaf password {
                       description "Password";
                       type string {
                         length "1 .. 255";
                       }
                       mandatory true;
                     }
                   }
                 }
               }
             }
           }
         }
       }
     }
     container schema {
       description "System schema";
       uses apply-advanced;
       container openconfig {
         description "Openconfig schema options";
         uses apply-advanced;
         leaf unhide {
           description "Unhide openconfig from CLI";
           type empty;
         }
       }
     }
     container statistics-timeout {
       description "Statistics - Configurable Timeout";
       uses apply-advanced;
       leaf statistics-timeout-value {
         description "Statistics - Configurable Timeout value in milliseconds(1000 to 60000)";
         type union {
           type string {
             pattern "<.*>|$.*";
           }
           type int32 {
             range "1000 .. 60000";
           }
         }
       }
     }
     container icmp {
       presence "enable icmp";
       description " ICMP ";
       uses apply-advanced;
       leaf ttl-expired-source-address {
         description "IPv4 address for ttl-expiry";
         type jt:ipv4addr;
       }
     }
     leaf time-zone {
       description "Time zone name or POSIX-compliant time zone string";
       default "UTC";
       units "<continent>/<major-city> or <time-zone>";
       type string {
       }
     }
     leaf use-imported-time-zones {
       description "Use locally generated time-zone database";
       type empty;
     }
     leaf regex-additive-logic {
       description "Set regex-additive-logic";
       type empty;
     }
     leaf extended-echo {
       description "Enable ICMP extended echo processing";
       type empty;
     }
     leaf dump-device {
       description "Device to record memory snapshots on operating system failure";
       type string;
     }
     leaf mirror-flash-on-disk {
       description "Mirror contents of the flash drive onto hard drive";
       status deprecated;
       type empty;
     }
     container icmp-rate-limit {
       description "Rate-limiting parameters for ICMP messages";
       status deprecated;
       leaf packet-rate {
         description "ICMP rate-limiting packets earned per second";
         default "1000";
         type union {
           type uint32;
           type string {
             pattern "<.*>|$.*";
           }
         }
       }
       leaf bucket-size {
         description "ICMP rate-limiting maximum bucket size";
         default "5";
         units "seconds";
         type union {
           type uint32;
           type string {
             pattern "<.*>|$.*";
           }
         }
       }
     }
     leaf tcp-ack-rst-syn {
       description "Send ACKs for in-window RSTs and SYN packets on TCP connections";
       status deprecated;
       type empty;
     }
     leaf-list authentication-order {
       ordered-by user;
       type enumeration {
         enum "radius" {
           description "Remote Authentication Dial-In User Service";
         }
         enum "tacplus" {
           description "TACACS+ authentication services";
         }
         enum "password" {
           description "Traditional password authentication";
         }
       }
     }
     container name-resolution {
       description "Configure hostname resolution behaviour";
       uses apply-advanced;
       container no-resolve-host-on-input {
         presence "enable no-resolve-host-on-input";
         description "Do not resolve hostnames at the time of input";
       }
     }
     list radius-server {
       key name;
       ordered-by user;
       description "RADIUS server configuration";
       uses radius-server-object;
     }
     list tacplus-server {
       key name;
       ordered-by user;
       description "TACACS+ server configuration";
       uses tacplus-server-object;
     }
     container password-options {
       description "Local password options, password should be configured at [system authentication-order]";
       uses apply-advanced;
       leaf tacplus-authorization {
         description "TACACS+ authorization for locally authenticated users";
         type empty;
       }
     }
     container ldap-server {
       presence "enable ldap-server";
       description "LDAP server configuration";
       uses apply-advanced;
       leaf-list address {
         ordered-by user;
         description "LDAP authentication server address";
         type jt:hostname;
         max-elements 2;
       }
       leaf-list port {
         ordered-by user;
         description "LDAP authentication server port number";
         type union {
           type uint32;
           type string {
             pattern "<.*>|$.*";
           }
         }
         max-elements 2;
       }
       leaf base {
         description "LDAP base";
         type string;
         mandatory true;
       }
       leaf binddn {
         description "LDAP binddn";
         type string;
         mandatory true;
       }
       leaf bindpw {
         description "LDAP bindpw";
         type string;
         mandatory true;
       }
       leaf routing-instance {
         description "LDAP routing instance";
         type string {
         }
       }
       leaf ldaps-cert {
         description "LDAPS client certificate id";
         type string;
         mandatory true;
       }
     }
     container accounting {
       description "System accounting configuration";
       uses apply-advanced;
       leaf-list events {
         description "Events to be logged";
         type enumeration {
           enum "login" {
             description "Login session";
           }
           enum "change-log" {
             description "Configuration changes";
           }
           enum "interactive-commands" {
             description "Commands";
           }
         }
       }
       leaf enhanced-avs-max {
         description "No. of AV pairs each of which can store a max of 250 Bytes";
         default "7";
         type union {
           type string {
             pattern "<.*>|$.*";
           }
           type int32 {
             range "7 .. 15";
           }
         }
       }
       container traceoptions {
         description "Trace options for system accounting";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace all operations";
               }
               enum "events" {
                 description "Trace accounting events and their processing";
               }
               enum "config" {
                 description "Trace configuration processing";
               }
               enum "radius" {
                 description "Trace RADIUS processing";
               }
               enum "tacplus" {
                 description "Trace TACPLUS processing";
               }
             }
           }
         }
       }
       container destination {
         description "Destination for system accounting records";
         uses apply-advanced;
         container radius {
           presence "enable radius";
           description "Configure RADIUS accounting";
           uses apply-advanced;
           list server {
             key name;
             ordered-by user;
             description "RADIUS accounting server configuration";
             uses radius-server-object;
           }
         }
         container tacplus {
           presence "enable tacplus";
           description "Send TACACS+ accounting records";
           uses apply-advanced;
           list server {
             key name;
             ordered-by user;
             description "TACACS+ server configuration";
             uses tacplus-server-object;
           }
         }
       }
     }
     leaf allow-icmp4-extension {
       description "Allow icmp4 to add additional data structures in the extension";
       type empty;
     }
     leaf allow-icmp6-extension {
       description "Allow icmp6 to add additional data structures in the extension";
       type empty;
     }
     container syslog {
       description "System logging facility";
       uses apply-advanced;
       container archive {
         description "Archive file information";
         presence "enable archive";
         uses archive-object;
       }
       list user {
         key name;
         ordered-by user;
         description "Notify a user of the event";
         leaf name {
           description "Name of user to notify";
           type string {
           }
         }
         uses apply-advanced;
         list contents {
           key name;
           uses syslog-object;
         }
         leaf match {
           description "Regular expression for lines to be logged";
           type jt:regular-expression;
         }
         leaf allow-duplicates {
           description "Do not suppress the repeated message";
           type empty;
         }
         leaf-list match-strings {
           ordered-by user;
           description "Matching string(s) for lines to be logged";
           type string;
           max-elements 50;
         }
       }
       list host {
         key name;
         ordered-by user;
         description "Host to be notified";
         leaf name {
           description "Name of host to notify";
           type string;
         }
         uses apply-advanced;
         list contents {
           key name;
           uses syslog-object;
         }
         leaf match {
           description "Regular expression for lines to be logged";
           type jt:regular-expression;
         }
         leaf allow-duplicates {
           description "Do not suppress the repeated message";
           type empty;
         }
         leaf port {
           description "Port number";
           type union {
             type uint16;
             type string {
               pattern "<.*>|$.*";
             }
           }
         }
         leaf facility-override {
           description "Alternate facility for logging to remote host";
           type enumeration {
             enum "authorization" {
               description "Authorization system";
             }
             enum "daemon" {
               description "Various system processes";
             }
             enum "ftp" {
               description "FTP process";
             }
             enum "kernel" {
               description "Kernel";
             }
             enum "user" {
               description "User processes";
             }
             enum "local0" {
               description "Local logging option number 0";
             }
             enum "local1" {
               description "Local logging option number 1";
             }
             enum "local2" {
               description "Local logging option number 2";
             }
             enum "local3" {
               description "Local logging option number 3";
             }
             enum "local4" {
               description "Local logging option number 4";
             }
             enum "local5" {
               description "Local logging option number 5";
             }
             enum "local6" {
               description "Local logging option number 6";
             }
             enum "local7" {
               description "Local logging option number 7";
             }
           }
         }
         leaf log-prefix {
           description "Prefix for all logging to this host";
           type string {
           }
         }
         leaf source-address {
           description "Use specified address as source address";
           type jt:ipaddr;
         }
         leaf explicit-priority {
           description "Include priority and facility in messages";
           type empty;
         }
         leaf exclude-hostname {
           description "Exclude hostname field in messages";
           type empty;
         }
         leaf transport {
           description "Transport type";
           default "udp";
           type enumeration {
             enum "tcp" {
               description "TCP as transport for syslog";
             }
             enum "udp" {
               description "UDP as transport for syslog";
             }
             enum "tls" {
               description "TLS as transport for syslog";
             }
           }
         }
         leaf-list match-strings {
           ordered-by user;
           description "Matching string(s) for lines to be logged";
           type string;
           max-elements 50;
         }
         container structured-data {
           presence "enable structured-data";
           description "Log system message in structured format";
           uses apply-advanced;
           choice format {
             case case_1 {
               leaf brief {
                 description "Omit English-language text from end of logged message";
                 type empty;
               }
             }
           }
         }
       }
       leaf allow-duplicates {
         description "Do not suppress the repeated message for all targets";
         type empty;
       }
       list file {
         key name;
         description "File in which to log data";
         leaf name {
           description "Name of file in which to log data";
           type string {
             length "1 .. 1024";
           }
         }
         uses apply-advanced;
         list contents {
           key name;
           uses syslog-object;
         }
         leaf match {
           description "Regular expression for lines to be logged";
           type jt:regular-expression;
         }
         leaf allow-duplicates {
           description "Do not suppress the repeated message";
           type empty;
         }
         container archive {
           description "Archive file information";
           presence "enable archive";
           uses archive-object;
         }
         leaf explicit-priority {
           description "Include priority and facility in messages";
           type empty;
         }
         leaf-list match-strings {
           ordered-by user;
           description "Matching string(s) for lines to be logged";
           type string;
           max-elements 50;
         }
         container structured-data {
           presence "enable structured-data";
           description "Log system message in structured format";
           uses apply-advanced;
           choice format {
             case case_1 {
               leaf brief {
                 description "Omit English-language text from end of logged message";
                 type empty;
               }
             }
           }
         }
       }
       list console {
         key name;
         description "Console logging";
         leaf name {
           description "Facility type";
           type enumeration {
             enum "any" {
               description "All facilities";
             }
             enum "authorization" {
               description "Authorization system";
             }
             enum "daemon" {
               description "Various system processes";
             }
             enum "ftp" {
               description "FTP process";
             }
             enum "ntp" {
               description "NTP process";
             }
             enum "security" {
               description "Security related";
             }
             enum "kernel" {
               description "Kernel";
             }
             enum "user" {
               description "User processes";
             }
             enum "dfc" {
               description "Dynamic flow capture";
             }
             enum "external" {
               description "Local external applications";
             }
             enum "firewall" {
               description "Firewall filtering system";
             }
             enum "pfe" {
               description "Packet Forwarding Engine";
             }
             enum "conflict-log" {
               description "Configuration conflict log";
             }
             enum "change-log" {
               description "Configuration change log";
             }
             enum "interactive-commands" {
               description "Commands executed by the UI";
             }
             enum "application-status" {
               description "Application stop / start status";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       container time-format {
         presence "enable time-format";
         description "Additional information to include in system log timestamp";
         leaf year {
           description "Include year in timestamp";
           type empty;
         }
         leaf millisecond {
           description "Include milliseconds in timestamp";
           type empty;
         }
       }
       leaf source-address {
         description "Use specified address as source address";
         type jt:ipaddr;
       }
       leaf log-rotate-frequency {
         description "Rotate log frequency";
         default "15";
         units "minutes";
         type union {
           type string {
             pattern "<.*>|$.*";
           }
           type uint32 {
             range "1 .. 59";
           }
         }
       }
       container server {
         presence "enable server";
         description "Enable syslog server";
         uses apply-advanced;
         list routing-instances {
           key name;
           ordered-by user;
           description "Enable/disable syslog server in routing-instances";
           leaf name {
             description "Routing instance name";
             type string;
           }
           uses apply-advanced;
           container disable {
             presence "enable disable";
             description "Disable syslog server in this routing instance";
           }
         }
       }
       leaf alternate-format {
         description "Append node name with daemon name instead of hostname(default) in the log entries";
         type empty;
       }
     }
     choice compress-configuration-files-choice {
       leaf compress-configuration-files {
         description "Compress the router configuration files";
         type empty;
       }
       leaf no-compress-configuration-files {
         description "Don't compress the router configuration files";
         type empty;
       }
     }
     container license {
       description "License information for the router";
       uses license-object;
     }
     container kernel-options {
       description "Kernel options: selectively enable few knobs";
       uses apply-advanced;
       leaf select-active-unilist-member {
         description "Select active unilist member for host path forwarding";
         status deprecated;
         type empty;
       }
     }
     leaf netlink-async-mode {
       description "Enable async mode in nlsd";
       type empty;
     }
     container snapshot {
       description "System snapshot";
       uses apply-advanced;
       container recovery {
         description "System snapshot recovery management";
         uses apply-advanced;
         leaf on-upgrade {
           description "Update the recovery snapshot when the JUNOS release changes";
           type empty;
         }
         leaf configuration-only {
           description "Save configuration only, snapshot updated when out-of-date";
           type empty;
         }
         choice automatic-choice {
           leaf automatic {
             description "Automatically recover junos volume when necessary";
             type empty;
           }
           leaf no-automatic {
             description "Don't automatically recover junos volume when necessary";
             type empty;
           }
         }
         leaf-list configuration-preference {
           ordered-by user;
           description "Configuration to use when booting a snapshot from OAM";
           type enumeration {
             enum "config" {
               description "Use '/config/juniper.conf.gz' if available";
             }
             enum "snapshot" {
               description "Use configuration saved in snapshot";
             }
           }
         }
       }
       choice configuration-choice {
         leaf configuration {
           description "Save configuration in snapshot";
           type empty;
         }
         leaf no-configuration {
           description "Don't save configuration in snapshot";
           type empty;
         }
       }
     }
     container processes {
       description "Process control";
       uses apply-advanced;
       container dhcp-service {
         presence "enable dhcp-service";
         description "DHCP service process";
         uses apply-advanced;
         choice enable-disable {
           case case_1 {
             leaf disable {
               description "Disable dhcp-service process";
               type empty;
             }
           }
         }
         container traceoptions {
           description "Traceoptions for DHCP";
           uses jdhcp-traceoptions-level-type;
         }
       }
       container routing {
         description "Routing process";
         uses apply-advanced;
         container bgp {
           description "BGP protocol control";
           uses apply-advanced;
           container rib-sharding {
             presence "enable rib-sharding";
             description "Enable BGP RIB sharding";
             uses apply-advanced;
             leaf number-of-shards {
               description "Set number of sharding threads";
               type union {
                 type string {
                   pattern "<.*>|$.*";
                 }
                 type uint32 {
                   range "1 .. 31";
                 }
               }
             }
           }
           container update-threading {
             presence "enable update-threading";
             description "Enable BGP update threading";
             uses apply-advanced;
             leaf number-of-threads {
               description "Set number of update threads";
               type union {
                 type string {
                   pattern "<.*>|$.*";
                 }
                 type uint32 {
                   range "1 .. 128";
                 }
               }
             }
             leaf group-split-size {
               description "Threshold value to assign a new update thread for group";
               type union {
                 type string {
                   pattern "<.*>|$.*";
                 }
                 type uint32 {
                   range "0 .. 2000";
                 }
               }
             }
           }
           leaf tcp-listen-port {
             description "TCP port number to accept incoming BGP connections";
             type union {
               type string {
                 pattern "<.*>|$.*";
               }
               type uint16 {
                 range "1 .. 65535";
               }
             }
           }
         }
       }
     }
   }
   grouping archive-object {
     uses apply-advanced;
     leaf size {
       description "Size of files to be archived";
       units "bytes";
       type string;
     }
     leaf files {
       description "Number of files to be archived";
       type string;
     }
     choice world-readable-choice {
       leaf world-readable {
         description "Allow any user to read the log file";
         type empty;
       }
       leaf no-world-readable {
         description "Don't allow any user to read the log file";
         type empty;
       }
     }
     choice binary-data-choice {
       leaf binary-data {
         description "Mark file as if it contains binary data";
         type empty;
       }
       leaf no-binary-data {
         description "Don't mark file as if it contains binary data";
         type empty;
       }
     }
     leaf transfer-interval {
       description "Frequency at which to transfer files to archive sites";
       units "minutes";
       type union {
         type string {
           pattern "<.*>|$.*";
         }
         type uint32 {
           range "5 .. 2880";
         }
       }
     }
     leaf start-time {
       description "Start time for file transmission (yyyy-mm-dd.hh:mm)";
       type jt:time;
     }
     list archive-sites {
       key name;
       ordered-by user;
       leaf name {
         description "Primary and failover URLs to receive archive files";
         type string;
       }
       leaf password {
         description "Password for login into the archive site";
         type jt:unreadable;
       }
       leaf routing-instance {
         description "Routing instance";
         type string {
         }
       }
     }
   }
   grouping authentication-object {
     description "Authentication method";
     uses apply-advanced;
     leaf plain-text-password-value {
       description "Plain text password";
       type string;
     }
     leaf encrypted-password {
       description "Encrypted password string";
       type string {
         length "1 .. 128";
       }
     }
     leaf no-public-keys {
       description "Disables SSH public key based authentication";
       type empty;
     }
     list ssh-rsa {
       key name;
       ordered-by user;
       description "Secure shell (SSH) RSA public key string";
       leaf name {
         description "Secure shell (SSH) RSA public key string";
         type string {
         }
       }
       uses apply-advanced;
       leaf key-options {
         description "SSH key options";
         type string;
       }
       leaf from {
         description "Pattern-list of allowed hosts";
         type string {
         }
       }
     }
     list ssh-dsa {
       key name;
       ordered-by user;
       description "Secure shell (SSH) DSA public key string";
       status deprecated;
       leaf name {
         description "Secure shell (SSH) DSA public key string";
         type string {
         }
       }
       uses apply-advanced;
       leaf key-options {
         description "SSH key options";
         type string;
       }
       leaf from {
         description "Pattern-list of allowed hosts";
         type string {
         }
       }
     }
     list ssh-ecdsa {
       key name;
       ordered-by user;
       description "Secure shell (SSH) ECDSA public key string";
       leaf name {
         description "Secure shell (SSH) ECDSA public key string";
         type string {
         }
       }
       uses apply-advanced;
       leaf key-options {
         description "SSH key options";
         type string;
       }
       leaf from {
         description "Pattern-list of allowed hosts";
         type string {
         }
       }
     }
     list ssh-ed25519 {
       key name;
       ordered-by user;
       description "Secure shell (SSH) ED25519 public key string";
       leaf name {
         description "Secure shell (SSH) EC25519 public key string";
         type string {
         }
       }
       uses apply-advanced;
       leaf key-options {
         description "SSH key options";
         type string;
       }
       leaf from {
         description "Pattern-list of allowed hosts";
         type string {
         }
       }
     }
   }
   grouping jdhcp-traceoptions-level-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping ldp-sync-obj {
     uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping ldp_filter_obj {
     description "Filter to apply to tracing";
     leaf match-on {
       description "Argument on which to match";
       type enumeration {
         enum "fec" {
           description "Filter based on FEC associated to the traced object.";
         }
         enum "address" {
           description "Filter based on packet source and destination addresses.";
         }
       }
       mandatory true;
     }
     leaf-list policy {
       ordered-by user;
       description "Filter policy";
       type jt:policy-algebra;
     }
   }
   grouping license-object {
     description "License configuration for this router";
     uses apply-advanced;
     container autoupdate {
       presence "enable autoupdate";
       description "Autoupdate license keys from license servers";
       uses apply-advanced;
       list url {
         key name;
         ordered-by user;
         description "URL of a license server";
         max-elements 10;
         leaf name {
           description "URL of a license server for license keys";
           type string;
         }
         leaf password {
           description "Password of URL for a license server";
           type jt:unreadable;
         }
       }
     }
     container log-frequency {
       description "Generate a syslog message for nagging";
       choice time_choice {
         case case_1 {
           leaf time-of-day {
             description "Time of day at which to log nag message (hh:mm)";
             type jt:time-of-day;
           }
         }
         case case_2 {
           leaf time-interval {
             description "Frequency for logging nag message (multiples of 60)";
             units "seconds";
             type union {
               type string {
                 pattern "<.*>|$.*";
               }
               type uint32 {
                 range "60 .. 86400";
               }
             }
           }
         }
       }
     }
     container renew {
       presence "enable renew";
       description "License renew lead time and checking interval";
       leaf before-expiration {
         description "License renew lead time before expiration in days";
         type union {
           type string {
             pattern "<.*>|$.*";
           }
           type uint32 {
             range "0 .. 60";
           }
         }
         mandatory true;
       }
       leaf interval {
         description "License checking interval in hours";
         type union {
           type string {
             pattern "<.*>|$.*";
           }
           type uint32 {
             range "1 .. 336";
           }
         }
         mandatory true;
       }
     }
     container traceoptions {
       description "Trace options for licenses";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "all" {
               description "Trace all operations";
             }
             enum "events" {
               description "Trace licensing events and their processing";
             }
             enum "config" {
               description "Trace license configuration processing";
             }
           }
         }
       }
     }
     container keys {
       presence "enable keys";
       description "License keys";
       uses apply-advanced;
       list key {
         key name;
         ordered-by user;
         description "License key";
         leaf name {
           description "License key";
           type string;
         }
         uses apply-advanced;
       }
     }
     choice mode-selection {
       case case_1 {
         leaf standalone-mode {
           description "Forcing the node to standalone licensing";
           type empty;
         }
       }
     }
   }
   grouping log-object {
     description "Configure auditable security logs";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
   }
   grouping login-class-object {
     leaf name {
       description "Login class name";
       type string {
       }
     }
     uses apply-advanced;
     leaf-list allowed-days {
       ordered-by user;
       description "Day(s) of week when access is allowed.";
       type enumeration {
         enum "sunday" {
           description "Sunday";
         }
         enum "monday" {
           description "Monday";
         }
         enum "tuesday" {
           description "Tuesday";
         }
         enum "wednesday" {
           description "Wednesday";
         }
         enum "thursday" {
           description "Thursday";
         }
         enum "friday" {
           description "Friday";
         }
         enum "saturday" {
           description "Saturday";
         }
       }
     }
     leaf access-start {
       description "Start time for remote access (hh:mm)";
       type jt:time-of-day;
     }
     leaf access-end {
       description "End time for remote access (hh:mm)";
       type jt:time-of-day;
     }
     leaf idle-timeout {
       description "Maximum idle time before logout";
       units "minutes";
       type union {
         type uint32;
         type string {
           pattern "<.*>|$.*";
         }
       }
     }
     leaf logical-system {
       description "Logical system associated with login";
       type string;
     }
     leaf tenant {
       description "Tenant associated with this login";
       type string;
     }
     leaf login-alarms {
       description "Display system alarms when logging in";
       type empty;
     }
     leaf login-script {
       description "Execute this login-script when logging in";
       type string;
     }
     leaf login-tip {
       description "Display tip when logging in";
       type empty;
     }
     leaf no-sftp-server {
       description "Disable incoming SFTP connections";
       type empty;
     }
     leaf-list permissions {
       ordered-by user;
       type string;
     }
     leaf allow-commands {
       description "Regular expression for commands to allow explicitly";
       type jt:regular-expression;
     }
     leaf deny-commands {
       description "Regular expression for commands to deny explicitly";
       type jt:regular-expression;
     }
     leaf allow-configuration {
       description "Regular expression for configure to allow explicitly";
       type jt:regular-expression;
     }
     leaf deny-configuration {
       description "Regular expression for configure to deny explicitly";
       type jt:regular-expression;
     }
     leaf-list allow-commands-regexps {
       ordered-by user;
       description "Object path regular expressions to allow commands";
       type string;
     }
     leaf-list deny-commands-regexps {
       ordered-by user;
       description "Object path regular expressions to deny commands";
       type string;
     }
     leaf-list allow-configuration-regexps {
       ordered-by user;
       description "Object path regular expressions to allow";
       type string;
     }
     leaf-list deny-configuration-regexps {
       ordered-by user;
       description "Object path regular expressions to deny";
       type string;
     }
     leaf allow-configuration-exact-match {
       description "Regular expression for configure to allow exact match explicitly";
       type jt:regular-expression;
     }
     leaf deny-configuration-exact-match {
       description "Regular expression for configure to deny exact match explicitly";
       type jt:regular-expression;
     }
     leaf-list allow-grpc-rpc-regexps {
       ordered-by user;
       description "Regular expressions of gRPC rpcs to be allowed";
       type string;
     }
     leaf-list deny-grpc-rpc-regexps {
       ordered-by user;
       description "Regular expressions of gRPC rpcs to be denied";
       type string;
     }
     leaf configuration-breadcrumbs {
       description "Enable breadcrumbs during display of configuration";
       type empty;
     }
     list confirm-commands {
       key name;
       ordered-by user;
       description "List of commands to be confirmed explicitly";
       leaf name {
         description "Regular expression for confirm commands";
         type jt:regular-expression;
       }
       uses apply-advanced;
       leaf message {
         description "Message to be displayed during confirmation";
         type string;
       }
     }
     choice hidden-commands {
       case case_1 {
         leaf allow-hidden-commands {
           description "Allow all hidden commands to be executed";
           type empty;
         }
       }
       case case_2 {
         container no-hidden-commands {
           description "Deny all hidden commands with exemptions";
           uses apply-advanced;
           list except {
             key name;
             ordered-by user;
             description "Specify the list of hidden command to be exempted";
             leaf name {
               description "Exempted hidden command(s)";
               type string;
             }
             uses apply-advanced;
           }
         }
       }
     }
     container cli {
       uses apply-advanced;
       leaf prompt {
         description "Cli prompt name for this class";
         type string {
           length "1 .. 255";
         }
       }
       container timestamp {
         presence "enable timestamp";
         description "Cli Timestamp for this class (default format is '%b %d %T')";
         uses apply-advanced;
         leaf format {
           description "Timestamp format (default is '%b %d %T')";
           default "%b %d %T";
           type string {
           }
         }
       }
     }
     leaf web-ui-hidden-menus {
       description "Hidden menus in web user interface";
       type string;
     }
     leaf web-ui-read-only-menus {
       description "Read only menus in web user interface";
       type string;
     }
     leaf security-role {
       description "Common Criteria security role";
       type enumeration {
         enum "audit-administrator" {
           description "Audit administrator";
         }
         enum "crypto-administrator" {
           description "Cryptographic administrator";
         }
         enum "ids-administrator" {
           description "IDS administrator";
         }
         enum "security-administrator" {
           description "Security administrator";
         }
       }
     }
   }
   grouping login-user-object {
     leaf name {
       description "User name (login)";
       type string {
       }
     }
     uses apply-advanced;
     leaf full-name {
       description "Full name";
       type string {
         length "1 .. 255";
       }
     }
     container cli {
       uses apply-advanced;
       leaf prompt {
         description "Cli prompt name for this user";
         type string {
           length "1 .. 255";
         }
       }
       container timestamp {
         presence "enable timestamp";
         description "Cli Timestamp for this class (default format is '%b %d %T')";
         uses apply-advanced;
         leaf format {
           description "Timestamp format (default is '%b %d %T')";
           default "%b %d %T";
           type string {
           }
         }
       }
       choice allow-syslog-output-choice {
         leaf allow-syslog-output {
           description "Enable monitor and syslog output";
           type empty;
         }
         leaf no-allow-syslog-output {
           description "Don't enable monitor and syslog output";
           type empty;
         }
       }
     }
     leaf uid {
       description "User identifier (uid)";
       type union {
         type string {
           pattern "<.*>|$.*";
         }
         type uint32 {
           range "100 .. 64000";
         }
       }
     }
     leaf class {
       description "Login class";
       type string {
       }
       mandatory true;
     }
     container authentication {
       description "Authentication method";
       uses authentication-object;
     }
     leaf-list authorized-principals {
       ordered-by user;
       description "List of authorized principals";
       type string;
     }
     leaf authorized-principals-file {
       description "File containing list of authorized principals";
       type string;
     }
   }
   grouping lsp_nh_obj {
     leaf name {
       description "LSP to use to reach destination";
       type string;
       mandatory true;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     leaf allow {
       type empty;
     }
   }
   grouping metric_expression_type {
     uses apply-advanced;
     container metric {
       description "Parameters for metric attribute";
       leaf multiplier {
         description "Coefficient for metric attribute";
         type decimal64 {
           fraction-digits 9;
         }
       }
       leaf offset {
         description "Offset for metric attribute";
         type union {
           type int32;
           type string {
             pattern "<.*>|$.*";
           }
         }
       }
     }
     container metric2 {
       description "Parameters for metric2 attribute";
       leaf multiplier {
         description "Coefficient for metric2 attribute";
         default "1.0";
         type decimal64 {
           fraction-digits 9;
         }
       }
       leaf offset {
         description "Offset for metric2 attribute";
         type union {
           type int32;
           type string {
             pattern "<.*>|$.*";
           }
         }
       }
     }
   }
   grouping mpls_filter {
     description "Define a MPLS firewall filter";
     leaf name {
       description "Filter name";
       type string {
         length "1 .. 127";
       }
     }
     uses apply-advanced;
     list term {
       key name;
       ordered-by user;
       description "Define a firewall term";
       max-elements 16;
       leaf name {
         description "Term name";
         type string {
           length "1 .. 127";
         }
       }
       uses apply-advanced;
       container from {
         description "Define match criteria";
         uses apply-advanced;
         leaf exp {
           description "Match MPLS EXP bits - Range of values between 0 and 7 in decimal, hex or binary";
           type string {
           }
         }
         leaf label {
           description "Match MPLS label value - Range of values between 0 and 1048575 in decimal or hex";
           type string {
           }
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
         }
         leaf count {
           description "Count the packet in the named counter";
           type string {
             length "1 .. 127";
           }
         }
         leaf log {
           description "Log the packet";
           type empty;
         }
         leaf syslog {
           description "System log (syslog) information about the packet";
           type empty;
         }
       }
     }
   }
   grouping mrp-trace-options {
     description "Trace options for MMRP Protocol";
     uses apply-advanced;
     container file {
       description "Trace file options";
       leaf filename {
         description "Name of file in which to write trace information";
         type string {
           length "1 .. 1024";
         }
         //mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "events" {
             description "Trace events to the protocol state machine";
           }
           enum "pdu" {
             description "Trace RAPS PDU reception and transmission";
           }
           enum "timers" {
             description "Trace protocol timers";
           }
           enum "state-machine" {
             description "Trace information of the state machine";
           }
           enum "socket" {
             description "Trace soccket activity";
           }
           enum "error" {
             description "Trace all failure conditions";
           }
           enum "all" {
             description "Trace all";
           }
         }
       }
       leaf disable {
         description "Disable this trace flag";
         type empty;
       }
     }
   }
   grouping network_type {
     leaf name {
       description "Network prefix";
       type jt:ipprefix;
     }
     uses apply-advanced;
     leaf-list dyn-tunnel-attribute-policy {
       ordered-by user;
       description "Import policy for dynamic-tunnel under this destination network";
       type jt:policy-algebra;
     }
     leaf preference {
       description "Preference of tunnel route under this destination network";
       type union {
         type uint32;
         type string {
           pattern "<.*>|$.*";
         }
       }
     }
     leaf-list colors {
       ordered-by user;
       description "Set of color list that will be supported for tunnel creation";
       type union {
         type uint32;
         type string {
           pattern "<.*>|$.*";
         }
       }
     }
     leaf best-effort {
       description "Best-effort transport class";
       type empty;
     }
   }
   grouping output-plugin {
     leaf name {
       description "Plugin name";
       type string;
     }
     uses apply-advanced;
     list parameters {
       key name;
       ordered-by user;
       description "List of key:value parameters for plugin";
       uses parameter-pair;
     }
   }
   grouping override-type {
     description "DHCP override processing";
     uses apply-advanced;
     leaf no-unicast-replies {
       description "Overwrite unicast bit in incoming packet, when present";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       status deprecated;
       type string {
         length "1 .. 252";
       }
     }
     leaf include-option-82-in-vsa {
       description "Include option 82 in Dhcp-Options RADIUS VSA";
       type empty;
     }
     leaf layer2-unicast-replies {
       description "Do not broadcast client responses";
       type empty;
     }
     leaf trust-option-82 {
       description "Trust options-82 option";
       type empty;
     }
     leaf delay-authentication {
       description "Delay subscriber authentication in DHCP protocol processing until request packet";
       type empty;
     }
     leaf interface-client-limit {
       description "Limit the number of client allowed on an interface";
       type union {
         type string {
           pattern "<.*>|$.*";
         }
         type uint32 {
           range "1 .. 500000";
         }
       }
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     leaf send-release-on-delete {
       description "Always send RELEASE to the server when a binding is deleted";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping parameter-pair {
     leaf name {
       description "Parameter key";
       type string;
     }
     uses apply-advanced;
     leaf value {
       description "Parameter value";
       type string;
     }
   }
   grouping periodic_oam {
     uses apply-advanced;
     container mpls-tp-mode {
       presence "enable mpls-tp-mode";
       description "MPLS-TP Mode, Do not use IP addressing for OAM";
       uses apply-advanced;
       container lsping-channel-type {
         description "Supported Control-channel types for MPLS-TP mode....";
         uses apply-advanced;
         choice action-choice {
           case case_1 {
             leaf ipv4 {
               description "Use channel-type IPv4(0x0021), With IP-UDP encapsulation";
               type empty;
             }
           }
           case case_2 {
             leaf on-demand-cv {
               description "Use channel-type On-Demand-CV(0x0025), Without IP-UDP encapsulation";
               type empty;
             }
           }
         }
       }
     }
     container bfd-port {
       description "Egress knob to select MHOP-BFD port for MPLS BFD";
       uses apply-advanced;
       leaf-list import {
         ordered-by user;
         description "Import policy";
         type jt:policy-algebra;
       }
     }
     container bfd-liveness-detection {
       description "Bidirectional Forwarding Detection options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container failure-action {
         description "Action to take when BFD session goes down";
         choice action-choice {
           case case_1 {
             leaf teardown {
               description "Teardown label switched path and resignal";
               type empty;
             }
           }
           case case_2 {
             container make-before-break {
               presence "enable make-before-break";
               description "Resignal the label switched path before teardown";
               uses apply-advanced;
               leaf teardown-timeout {
                 description "Time to wait before teardown";
                 units "seconds";
                 type union {
                   type string {
                     pattern "<.*>|$.*";
                   }
                   type uint32 {
                     range "0 .. 65535";
                   }
                 }
               }
             }
           }
         }
       }
       leaf no-router-alert-option {
         description "Do not set Router-Alert options in IP header for MPLS-BFD";
         type empty;
       }
       leaf use-ip-ttl-1 {
         description "Set TTL value to 1 in IP header for MPLS-BFD";
         type empty;
       }
     }
     container performance-monitoring {
       description "Performance monitoring options";
       uses apply-advanced;
       container traceoptions {
         description "Trace options for PM";
         uses apply-advanced;
         container file {
           description "Trace file options";
           leaf filename {
             description "Name of file in which to write trace information";
             type string {
               length "1 .. 1024";
             }
             //mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "init" {
                 description "Trace init commnad";
               }
               enum "error" {
                 description "Trace error conditions";
               }
               enum "event" {
                 description "Trace state machine events";
               }
               enum "general" {
                 description "Trace general events";
               }
               enum "packet" {
                 description "Trace various packets ";
               }
               enum "timer" {
                 description "Trace timer processing";
               }
               enum "all" {
                 description "Trace everything";
               }
             }
           }
         }
       }
       container querier {
         description "Querier options";
         uses apply-advanced;
         container loss {
           description "Loss measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic class";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
           }
         }
         container delay {
           description "Delay measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic classes";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
         container loss-delay {
           description "Combined loss-delay measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic classes";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
       }
       container responder {
         description "Responder options";
         uses apply-advanced;
         container loss {
           description "Loss measurement options";
           uses apply-advanced;
           leaf min-query-interval {
             description "Minimum query interval";
             units "milliseconds";
             type union {
               type string {
                 pattern "<.*>|$.*";
               }
               type uint32 {
                 range "1000 .. 4294967295";
               }
             }
           }
         }
         container delay {
           description "Delay measurement options";
           uses apply-advanced;
           leaf min-query-interval {
             description "Minimum query interval";
             units "milliseconds";
             type union {
               type string {
                 pattern "<.*>|$.*";
               }
               type uint32 {
                 range "1000 .. 4294967295";
               }
             }
           }
         }
       }
     }
   }
   grouping prefix_list_items {
     leaf name {
       description "Address prefix";
       type jt:ipprefix-only;
     }
     uses apply-advanced;
   }
   grouping programmable-rpd-type {
     uses apply-advanced;
     container traceoptions {
       description "Trace options";
       uses apply-advanced;
       container file {
         description "Trace file options";
         leaf filename {
           description "Name of file in which to write trace information";
           type string {
             length "1 .. 1024";
           }
           //mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "client" {
               description "Client events";
             }
             enum "japi" {
               description "JAPI related traces";
             }
             enum "routing-interface" {
               description "Routing interface traces";
             }
             enum "te-path-compute" {
               description "TE Path Computation traces";
             }
             enum "statistics" {
               description "Statistics related traces";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     container purge-timeout {
       presence "enable purge-timeout";
       description "Purge timeout for all programmable-rpd clients in seconds";
       choice purge-parm {
         case case_1 {
           leaf never {
             description "Client programmed objects are never purged";
             type empty;
           }
         }
         case case_2 {
           leaf timeout {
             description "Timeout value, in seconds, for purging client programmed objects";
             units "seconds";
             type union {
               type string {
                 pattern "<.*>|$.*";
               }
               type uint32 {
                 range "1 .. 604800";
               }
             }
           }
         }
       }
     }
     list client {
       key name;
       ordered-by user;
       description "Programmable-rpd client options";
       leaf name {
         description "Client ID";
         type string {
           length "1 .. 255";
         }
       }
       uses apply-advanced;
       list interface-notification {
         key name;
         ordered-by user;
         description "Interfaces for notification";
         leaf name {
           description "Interface";
           type string {
             length "1 .. 32";
           }
         }
         uses apply-advanced;
       }
     }
     container rib-service {
       presence "enable rib-service";
       description "RIB service API options";
       uses apply-advanced;
       container dynamic-next-hop-interface {
         presence "enable dynamic-next-hop-interface";
         description "Update routes for next-hop interface changes";
         uses apply-advanced;
         choice enable-disable {
           case case_1 {
             leaf disable {
               description "Disable dynamic next-hop interface handling";
               type empty;
             }
           }
         }
       }
     }
     leaf stats-sampling-interval {
       description "Sampling interval for programmable rpd statisitics";
       default "30";
       units "seconds";
       type union {
         type string {
           pattern "<.*>|$.*";
         }
         type uint32 {
           range "30 .. 3600";
         }
       }
     }
     leaf stats-aggregation-interval {
       description "Aggregation interval for programmable rpd statistics";
       default "60";
       units "seconds";
       type union {
         type string {
           pattern "<.*>|$.*";
         }
         type uint32 {
           range "60 .. 3600";
         }
       }
     }
   }
   grouping qualified_nh_obj {
     leaf name {
       description "Next hop to destination";
       type union {
         type jt:ipaddr-or-interface;
         type string {
           pattern "<.*>|$.*";
         }
       }
       mandatory true;
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf order {
       description "Order of qualified next hop";
       type union {
         type string {
           pattern "<.*>|$.*";
         }
         type uint16 {
           range "1 .. 65535";
         }
       }
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       container echo {
         description "Echo mode parameters";
         uses apply-advanced;
         leaf minimum-interval {
           description "Minimum transmit and receive interval";
           units "milliseconds";
           type union {
             type string {
               pattern "<.*>|$.*";
             }
             type uint32 {
               range "100 .. 255000";
             }
           }
           //mandatory true;
         }
       }
       container echo-lite {
         description "Echo-lite more parameters";
         uses apply-advanced;
         leaf minimum-interval {
           description "Minimum transmit and receive interval";
           units "milliseconds";
           type union {
             type string {
               pattern "<.*>|$.*";
             }
             type uint32 {
               range "100 .. 255000";
             }
           }
           //mandatory true;
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping radius-server-object {
     leaf name {
       description "RADIUS server address";
       type jt:hostname;
     }
     uses apply-advanced;
     leaf routing-instance {
       description "Routing instance";
       type string {
       }
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "RADIUS server accounting port number";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
       mandatory true;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf no-message-authenticator {
       description "Do not deny login if Message-Authenticator is not present";
       type empty;
     }
     leaf source-address {
       description "Use specified address as source address";
       type jt:ipaddr;
     }
     container tls {
       description "Radius over TLS";
       uses apply-advanced;
       leaf-list trusted-ca-group {
         ordered-by user;
         description "Name of the trusted CA groups (maximum 20)";
         type string {
           length "1 .. 63";
         }
         max-elements 20;
       }
       container mutual-authentication {
         description "Enable TLS mutual authentication";
         uses apply-advanced;
         leaf certificate-id {
           description "Local Certificate ID";
           type string {
           }
           mandatory true;
         }
       }
     }
   }
   grouping relay-bulk-leasequery-v4-type {
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       container vlan-id-only {
         presence "enable vlan-id-only";
         description "Use only VLAN id";
         uses apply-advanced;
       }
       leaf no-vlan-interface-name {
         description "Not include vlan or interface name";
         type empty;
       }
       leaf include-irb-and-l2 {
         description "Include IRB and L2 interface name";
         type empty;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       container hostname-only {
         presence "enable hostname-only";
         description "Include hostname only";
         uses apply-advanced;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-remote-id {
         description "Keep incoming remote identifier";
         type empty;
       }
       leaf use-string {
         description "Use raw string instead of the default remote id";
         status deprecated;
         type string;
       }
     }
     leaf server-id-override {
       description "Add link-selection and server-id sub-options on packets to server";
       type empty;
     }
     leaf link-selection {
       description "Add link-selection suboption on packets to server";
       type empty;
     }
     leaf exclude-relay-agent-identifier {
       description "Exclude relay agent identifier from packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping rib-inet3 {
     uses apply-advanced;
     container inet.3 {
       presence "enable inet.3";
       description "Use inet.3 to exchange labeled unicast routes";
       uses apply-advanced;
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
           //mandatory true;
         }
       }
     }
     leaf protocol-instance-name {
       description "Name of protocol instance under routing instance";
       type string;
     }
     list route {
       key name;
       description "Individual route options";
       leaf name {
         description "Destination prefix";
         type jt:ipprefix;
       }
       uses apply-advanced;
       leaf description {
         description "Description for aggregate routes";
         type string {
         }
       }
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
           //mandatory true;
         }
       }
     }
   }
   grouping rib_group_inet_type {
     description "Routing table group";
     leaf ribgroup-name {
       description "Name of the routing table group";
       type string;
       //mandatory true;
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_list_items {
     leaf name {
       description "RIB name or wildcard";
       type string;
     }
     uses apply-advanced;
   }
   grouping rib_static_metric_type {
     leaf metric-value {
       description "Metric value";
       type union {
         type uint32;
         type string {
           pattern "<.*>|$.*";
         }
       }
       mandatory true;
     }
     leaf type {
       description "Metric type";
       type union {
         type string {
           pattern "<.*>|$.*";
         }
         type uint32 {
           range "1 .. 16";
         }
       }
     }
   }
   grouping rmopd-traceoptions {
     description "Trace options for remote-monitoring";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping route_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     leaf get-route-range {
       description "Get the range";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping rpd_rib_group_type {
     description "Routing table group";
     leaf name {
       description "Routing table group";
       type string;
     }
     uses apply-advanced;
     leaf export-rib {
       description "Export routing table";
       type string;
     }
     leaf-list import-rib {
       ordered-by user;
       description "Import routing table";
       type string;
     }
     leaf-list import-policy {
       ordered-by user;
       description "Import policy";
       type jt:policy-algebra;
     }
   }
   grouping rtf_prefix_list_items {
     leaf name {
       description "Family route-target prefix";
       type string {
         length "1 .. 63";
       }
     }
     uses apply-advanced;
   }
   grouping scripts_type {
     uses apply-advanced;
     container commit {
       description "Commit-time scripting mechanism";
       uses apply-advanced;
       leaf allow-transients {
         description "Allow loading of transient configuration changes";
         type empty;
       }
       container traceoptions {
         description "Trace options for commit scripts";
         uses script_traceoptions;
       }
       leaf refresh {
         description "Refresh all operation scripts from their source";
         type empty;
       }
       leaf refresh-from {
         description "Refresh all operation scripts from a given base URL";
         type string {
           length "1 .. 254";
         }
       }
       leaf max-datasize {
         description "Maximum data segment size for scripts execution";
         units "bytes";
         type string;
       }
       leaf direct-access {
         description "Access the configuration directly from database";
         type empty;
       }
       container dampen {
         presence "enable dampen";
         description "Dampen execution of commit scripts";
         uses apply-advanced;
         container dampen-options {
           description "Dampen options for commit scripts";
           uses apply-advanced;
           leaf cpu-factor {
             description "CPU factor at which to pause";
             type union {
               type string {
                 pattern "<.*>|$.*";
               }
               type uint32 {
                 range "1 .. 100";
               }
             }
           }
           leaf line-interval {
             description "Line interval at which to pause";
             type union {
               type string {
                 pattern "<.*>|$.*";
               }
               type uint32 {
                 range "1 .. 4294967295";
               }
             }
           }
           leaf time-interval {
             description "Time to pause";
             units "microseconds";
             type union {
               type string {
                 pattern "<.*>|$.*";
               }
               type uint32 {
                 range "1 .. 4294967295";
               }
             }
           }
         }
       }
       list file {
         key name;
         ordered-by user;
         description "Commit script file";
         uses commit_scripts_file_type;
       }
     }
     container op {
       description "Operations scripting";
       uses apply-advanced;
       leaf refresh {
         description "Refresh all operation scripts from their source";
         type empty;
       }
       leaf refresh-from {
         description "Refresh all operation scripts from a given base URL";
         type string {
           length "1 .. 254";
         }
       }
       container traceoptions {
         description "Trace options for operation scripts";
         uses script_traceoptions;
       }
       list file {
         key name;
         description "Configuration for each operation script";
         uses op_scripts_file_type;
       }
       leaf no-allow-url {
         description "Do not allow the remote execution of op scripts";
         type empty;
       }
       leaf allow-url-for-python {
         description "Allow the remote execution of Python op scripts";
         type empty;
       }
       leaf max-datasize {
         description "Maximum data segment size for scripts execution";
         units "bytes";
         type string;
       }
       container dampen {
         presence "enable dampen";
         description "Dampen execution of op scripts";
         uses apply-advanced;
         container dampen-options {
           description "Dampen options for op scripts";
           uses apply-advanced;
           leaf cpu-factor {
             description "CPU factor at which to pause";
             type union {
               type string {
                 pattern "<.*>|$.*";
               }
               type uint32 {
                 range "1 .. 100";
               }
             }
           }
           leaf line-interval {
             description "Line interval at which to pause";
             type union {
               type string {
                 pattern "<.*>|$.*";
               }
               type uint32 {
                 range "1 .. 4294967295";
               }
             }
           }
           leaf time-interval {
             description "Time to pause";
             units "microseconds";
             type union {
               type string {
                 pattern "<.*>|$.*";
               }
               type uint32 {
                 range "1 .. 4294967295";
               }
             }
           }
         }
       }
       container start {
         description "Start op scripts with start-criteria check";
         uses apply-advanced;
         container start-options {
           description "Start options for op scripts";
           uses apply-advanced;
           leaf mem-factor {
             description "Memory factor at which to start/stop";
             type union {
               type string {
                 pattern "<.*>|$.*";
               }
               type uint32 {
                 range "1 .. 100";
               }
             }
           }
         }
       }
     }
     container translation {
       description "Translation scripts";
       uses apply-advanced;
       leaf max-datasize {
         description "Maximum data segment size for translation scripts execution";
         units "bytes";
         type string;
       }
     }
     container action {
       description "Action scripts";
       uses apply-advanced;
       leaf max-datasize {
         description "Maximum data segment size for action scripts execution";
         units "bytes";
         type string;
       }
     }
     leaf language {
       description "Allow/Disallow Python scripts on-box";
       type enumeration {
         enum "python" {
           description "Allow Python 2.x scripts on-box (Python2.x support will be deprecated in 21.1)";
         }
         enum "python3" {
           description "Allow Python 3.x scripts on-box";
         }
       }
     }
     leaf synchronize {
       description "Push all scripts to other RE on commit synchronize";
       type empty;
     }
   }
   grouping commit_scripts_file_type {
     leaf name {
       description "Local filename of the script file";
       type string {
         length "1 .. 254";
       }
     }
     uses apply-advanced;
     leaf optional {
       description "Allow commit to succeed if the script is missing";
       type empty;
     }
     leaf source {
       description "URL of source for this script";
       type string {
         length "1 .. 254";
       }
     }
     leaf cert-file {
       description "Specify the certificate file name";
       type string;
     }
     leaf routing-instance {
       description "Routing instance";
       type string {
       }
     }
     leaf refresh {
       description "Refresh all operation scripts from their source";
       type empty;
     }
     leaf refresh-from {
       description "Refresh all operation scripts from a given base URL";
       type string {
         length "1 .. 254";
       }
     }
     container checksum {
       description "Checksum of this script";
       uses apply-advanced;
       leaf sha-256 {
         description "SHA-256 checksum of this script";
         type string {
           length "1 .. 254";
         }
       }
     }
   }
   grouping op_scripts_file_type {
     leaf name {
       description "Local filename of the script file";
       type string {
         length "1 .. 254";
       }
     }
     uses apply-advanced;
     leaf command {
       description "Command alias for the script file";
       type string {
         length "1 .. 254";
       }
     }
     container dampen {
       presence "enable dampen";
       description "Dampen execution of the script";
       uses apply-advanced;
       container dampen-options {
         description "Dampen options for the script";
         uses apply-advanced;
         leaf cpu-factor {
           description "CPU factor at which to pause";
           type union {
             type string {
               pattern "<.*>|$.*";
             }
             type uint32 {
               range "1 .. 100";
             }
           }
         }
         leaf line-interval {
           description "Line interval at which to pause";
           type union {
             type string {
               pattern "<.*>|$.*";
             }
             type uint32 {
               range "1 .. 4294967295";
             }
           }
         }
         leaf time-interval {
           description "Time to pause";
           units "microseconds";
           type union {
             type string {
               pattern "<.*>|$.*";
             }
             type uint32 {
               range "1 .. 4294967295";
             }
           }
         }
       }
     }
     container start {
       description "Start op scripts with start-criteria check";
       uses apply-advanced;
       container start-options {
         description "Start options for the op script";
         uses apply-advanced;
         leaf mem-factor {
           description "Memory factor at which to start/stop";
           type union {
             type string {
               pattern "<.*>|$.*";
             }
             type uint32 {
               range "1 .. 100";
             }
           }
         }
       }
     }
     leaf description {
       description "Description of the script";
       type string {
         length "1 .. 254";
       }
     }
     leaf source {
       description "URL of source for this script";
       type string {
         length "1 .. 254";
       }
     }
     leaf cert-file {
       description "Specify the certificate file name";
       type string;
     }
     leaf routing-instance {
       description "Routing instance";
       type string {
       }
     }
     leaf allow-commands {
       description "Regular expression for commands to allow explicitly";
       type jt:regular-expression;
     }
     leaf refresh {
       description "Refresh all operation scripts from their source";
       type empty;
     }
     leaf refresh-from {
       description "Refresh all operation scripts from a given base URL";
       type string {
         length "1 .. 254";
       }
     }
     list arguments {
       key name;
       description "Command line argument to the script";
       leaf name {
         description "Name of the argument";
         type string {
           length "1 .. 254";
         }
       }
       uses apply-advanced;
       leaf description {
         description "Description of the argument";
         type string {
           length "1 .. 254";
         }
       }
     }
     container checksum {
       description "Checksum of this script";
       uses apply-advanced;
       leaf sha-256 {
         description "SHA-256 checksum of this script";
         type string {
           length "1 .. 254";
         }
       }
     }
   }
   grouping script_traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     list flag {
       key name;
       description "Tracing parameters";
       leaf name {
         type enumeration {
           enum "all" {
             description "Trace all operations";
           }
           enum "events" {
             description "Trace important events";
           }
           enum "input" {
             description "Trace script input data";
           }
           enum "offline" {
             description "Generate data for offline development";
           }
           enum "output" {
             description "Trace script output data";
           }
           enum "rpc" {
             description "Trace script RPCs";
           }
           enum "xslt" {
             description "Trace the XSLT library";
           }
         }
       }
     }
   }
   grouping security-ipsec-vpn {
     uses apply-advanced;
     container traceoptions {
       description "Trace options for IPSec data-plane debug";
       uses ipsec-traceoptions;
     }
     list security-association {
       key name;
       ordered-by user;
       description "Define an IPSec security association";
       uses ipsec-sa;
     }
   }
   grouping ipsec-sa {
     leaf name {
       description "Name of IPSec security association";
       type string {
         length "1 .. 32";
       }
     }
     uses apply-advanced;
     leaf description {
       description "Text description of security association";
       type string {
         length "1 .. 80";
       }
     }
     leaf mode {
       description "Define security association mode";
       default "transport";
       type enumeration {
         enum "transport" {
           description "Transport mode";
         }
         enum "tunnel" {
           description "Tunnel mode";
         }
       }
     }
     choice sa_choice {
       case case_1 {
         container manual {
           description "Define a manual security association";
           uses apply-advanced;
           list direction {
             key name;
             ordered-by user;
             description "Define the direction of the security association";
             leaf name {
               type enumeration {
                 enum "inbound" {
                   description "Inbound security association";
                 }
                 enum "outbound" {
                   description "Outbound security association";
                 }
                 enum "bidirectional" {
                   description "Bidirectional security association";
                 }
               }
             }
             uses apply-advanced;
             leaf protocol {
               description "Define an IPSec protocol for the security association";
               type enumeration {
                 enum "ah" {
                   description "Authentication header";
                 }
                 enum "esp" {
                   description "Encapsulated Security Payload header";
                 }
                 enum "bundle" {
                   description "Bundle (AH authentication plus ESP encryption)";
                 }
               }
               mandatory true;
             }
             leaf spi {
               description "Define security parameter index";
               type union {
                 type string {
                   pattern "<.*>|$.*";
                 }
                 type uint32 {
                   range "256 .. 16639";
                 }
               }
               mandatory true;
             }
             container authentication {
               description "Define authentication parameters";
               uses apply-advanced;
               leaf algorithm {
                 description "Define authentication algorithm";
                 type enumeration {
                   enum "hmac-md5-96" {
                     description "HMAC-MD5-96 authentication algorithm";
                   }
                   enum "hmac-sha1-96" {
                     description "HMAC-SHA1-96 authentication algorithm";
                   }
                   enum "hmac-sha2-256" {
                     description "HMAC-SHA2-256 authentication algorithm";
                   }
                   enum "hmac-sha-256-128" {
                     description "HMAC-SHA-256-128 authentication algorithm";
                   }
                 }
                 mandatory true;
               }
               container key {
                 description "Define an authentication key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                       }
                     }
                   }
                 }
               }
             }
             container encryption {
               description "Define encryption parameters";
               uses apply-advanced;
               leaf algorithm {
                 description "Define encryption algorithm";
                 type enumeration {
                   enum "des-cbc" {
                     description "DES-CBC encryption algorithm";
                   }
                   enum "3des-cbc" {
                     description "3DES-CBC encryption algorithm";
                   }
                   enum "aes-128-cbc" {
                     description "AES-CBC 128-bit encryption algorithm";
                   }
                   enum "aes-192-cbc" {
                     description "AES-CBC 192-bit encryption algorithm";
                   }
                   enum "aes-256-cbc" {
                     description "AES-CBC 256-bit encryption algorithm";
                   }
                 }
                 mandatory true;
               }
               container key {
                 description "Define an encryption key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                       }
                     }
                   }
                 }
               }
             }
           }
         }
       }
       case case_2 {
       }
     }
   }
   grouping ipsec-traceoptions {
     description "Data-plane IPSec tracing options";
     uses apply-advanced;
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping security-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
           enum "ams" {
             description "Trace AMS events";
           }
           enum "lic" {
             description "Trace License events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping server-group-type {
     uses apply-advanced;
     list server-group {
       key name;
       description "One or more server groups";
       leaf name {
         description "Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping source_address_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
   }
   grouping spring-te-template-map {
     description "SPRING-TE template color map";
     leaf name {
       description "Name of SPRING-TE template";
       type string;
       mandatory true;
     }
     uses apply-advanced;
     choice colors {
       case case_1 {
         leaf-list color {
           description "Set of color list to be mapped to corresponding SPRING-TE template";
           type union {
             type uint32;
             type string {
               pattern "<.*>|$.*";
             }
           }
         }
       }
       case case_2 {
         leaf color-any {
           description "Map any color to corresponding SPRING-TE template";
           type empty;
         }
       }
     }
   }
   grouping springte_lsp_nh_obj {
     uses apply-advanced;
     leaf nexthop {
       description "SPRING-TE LSP to use to reach destination";
       type string {
         length "1 .. 128";
       }
       mandatory true;
     }
     container lsp-source {
       description "Source of tunnel creation";
       uses apply-advanced;
       choice lsp-src-choice {
         case case_1 {
           leaf pcep {
             description "Path computation element protocol";
             type empty;
           }
         }
         case case_2 {
           leaf static {
             description "Static configuration";
             type empty;
           }
         }
         case case_3 {
           leaf dtm {
             description "Dynamic tunnel module";
             type empty;
           }
         }
         case case_4 {
           leaf bgp {
             description "BGP SRTE";
             type empty;
           }
         }
       }
     }
   }
   grouping syslog-object {
     leaf name {
       description "Facility type";
       type enumeration {
         enum "any" {
           description "All facilities";
         }
         enum "authorization" {
           description "Authorization system";
         }
         enum "daemon" {
           description "Various system processes";
         }
         enum "ftp" {
           description "FTP process";
         }
         enum "ntp" {
           description "NTP process";
         }
         enum "security" {
           description "Security related";
         }
         enum "kernel" {
           description "Kernel";
         }
         enum "user" {
           description "User processes";
         }
         enum "dfc" {
           description "Dynamic flow capture";
         }
         enum "external" {
           description "Local external applications";
         }
         enum "firewall" {
           description "Firewall filtering system";
         }
         enum "pfe" {
           description "Packet Forwarding Engine";
         }
         enum "conflict-log" {
           description "Configuration conflict log";
         }
         enum "change-log" {
           description "Configuration change log";
         }
         enum "interactive-commands" {
           description "Commands executed by the UI";
         }
       }
     }
     choice level {
       case case_1 {
         leaf any {
           description "All levels";
           type empty;
         }
       }
       case case_2 {
         leaf emergency {
           description "Panic conditions";
           type empty;
         }
       }
       case case_3 {
         leaf alert {
           description "Conditions that should be corrected immediately";
           type empty;
         }
       }
       case case_4 {
         leaf critical {
           description "Critical conditions";
           type empty;
         }
       }
       case case_5 {
         leaf error {
           description "Error conditions";
           type empty;
         }
       }
       case case_6 {
         leaf warning {
           description "Warning messages";
           type empty;
         }
       }
       case case_7 {
         leaf notice {
           description "Conditions that should be handled specially";
           type empty;
         }
       }
       case case_8 {
         leaf info {
           description "Informational messages";
           type empty;
         }
       }
       case case_9 {
         leaf none {
           description "No messages";
           type empty;
         }
       }
     }
   }
   grouping tacplus-server-object {
     leaf name {
       description "TACACS+ authentication server address";
       type jt:hostname;
     }
     uses apply-advanced;
     leaf routing-instance {
       description "Routing instance";
       type string {
       }
     }
     leaf port {
       description "TACACS+ authentication server port number";
       default "49";
       type union {
         type uint16;
         type string {
           pattern "<.*>|$.*";
         }
       }
     }
     leaf secret {
       description "Shared secret with the authentication server";
       type jt:unreadable;
     }
     leaf timeout {
       description "Request timeout period";
       default "3";
       units "seconds";
       type union {
         type string {
           pattern "<.*>|$.*";
         }
         type uint32 {
           range "1 .. 90";
         }
       }
     }
     leaf single-connection {
       description "Optimize TCP connection attempts";
       type empty;
     }
     leaf source-address {
       description "Use specified address as source address";
       type jt:hostname;
     }
   }
   grouping te-class-object {
     leaf traffic-class {
       description "Traffic class";
       type enumeration {
         enum "ct0" {
           description "Traffic class 0";
         }
         enum "ct1" {
           description "Traffic class 1";
         }
         enum "ct2" {
           description "Traffic class 2";
         }
         enum "ct3" {
           description "Traffic class 3";
         }
       }
       //mandatory true;
     }
     leaf priority {
       description "Preemption priority for this class";
       type union {
         type string {
           pattern "<.*>|$.*";
         }
         type uint32 {
           range "0 .. 7";
         }
       }
       //mandatory true;
     }
   }
   grouping three-color-policer-type {
     description "Three-color policer";
     leaf name {
       description "Policer name";
       type string {
       }
     }
     uses apply-advanced;
     container action {
       description "Action for three-color policer";
       uses apply-advanced;
       list loss-priority {
         key name;
         ordered-by user;
         description "Loss priority for packet";
         uses three-color-policer-action;
       }
     }
     choice rate-type-choice {
       case case_1 {
         container single-rate {
           description "Single-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic";
             units "bytes";
             type string;
           }
           leaf excess-burst-size {
             description "Burst size allowed for excess traffic";
             units "bytes";
             type string;
           }
         }
       }
       case case_2 {
         container two-rate {
           description "Two-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             units "bytes";
             type string;
           }
           leaf peak-information-rate {
             description "Bandwidth allowed for peak traffic";
             units "bits per second";
             type string;
           }
           leaf peak-burst-size {
             description "Burst size allowed for peak traffic  ";
             units "bytes";
             type string;
           }
         }
       }
     }
   }
   grouping three-color-policer-action {
     description "Action for three-color policer";
     leaf name {
       description "Loss priority for packet";
       type enumeration {
         enum "high" {
           description "High loss priority";
         }
       }
     }
     uses apply-advanced;
     container then {
       description "Action to take if the rate limits are exceeded";
       uses apply-advanced;
       leaf discard {
         description "Discard the packet";
         type empty;
       }
     }
   }
   grouping twamp-authentication-key-chain {
     leaf name {
       description "Name of authentication key chain";
       type string {
       }
     }
     uses apply-advanced;
     list key-id {
       key name;
       description "Authentication element configuration";
       leaf name {
         description "Authentication element identifier";
         type string {
           length "1 .. 80";
         }
       }
       uses apply-advanced;
       leaf secret {
         description "Authentication key";
         type string {
           length "1 .. 256";
         }
         mandatory true;
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       description "One or more server groups";
       leaf name {
         description "DHCPv6 Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     leaf priority {
       description "Virtual router election priority";
       type union {
         type string {
           pattern "<.*>|$.*";
         }
         type uint32 {
           range "0 .. 255";
         }
       }
     }
     leaf mode {
       type enumeration {
         enum "master" {
           description "VRRP mode master";
         }
         enum "backup" {
           description "VRRP mode backup";
         }
       }
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     leaf authentication-type {
       description "Authentication type";
       type enumeration {
         enum "simple" {
           description "Simple password";
         }
       }
     }
     leaf authentication-key {
       description "Authentication key";
       type string;
     }
     leaf virtual-mac-disable {
       description "Disable advertisement of virtual MAC address for configured virtual ip-address";
       type empty;
     }
     container track {
       description "Interfaces to track for VRRP group";
       uses apply-advanced;
       list interface {
         key name;
         ordered-by user;
         description "Interface to track in VRRP group";
         leaf name {
           description "Name of interface";
           type union {
             type jt:interface-unit;
             type string {
               pattern "<.*>|$.*";
             }
           }
         }
         uses apply-advanced;
         container weight {
           description "Adjust priority by this weight";
           uses apply-advanced;
           leaf cost {
             description "Value to subtract from priority when interface is down";
             type union {
               type string {
                 pattern "<.*>|$.*";
               }
               type int32 {
                 range "-253 .. 253";
               }
             }
           }
           leaf reverse {
             description "Will cause vrrp instance to be down when interface is up and vice versa";
             type empty;
           }
         }
       }
       list track-script {
         key name;
         ordered-by user;
         description "Tracking script for VRRP group";
         leaf name {
           description "Script instance";
           type string;
         }
         uses apply-advanced;
         leaf script-name {
           description "Name of script";
           type string;
         }
         leaf interval {
           description "Run script at every interval";
           type union {
             type string {
               pattern "<.*>|$.*";
             }
             type uint32 {
               range "0 .. 4294967295";
             }
           }
         }
         leaf time-out {
           description "Timeout";
           type union {
             type string {
               pattern "<.*>|$.*";
             }
             type uint32 {
               range "0 .. 4294967295";
             }
           }
         }
         leaf rise {
           description "Rise";
           type union {
             type string {
               pattern "<.*>|$.*";
             }
             type uint32 {
               range "1 .. 4294967295";
             }
           }
         }
         leaf fall {
           description "Fall";
           type union {
             type string {
               pattern "<.*>|$.*";
             }
             type uint32 {
               range "1 .. 4294967295";
             }
           }
         }
         container weight {
           description "Adjust priority by this weight";
           uses apply-advanced;
           leaf cost {
             description "Value to subtract from priority when script returns non-zero code";
             type union {
               type string {
                 pattern "<.*>|$.*";
               }
               type int32 {
                 range "-253 .. 253";
               }
             }
           }
           leaf reverse {
             description "Will cause vrrp instance to be down when script is up and vice versa";
             type empty;
           }
         }
       }
       leaf-list notify-script {
         ordered-by user;
         description "Notify script for VRRP group";
         type string;
       }
       container notify-master {
         description "Notify script to MASTER transition";
         uses apply-advanced;
         leaf-list script-name {
           ordered-by user;
           description "Name of script";
           type string;
         }
         leaf username {
           description "Username under which scripts should run";
           type string;
         }
       }
       container notify-backup {
         description "Notify script to BACKUP transition";
         uses apply-advanced;
         leaf-list script-name {
           ordered-by user;
           description "Name of script";
           type string;
         }
         leaf username {
           description "Username under which scripts should run";
           type string;
         }
       }
       container notify-fault {
         description "Notify script to FAULT transition";
         uses apply-advanced;
         leaf-list script-name {
           ordered-by user;
           description "Name of script";
           type string;
         }
         leaf username {
           description "Username under which scripts should run";
           type string;
         }
       }
     }
     list virtual-address {
       key name;
       ordered-by user;
       description "Virtual IPv4 address";
       uses virtual-address;
     }
     container unicast {
       description "Unicast parameters";
       uses apply-advanced;
       list local-address {
         key name;
         ordered-by user;
         description "Unicast local ipv4 address";
         uses inet-local-address;
       }
       list peer-address {
         key name;
         ordered-by user;
         description "Unicast peer ipv4 address";
         uses inet-peer-address;
       }
     }
   }
   grouping inet-local-address {
     leaf name {
       description "One or more unicast source ipv4 address";
       type jt:ipv4addr;
     }
     uses apply-advanced;
   }
   grouping inet-peer-address {
     leaf name {
       description "One or more unicast peer ipv4 address";
       type jt:ipv4addr;
     }
     uses apply-advanced;
   }
   grouping virtual-address {
     leaf name {
       description "One or more virtual IPv4 addresses";
       type jt:ipv4prefix;
     }
     uses apply-advanced;
     leaf device-name {
       description "Name of device";
       type union {
         type jt:interface-unit;
         type string {
           pattern "<.*>|$.*";
         }
       }
     }
   }
   grouping vrrp-inet6-group {
     description "Virtual Router Redundancy Protocol group";
     leaf name {
       description "Identifier for VRRP group";
       type union {
         type string {
           pattern "<.*>|$.*";
         }
         type uint32 {
           range "0 .. 255";
         }
       }
     }
     uses apply-advanced;
     leaf priority {
       description "Virtual router election priority";
       type union {
         type string {
           pattern "<.*>|$.*";
         }
         type uint32 {
           range "0 .. 255";
         }
       }
     }
     leaf mode {
       type enumeration {
         enum "master" {
           description "VRRP mode master";
         }
         enum "backup" {
           description "VRRP mode backup";
         }
       }
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     leaf authentication-type {
       description "Authentication type";
       type enumeration {
         enum "simple" {
           description "Simple password";
         }
       }
     }
     leaf authentication-key {
       description "Authentication key";
       type string;
     }
     leaf virtual-mac-disable {
       description "Disable advertisement of virtual MAC address for configured virtual ip-address";
       type empty;
     }
     container track {
       description "Interfaces to track for VRRP group";
       uses apply-advanced;
       list interface {
         key name;
         ordered-by user;
         description "Interface to track in VRRP group";
         leaf name {
           description "Name of interface";
           type union {
             type jt:interface-unit;
             type string {
               pattern "<.*>|$.*";
             }
           }
         }
         uses apply-advanced;
         container weight {
           description "Adjust priority by this weight";
           uses apply-advanced;
           leaf cost {
             description "Value to subtract from priority when interface is down";
             type union {
               type string {
                 pattern "<.*>|$.*";
               }
               type int32 {
                 range "-253 .. 253";
               }
             }
           }
           leaf reverse {
             description "Will cause vrrp instance to be down when interface is up and vice versa";
             type empty;
           }
         }
       }
       list track-script {
         key name;
         ordered-by user;
         description "Tracking script for VRRP group";
         leaf name {
           description "Script instance";
           type string;
         }
         uses apply-advanced;
         leaf script-name {
           description "Name of script";
           type string;
         }
         leaf interval {
           description "Run script at every interval";
           type union {
             type string {
               pattern "<.*>|$.*";
             }
             type uint32 {
               range "0 .. 4294967295";
             }
           }
         }
         leaf time-out {
           description "Timeout";
           type union {
             type string {
               pattern "<.*>|$.*";
             }
             type uint32 {
               range "0 .. 4294967295";
             }
           }
         }
         leaf rise {
           description "Rise";
           type union {
             type string {
               pattern "<.*>|$.*";
             }
             type uint32 {
               range "1 .. 4294967295";
             }
           }
         }
         leaf fall {
           description "Fall";
           type union {
             type string {
               pattern "<.*>|$.*";
             }
             type uint32 {
               range "1 .. 4294967295";
             }
           }
         }
         container weight {
           description "Adjust priority by this weight";
           uses apply-advanced;
           leaf cost {
             description "Value to subtract from priority when script returns non-zero code";
             type union {
               type string {
                 pattern "<.*>|$.*";
               }
               type int32 {
                 range "-253 .. 253";
               }
             }
           }
           leaf reverse {
             description "Will cause vrrp instance to be down when script is up and vice versa";
             type empty;
           }
         }
       }
       leaf-list notify-script {
         ordered-by user;
         description "Notify script for VRRP group";
         type string;
       }
       container notify-master {
         description "Notify script to MASTER transition";
         uses apply-advanced;
         leaf-list script-name {
           ordered-by user;
           description "Name of script";
           type string;
         }
         leaf username {
           description "Username under which scripts should run";
           type string;
         }
       }
       container notify-backup {
         description "Notify script to BACKUP transition";
         uses apply-advanced;
         leaf-list script-name {
           ordered-by user;
           description "Name of script";
           type string;
         }
         leaf username {
           description "Username under which scripts should run";
           type string;
         }
       }
       container notify-fault {
         description "Notify script to FAULT transition";
         uses apply-advanced;
         leaf-list script-name {
           ordered-by user;
           description "Name of script";
           type string;
         }
         leaf username {
           description "Username under which scripts should run";
           type string;
         }
       }
     }
     list virtual-inet6-address {
       key name;
       ordered-by user;
       description "Virtual IPv6 address";
       uses virtual-inet6-address;
     }
     container unicast {
       description "Unicast parameters";
       uses apply-advanced;
       list local-address {
         key name;
         ordered-by user;
         description "Unicast local ipv6 address";
         uses inet6-local-address;
       }
       list peer-address {
         key name;
         ordered-by user;
         description "Unicast peer ipv6 address";
         uses inet6-peer-address;
       }
     }
   }
   grouping inet6-local-address {
     leaf name {
       description "One or more unicast source ipv6 address";
       type jt:ipv6addr;
     }
     uses apply-advanced;
   }
   grouping inet6-peer-address {
     leaf name {
       description "One or more unicast peer ipv6 address";
       type jt:ipv6addr;
     }
     uses apply-advanced;
   }
   grouping virtual-inet6-address {
     leaf name {
       description "One or more virtual IPv6 addresses";
       type jt:ipv6prefix;
     }
     uses apply-advanced;
     leaf device-name {
       description "Name of device";
       type union {
         type jt:interface-unit;
         type string {
           pattern "<.*>|$.*";
         }
       }
     }
   }
   grouping write-option-82-type {
     uses apply-advanced;
   }
 }
