module sorespo-ietf-l3vpn-svc {
  yang-version 1.1;
  namespace "http://example.com/sorespo-ietf-l3vpn-svc";
  prefix sorespo-l3vpn-svc;

  import ietf-l3vpn-svc {
    prefix l3vpn-svc;
  }
  import stratoweave {
    prefix sw;
  }
  import ietf-yang-tmf-map {
    prefix tmf;
  }

  description
    "Sorespo-specific augmentations for the standard IETF L3VPN service model.";

  revision 2026-03-31 {
    description
      "Move transform hooks out of the standard model and into augments.";
  }

  augment "/l3vpn-svc:l3vpn-svc/l3vpn-svc:vpn-services/l3vpn-svc:vpn-service" {
    sw:transform sorespo.cfs.L3VpnVpnService;
    tmf:cfs-service "L3VPN VPN Service";
  }

  augment "/l3vpn-svc:l3vpn-svc/l3vpn-svc:sites/l3vpn-svc:site" {
    sw:transform sorespo.cfs.L3VpnSite;
    tmf:cfs-service "L3VPN Site";

    container bgp-sessions {
      config false;
      description
        "Operational eBGP customer session telemetry, lifted from the RFS
         ebgp-customer state via the inter l3vpn endpoint. One entry per
         site-network-access with BGP configured. debug-active reflects the
         per-neighbor on-demand telemetry escalation (session down or flapping).";
      list bgp-session {
        key site-network-access;
        leaf site-network-access {
          type string;
        }
        leaf session-state {
          type enumeration {
            enum idle;
            enum connect;
            enum active;
            enum opensent;
            enum openconfirm;
            enum established;
          }
        }
        leaf last-event {
          type string;
        }
        leaf established-transitions {
          type uint64;
        }
        leaf debug-active {
          type boolean;
        }
        leaf negotiated-hold-time {
          type uint64;
        }
        leaf last-notification {
          type string;
        }
      }
    }
  }

  augment "/l3vpn-svc:l3vpn-svc/l3vpn-svc:sites/l3vpn-svc:site"
        + "/l3vpn-svc:site-network-accesses/l3vpn-svc:site-network-access"
        + "/l3vpn-svc:routing-protocols/l3vpn-svc:routing-protocol/l3vpn-svc:bgp" {
    description
      "Per-customer eBGP session authentication key. Optional: absent means the
       session has no MD5/TCP-AO authentication. Modelled per site-network-access
       because each customer session is an independent trust relationship.";
    leaf authentication-key {
      type string;
    }
  }
}
