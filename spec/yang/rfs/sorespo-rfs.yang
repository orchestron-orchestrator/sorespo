module sorespo-rfs {
    yang-version "1.1";
    namespace "http://example.com/sorespo-rfs";
    prefix "sorespo-rfs";

    import stratoweave-rfs {
        prefix sw-rfs;
    }
    import ietf-inet-types {
      prefix inet;
    }
    import stratoweave {
      prefix sw;
    }

    augment "/sw-rfs:rfs" {
        container base-config {

            sw:rfs-transform sorespo.rfs.BaseConfig;
          must "role = 'roadm' or (ipv4-address and ipv6-address and asn and ibgp-authentication-key)" {
            error-message "Router base configuration requires IPv4, IPv6, ASN, and iBGP authentication values";
          }

            leaf role {
                type string;
            }

            leaf ipv4-address {
                type string;
              when "not(../role = 'roadm')";
            }

            leaf ipv6-address {
                type string;
              when "not(../role = 'roadm')";
            }

            leaf asn {
                type inet:as-number;
              when "not(../role = 'roadm')";
            }

            leaf ibgp-authentication-key {
                type string;
              when "not(../role = 'roadm')";
            }
        }

        list line-interface {
          key name;
          sw:rfs-transform sorespo.rfs.LineInterface;
          description "ROADM to ROADM interfaces";
          leaf name {
              type string;
          }
          container remote {
              leaf device {
                  type string;
                  mandatory true;
              }
              leaf interface {
                  type string;
                  mandatory true;
              }
          }
        }

        list user-interface {
          key interface;
          sw:rfs-transform sorespo.rfs.UserInterface;
          description "ROADM to router interfaces";
          leaf interface {
              type string;
          }
          leaf vlan {
            type uint16 {
              range "1..4094";
            }
            mandatory true;
          }
          container remote {
              leaf router {
                  type string;
                  mandatory true;
              }
              leaf interface {
                  type string;
                  mandatory true;
              }
          }
        }
        list roadm-vlan {
          key "interface vlan";
          sw:rfs-transform sorespo.rfs.RoadmSubifaceVlan;
          description "vlans";
          leaf interface {
            type string;
            mandatory true;
          }
          leaf vlan {
            type uint16 {
              range "1..4094";
            }
            mandatory true;
          }
        }

        list backbone-interface {
            key name;

            sw:rfs-transform sorespo.rfs.BBInterface;

            leaf name {
                type string;
            }

            leaf ipv4-address {
                type string;
            }

            leaf ipv4-prefix-length {
                type uint8 {
                    range "0..32";
                }
                default "30";
            }

            leaf ipv6-address {
                type string;
            }

            leaf ipv6-prefix-length {
                type uint8 {
                    range "0..128";
                }
            }

            container remote {
                leaf device {
                    type string;
                    mandatory true;
                }
                leaf interface {
                    type string;
                    mandatory true;
                }
            }

            container state {
                config false;
                description
                    "Operational state of the backbone interface, polled from
                     the device. oper-status is the interface oper-state.";
                leaf oper-status {
                    type enumeration {
                        enum up;
                        enum down;
                        enum unknown;
                    }
                }
            }

        }

        list ibgp-neighbor {
          key address;
          sw:rfs-transform sorespo.rfs.IbgpNeighbor;
          leaf address {
            type inet:ip-address;
          }
          leaf asn {
            // Need this one for IOS XR: router bgp <asn>
            type inet:as-number;
            mandatory true;
          }
          leaf description {
            type string;
            mandatory true;
          }
          leaf ibgp-authentication-key {
            type string;
          }
        }

        list vrf {
          key name;
          sw:rfs-transform sorespo.rfs.Vrf;
          leaf name {
            type string;
          }
          leaf description {
            type string;
          }
          // TODO: compute RD in the layer above and use as key?!
          leaf id {
            type uint32;
            mandatory true;
          }
          leaf router-id {
            type uint32;
            mandatory true;
          }
          leaf asn {
            type inet:as-number;
            mandatory true;
          }
        }

        list vrf-interface {
            key "name";
            sw:rfs-transform sorespo.rfs.VrfInterface;
            leaf name {
                type string;
            }
            leaf description {
                type string;
            }
            leaf vrf {
                type string;
                description
                    "VRF name";
                mandatory true;
            }
            leaf ipv4-address {
                type inet:ipv4-address;
            }
            leaf ipv4-prefix-length {
                type uint8 {
                    range "1..31";
                }
                default "30";
            }
        }

    list ebgp-customer {
      key "vrf address";
      sw:rfs-transform sorespo.rfs.EbgpCustomer;
      leaf vrf {
        type string;
      }
      leaf address {
        type inet:ip-address;
      }
      leaf local-asn {
        type uint32;
        mandatory true;
      }
      leaf peer-asn {
        type uint32;
        mandatory true;
      }
      leaf description {
        type string;
      }
      leaf authentication-key {
        type string;
        description
          "Optional eBGP session authentication key (MD5/TCP-AO). Absent when
           the customer session has no authentication configured.";
      }

      container state {
        config false;
        description
          "eBGP customer neighbor session telemetry. The base set is always
           collected; the escalated detail is collected only while debug-active
           (session down or flapping).";
        leaf session-state {
          type enumeration {
            enum idle;
            enum connect;
            enum active;
            enum opensent;
            enum openconfirm;
            enum established;
          }
        }
        leaf last-event { type string; }
        leaf established-transitions { type uint64; }
        leaf debug-active { type boolean; }
        leaf negotiated-hold-time { type uint64; }
        leaf last-notification { type string; }
      }
    }
  }
}
