module Cisco-IOS-XR-um-cli-alias-cfg {

  /*** NAMESPACE / PREFIX DEFINITION ***/

  namespace "http://cisco.com/ns/yang/Cisco-IOS-XR-um-cli-alias-cfg";
  prefix um-cli-alias-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cli-alias package configuration.

     This YANG module augments the
     modules with configuration data.

     Copyright (c) 2021-2025 by Cisco Systems, Inc., and/or its affiliates.
     All rights reserved.";

  revision 2022-06-03 {
    description
      "Added containers submode-cli-blk and neutral under service";
    semver:module-version "1.1.0";
  }

  revision "2021-02-23" {
    description
      "Initial release";
    semver:module-version "1.0.0";
  }

  feature classic-admin-config {
    description
      "Classic admin configuration supported";
  }

  container admin {
    if-feature "classic-admin-config";
    description
      "Admin configuration";
    container alias {
      description
        "Create an alias for entity";
      container aliases {
        description
          "Alias name";
        list alias {
          key "alias-name";
          description
            "Alias name";
          leaf alias-name {
            type string {
              length "1..30" {
                description
                  "Alias name";
              }
            }
            description
              "Alias name";
          }
          leaf alias-body {
            type string {
              length "1..1014" {
                description
                  "Alias body with optional parameters e.g,(name) show $name";
              }
            }
            mandatory true;
            description
              "Alias body with optional parameters e.g,(name) show $name";
          }
        }
      }
    }
  }
  container service {
    description
      "Modify use of network based services";
    container cli {
      description
        "cli configuration services";
      container interactive {
        description
          "Change interactive behavior of commands";
        container disable {
          presence "Indicates a disable node is configured.";
          description
            "Disable commands from being interactive";
        }
      }
      container indentation {
        description
          "indentation tracking";
        container disable {
          presence "Indicates a disable node is configured.";
          description
            "disable the indentation";
        }
      }
      container submode-exit {
        description
          "Exit submode when only '!' seen in interactive mode";
        container enable {
          presence "Indicates a enable node is configured.";
          description
            "Enable the feature";
        }
      }
      container commit-optimized {
        description
          "Enable optimization for regular commit";
        container enable {
          presence "Indicates a enable node is configured.";
          description
            "Enable the feature";
        }
      }
      container delete-optimize {
        description
          "Enable delete optimize configuration";
        container enable {
          presence "Indicates a enable node is configured.";
          description
            "Enable the feature";
        }
      }
      container configuration {
        description
          "allowing to configuration submode";
        container disable {
          description
            "disable for read-only access users";
          leaf usergroup {
            type string {
              length "1..800" {
                description
                  "Usergroup name";
              }
            }
            description
              "Disable config mode for usergroup";
          }
        }
      }
      container history {
        description
          "cli commands history";
        leaf size {
          type uint32 {
            range "1000..5000" {
              description
                "maximum number of entries";
            }
          }
          description
            "maximum number of commands in history";
        }
      }
      container flex-cli-local-override {
        description
          "Enable Flex cli local config override";
        container enable {
          presence "Indicates a enable node is configured.";
          description
            "Enable the feature";
        }
      }
      container submode-cli-blk {
        description
          "Enable into submode-cli  mode";
        container enable {
          presence "Indicates a enable node is configured.";
          description
            "Enable the submode cli  feature";
        }
      }
      container neutral {
        description
          "Enable neutral configuration";
        container enable {
          presence "Indicates a enable node is configured.";
          description
            "Enable BLM cli feature";
        }
      }
    }
  }
  container logging {
    description
      "Modify message logging facilities";
    container suppress {
      description
        "Suppress logging behaviour";
      container deprecated {
        presence "Indicates a deprecated node is configured.";
        description
          "Enable deprecated message display";
      }
    }
  }
  container alias {
    description
      "Create an alias for entity";
    container aliases {
      description
        "Alias name";
      list alias {
        key "alias-name";
        description
          "Alias name";
        leaf alias-name {
          type string {
            length "1..30" {
              description
                "Alias name";
            }
          }
          description
            "Alias name";
        }
        leaf alias-body {
          type string {
            length "1..1014" {
              description
                "Alias body with optional parameters e.g,(name) show $name";
            }
          }
          mandatory true;
          description
            "Alias body with optional parameters e.g,(name) show $name";
        }
      }
    }
    container exec {
      description
        "Exec command alias";
      list alias {
        key "exec-alias-name";
        description
          "Exec Alias name";
        leaf exec-alias-name {
          type string {
            length "1..30" {
              description
                "Exec Alias name";
            }
          }
          description
            "Exec Alias name";
        }
        leaf aliased-exec-command {
          type string {
            length "1..800" {
              description
                "Aliased exec command";
            }
          }
          mandatory true;
          description
            "Aliased exec command";
        }
      }
    }
    container config {
      description
        "Config command alias";
      list alias {
        key "config-alias-name";
        description
          "Config Alias name";
        leaf config-alias-name {
          type string {
            length "1..30" {
              description
                "Config Alias name";
            }
          }
          description
            "Config Alias name";
        }
        leaf aliased-config-command {
          type string {
            length "1..800" {
              description
                "Aliased config command";
            }
          }
          mandatory true;
          description
            "Aliased config command";
        }
      }
    }
  }
}
