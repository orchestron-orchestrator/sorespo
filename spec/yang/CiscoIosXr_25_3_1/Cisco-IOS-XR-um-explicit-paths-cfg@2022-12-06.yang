module Cisco-IOS-XR-um-explicit-paths-cfg {

  /*** NAMESPACE / PREFIX DEFINITION ***/

  namespace "http://cisco.com/ns/yang/Cisco-IOS-XR-um-explicit-paths-cfg";
  prefix um-explicit-paths-cfg;

  /*** LINKAGE (IMPORTS / INCLUDES) ***/

  import ietf-inet-types {
    prefix inet;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR explicit-paths package configuration.

     This YANG module augments the
     modules with configuration data.

     Copyright (c) 2021-2025 by Cisco Systems, Inc., and/or its affiliates.
     All rights reserved.";

  revision 2022-12-06 {
    description
      "Added must statement under list index of explicit-path/name";
    semver:module-version "2.0.0";
  }

  revision "2021-01-14" {
    description
      "Initial release";
    semver:module-version "1.0.0";
  }

  container explicit-path {
    description
      "Explicit-path config commands";
    container identifiers {
      description
        "Specify explicit path by number";
      list identifier {
        key "identifier-id";
        description
          "Specify explicit path by number";
        leaf identifier-id {
          type uint32 {
            range "1..65535" {
              description
                "Enter number";
            }
          }
          description
            "Specify explicit path by number";
        }
        container indexes {
          description
            "Specify the next entry index to add or edit";
          list index {
            must "next-address/strict/ipv4/unicast/address or
                  next-address/strict/ipv4/unicast/unnumbered or
                  next-address/strict/ipv4/unicast/ifindex or
                  next-address/loose/ipv4/unicast/address or
                  next-address/loose/ipv4/unicast/unnumbered or
                  next-address/loose/ipv4/unicast/ifindex or
                  exclude-address/ipv4/unicast/address or
                  exclude-srlg/ipv4/unicast/address or
                  next-label";
            key "index-number";
            description
              "Specify the next entry index to add or edit";
            leaf index-number {
              type uint32 {
                range "1..65535" {
                  description
                    "Index number";
                }
              }
              description
                "Specify the next entry index to add or edit";
            }
            container next-address {
              description
                "Specify the next (adjacent) address in the path";
              container strict {
                description
                  "Specify the next address in the path as a strict hop";
                container ipv4 {
                  description
                    "Specify the address AFI";
                  container unicast {
                    description
                      "Specify the address SAFI";
                    leaf address {
                      type inet:ipv4-address-no-zone;
                      must "(../ifindex = 0) and not(../unnumbered or
                            ../../../../loose/ipv4/unicast/address or
                            ../../../../loose/ipv4/unicast/unnumbered or
                            ../../../../../exclude-address/ipv4/unicast/address or
                            ../../../../../exclude-srlg/ipv4/unicast/address or
                            ../../../../../next-label)";
                      description
                        "Specify the address SAFI";
                    }
                    leaf unnumbered {
                      type inet:ipv4-address-no-zone;
                      must "../ifindex and (../ifindex != 0) and not(../address or
                            ../../../../loose/ipv4/unicast/address or
                            ../../../../loose/ipv4/unicast/unnumbered or
                            ../../../../../exclude-address/ipv4/unicast/address or
                            ../../../../../exclude-srlg/ipv4/unicast/address or
                            ../../../../../next-label)";
                      description
                        "Enter Router Id (A.B.C.D) and Ifindex ";
                    }
                    leaf ifindex {
                      type union {
                        type uint32 {
                          range "1..4294967295" {
                            description
                              "Enter ifindex for unnumbered";
                          }
                        }
                        type uint32 {
                          range "0" {
                            description
                              "0 is the value needed for address";
                          }
                        }
                      }
                      must '../address or ../unnumbered';
                      description
                        "Enter Ifindex";
                    }
                  }
                }
              }
              container loose {
                description
                  "Specify the next address in the path as a loose hop";
                container ipv4 {
                  description
                    "Specify the address AFI";
                  container unicast {
                    description
                      "Specify the address SAFI";
                    leaf address {
                      type inet:ipv4-address-no-zone;
                      must "(../ifindex = 0) and not(../unnumbered or
                            ../../../../strict/ipv4/unicast/address or
                            ../../../../strict/ipv4/unicast/unnumbered or
                            ../../../../../exclude-address/ipv4/unicast/address or
                            ../../../../../exclude-srlg/ipv4/unicast/address or
                            ../../../../../next-label)";
                      description
                        "Specify the address SAFI";
                    }
                    leaf unnumbered {
                      type inet:ipv4-address-no-zone;
                      must "../ifindex and (../ifindex != 0) and not(../address or
                            ../../../../strict/ipv4/unicast/address or
                            ../../../../strict/ipv4/unicast/unnumbered or
                            ../../../../../exclude-address/ipv4/unicast/address or
                            ../../../../../exclude-srlg/ipv4/unicast/address or
                            ../../../../../next-label)";
                      description
                        "Enter Router Id (A.B.C.D) and Ifindex ";
                    }
                    leaf ifindex {
                      type union {
                        type uint32 {
                          range "1..4294967295" {
                            description
                              "Enter ifindex for unnumbered";
                          }
                        }
                        type uint32 {
                          range "0" {
                            description
                              "0 is the value needed for address";
                          }
                        }
                      }
                      must '../address or ../unnumbered';
                      description
                        "Enter Ifindex";
                    }
                  }
                }
              }
            }
            container exclude-address {
              description
                "Specify the next address to be excluded ";
              container ipv4 {
                description
                  "Specify the address AFI";
                container unicast {
                  description
                    "Specify the address SAFI";
                  leaf address {
                    type inet:ipv4-address-no-zone;
                    must "not(../../../../next-address/loose/ipv4/unicast/address or
                          ../../../../next-address/loose/ipv4/unicast/unnumbered or
                          ../../../../next-address/strict/ipv4/unicast/address or
                          ../../../../next-address/strict/ipv4/unicast/unnumbered or
                          ../../../../exclude-srlg/ipv4/unicast/address or
                          ../../../../next-label)";
                    description
                      "Specify the address SAFI";
                  }
                }
              }
            }
            container exclude-srlg {
              description
                "Specify an IP Addr to get SRLGs from for exclusion";
              container ipv4 {
                description
                  "Specify the address AFI";
                container unicast {
                  description
                    "Specify the address SAFI";
                  leaf address {
                    type inet:ipv4-address-no-zone;
                    must "not(../../../../next-address/loose/ipv4/unicast/address or
                          ../../../../next-address/loose/ipv4/unicast/unnumbered or
                          ../../../../next-address/strict/ipv4/unicast/address or
                          ../../../../next-address/strict/ipv4/unicast/unnumbered or
                          ../../../../exclude-address/ipv4/unicast/address or
                          ../../../../next-label)";
                    description
                      "Specify the address SAFI";
                  }
                }
              }
            }
            leaf next-label {
              type uint32 {
                range "0..1048575" {
                  description
                    "MPLS label value";
                }
              }
              must "not(../next-address/loose/ipv4/unicast/address or
                    ../next-address/loose/ipv4/unicast/unnumbered or
                    ../next-address/strict/ipv4/unicast/address or
                    ../next-address/strict/ipv4/unicast/unnumbered or
                    ../exclude-address/ipv4/unicast/address or
                    ../exclude-srlg/ipv4/unicast/address)";
              description
                "Specify the next MPLS label in the path";
            }
          }
        }
        container disable {
          presence "Indicates a disable node is configured.";
          description
            "Disable the explicit path";
        }
      }
    }
    container names {
      description
        "Specify explicit path by name";
      list name {
        key "name-name";
        description
          "Specify explicit path by name";
        leaf name-name {
          type string {
            length "1..800" {
              description
                "Specify an IP explicit path by name";
            }
          }
          description
            "Specify explicit path by name";
        }
        container indexes {
          description
            "Specify the next entry index to add or edit";
          list index {
            must "next-address/strict/ipv4/unicast/address or
                  next-address/strict/ipv4/unicast/unnumbered or
                  next-address/strict/ipv4/unicast/ifindex or
                  next-address/loose/ipv4/unicast/address or
                  next-address/loose/ipv4/unicast/unnumbered or
                  next-address/loose/ipv4/unicast/ifindex or
                  exclude-address/ipv4/unicast/address or
                  exclude-srlg/ipv4/unicast/address or
                  next-label";
            key "index-number";
            description
              "Specify the next entry index to add or edit";
            leaf index-number {
              type uint32 {
                range "1..65535" {
                  description
                    "Index number";
                }
              }
              description
                "Specify the next entry index to add or edit";
            }
            container next-address {
              description
                "Specify the next (adjacent) address in the path";
              container strict {
                description
                  "Specify the next address in the path as a strict hop";
                container ipv4 {
                  description
                    "Specify the address AFI";
                  container unicast {
                    description
                      "Specify the address SAFI";
                    leaf address {
                      type inet:ipv4-address-no-zone;
                      must "(../ifindex = 0) and not(../unnumbered or
                            ../../../../loose/ipv4/unicast/address or
                            ../../../../loose/ipv4/unicast/unnumbered or
                            ../../../../../exclude-address/ipv4/unicast/address or
                            ../../../../../exclude-srlg/ipv4/unicast/address or
                            ../../../../../next-label)";
                      description
                        "Specify the address SAFI";
                    }
                    leaf unnumbered {
                      type inet:ipv4-address-no-zone;
                      must "../ifindex and (../ifindex != 0) and not(../address or
                            ../../../../loose/ipv4/unicast/address or
                            ../../../../loose/ipv4/unicast/unnumbered or
                            ../../../../../exclude-address/ipv4/unicast/address or
                            ../../../../../exclude-srlg/ipv4/unicast/address or
                            ../../../../../next-label)";
                      description
                        "Enter Router Id (A.B.C.D) and Ifindex ";
                    }
                    leaf ifindex {
                      type union {
                        type uint32 {
                          range "1..4294967295" {
                            description
                              "Enter ifindex for unnumbered";
                          }
                        }
                        type uint32 {
                          range "0" {
                            description
                              "0 is the value needed for address";
                          }
                        }
                      }
                      must '../address or ../unnumbered';
                      description
                        "Enter Ifindex";
                    }
                  }
                }
              }
              container loose {
                description
                  "Specify the next address in the path as a loose hop";
                container ipv4 {
                  description
                    "Specify the address AFI";
                  container unicast {
                    description
                      "Specify the address SAFI";
                    leaf address {
                      type inet:ipv4-address-no-zone;
                      must "(../ifindex = 0) and not(../unnumbered or
                            ../../../../strict/ipv4/unicast/address or
                            ../../../../strict/ipv4/unicast/unnumbered or
                            ../../../../../exclude-address/ipv4/unicast/address or
                            ../../../../../exclude-srlg/ipv4/unicast/address or
                            ../../../../../next-label)";
                      description
                        "Specify the address SAFI";
                    }
                    leaf unnumbered {
                      type inet:ipv4-address-no-zone;
                      must "../ifindex and (../ifindex != 0) and not(../address or
                            ../../../../strict/ipv4/unicast/address or
                            ../../../../strict/ipv4/unicast/unnumbered or
                            ../../../../../exclude-address/ipv4/unicast/address or
                            ../../../../../exclude-srlg/ipv4/unicast/address or
                            ../../../../../next-label)";
                      description
                        "Enter Router Id (A.B.C.D) and Ifindex ";
                    }
                    leaf ifindex {
                      type union {
                        type uint32 {
                          range "1..4294967295" {
                            description
                              "Enter ifindex for unnumbered";
                          }
                        }
                        type uint32 {
                          range "0" {
                            description
                              "0 is the value needed for address";
                          }
                        }
                      }
                      must '../address or ../unnumbered';
                      description
                        "Enter Ifindex";
                    }
                  }
                }
              }
            }
            container exclude-address {
              description
                "Specify the next address to be excluded ";
              container ipv4 {
                description
                  "Specify the address AFI";
                container unicast {
                  description
                    "Specify the address SAFI";
                  leaf address {
                    type inet:ipv4-address-no-zone;
                    must "not(../../../../next-address/loose/ipv4/unicast/address or
                          ../../../../next-address/loose/ipv4/unicast/unnumbered or
                          ../../../../next-address/strict/ipv4/unicast/address or
                          ../../../../next-address/strict/ipv4/unicast/unnumbered or
                          ../../../../exclude-srlg/ipv4/unicast/address or
                          ../../../../next-label)";
                    description
                      "Specify the address SAFI";
                  }
                }
              }
            }
            container exclude-srlg {
              description
                "Specify an IP Addr to get SRLGs from for exclusion";
              container ipv4 {
                description
                  "Specify the address AFI";
                container unicast {
                  description
                    "Specify the address SAFI";
                  leaf address {
                    type inet:ipv4-address-no-zone;
                    must "not(../../../../next-address/loose/ipv4/unicast/address or
                          ../../../../next-address/loose/ipv4/unicast/unnumbered or
                          ../../../../next-address/strict/ipv4/unicast/address or
                          ../../../../next-address/strict/ipv4/unicast/unnumbered or
                          ../../../../exclude-address/ipv4/unicast/address or
                          ../../../../next-label)";
                    description
                      "Specify the address SAFI";
                  }
                }
              }
            }
            leaf next-label {
              type uint32 {
                range "0..1048575" {
                  description
                    "MPLS label value";
                }
              }
              must "not(../next-address/loose/ipv4/unicast/address or
                    ../next-address/loose/ipv4/unicast/unnumbered or
                    ../next-address/strict/ipv4/unicast/address or
                    ../next-address/strict/ipv4/unicast/unnumbered or
                    ../exclude-address/ipv4/unicast/address or
                    ../exclude-srlg/ipv4/unicast/address)";
              description
                "Specify the next MPLS label in the path";
            }
          }
        }
        container disable {
          presence "Indicates a disable node is configured.";
          description
            "Disable the explicit path";
        }
      }
    }
  }
}
