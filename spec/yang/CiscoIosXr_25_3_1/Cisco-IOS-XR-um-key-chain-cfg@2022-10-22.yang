module Cisco-IOS-XR-um-key-chain-cfg {

  /*** NAMESPACE / PREFIX DEFINITION ***/

  namespace "http://cisco.com/ns/yang/Cisco-IOS-XR-um-key-chain-cfg";
  prefix um-key-chain-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR key-chain package configuration.

     This YANG module augments the
     modules with configuration data.

     Copyright (c) 2022-2025 by Cisco Systems, Inc., and/or its affiliates.
     All rights reserved.";

  revision 2022-10-22 {
    description
      "Added timezone container";
    semver:module-version "1.1.0";
  }

  revision "2021-01-05" {
    description
      "Initial release";
    semver:module-version "1.0.0";
  }

  feature check_input_hex_string_length_typ6 {
    description
      "check input hex string length typ6";
  }

  feature check_input_hex_string_length {
    description
      "check input hex string length";
  }

  feature check_input_number {
    description
      "check input number";
  }

  container key {
    description
      "Configure a key";
    container chains {
      description
        "Configure a Key Chain ";
      list chain {
        key "key-chain-name";
        description
          "Name of the key chain - maximum 32 characters";
        leaf key-chain-name {
          type xr:Cisco-ios-xr-string {
            length "1..32" {
              description
                "Name of the key chain - maximum 32 characters";
            }
          }
          description
            "Name of the key chain - maximum 32 characters";
        }
        container accept-tolerance {
          description
            "Configure a tolerance value for accept keys of this keychain";
          leaf tolerance-value {
            type uint32 {
              range "1..8640000" {
                description
                  "Configure a tolerance-value";
              }
            }
            description
              "Configure a tolerance-value";
          }
          container infinite {
            presence "Indicates a infinite node is configured.";
            description
              "Never expires";
          }
        }
        container macsec {
          presence "Indicates a macsec node is configured.";
          description
            "Configures as macsec key chain";
          container keys {
            description
              "Configure CKN for macsec PSK";
            list key {
              key "ckn";
              description
                "Configure CKN for macsec PSK";
              leaf ckn {
                type xr:Cisco-ios-xr-string {
                  length "2..64" {
                    description
                      "Enter CKN as non-zero hex string of even length, i.e 1-32 bytes of MACsec CKN";
                  }
                }
                description
                  "Configure CKN for macsec PSK";
              }
              container key-string {
                must 'password or password6';
                presence "Indicates a key-string node is configured.";
                description
                  "Configure CAK as hex string";
                leaf password {
                  type xr:Proprietary-password;
                  must 'not(../password6)';
                  description
                    "Enter encrypted CAK as hex string";
                }
                leaf password6 {
                  if-feature "check_input_hex_string_length_typ6";
                  if-feature "check_input_hex_string_length";
                  type xr:Type6-password;
                  must 'not(../password)';
                  description
                    "Enter encrypted type6 password";
                }
                leaf cryptographic-algorithm {
                  type enumeration {
                    enum aes-128-cmac {
                      value 7;
                      description
                        "aes 128 cmac";
                    }
                    enum aes-256-cmac {
                      value 8;
                      description
                        "aes 256 cmac";
                    }
                  }
                  mandatory true;
                  description
                    "Cryptographic Algorithm";
                }
              }
              container lifetime {
                description
                  "Configure lifetime";
                container start-time {
                  must '../end-time or ../duration or ../infinite';
                  presence "Indicates a start-time node is configured.";
                  description
                    "Configure lifetime start time";
                  leaf hour {
                    type uint32 {
                      range "0..23" {
                        description
                          "Time to start (hh:mm:ss)";
                      }
                    }
                    mandatory true;
                    description
                      "Start time hour";
                  }
                  leaf minute {
                    type uint32 {
                      range "0..59" {
                        description
                          "Time to start (hh:mm:ss)";
                      }
                    }
                    mandatory true;
                    description
                      "Start time minute";
                  }
                  leaf second {
                    type uint32 {
                      range "0..59" {
                        description
                          "Time to start (hh:mm:ss)";
                      }
                    }
                    mandatory true;
                    description
                      "Start time second";
                  }
                  leaf month {
                    type enumeration {
                      enum january {
                        value 0;
                        description
                          "January";
                      }
                      enum february {
                        value 1;
                        description
                          "February";
                      }
                      enum march {
                        value 2;
                        description
                          "March";
                      }
                      enum april {
                        value 3;
                        description
                          "April";
                      }
                      enum may {
                        value 4;
                        description
                          "May";
                      }
                      enum june {
                        value 5;
                        description
                          "June";
                      }
                      enum july {
                        value 6;
                        description
                          "July";
                      }
                      enum august {
                        value 7;
                        description
                          "August";
                      }
                      enum september {
                        value 8;
                        description
                          "September";
                      }
                      enum october {
                        value 9;
                        description
                          "October";
                      }
                      enum november {
                        value 10;
                        description
                          "November";
                      }
                      enum december {
                        value 11;
                        description
                          "December";
                      }
                    }
                    mandatory true;
                    description
                      "Month of the year";
                  }
                  leaf day-of-month {
                    type uint32 {
                      range "1..31" {
                        description
                          "Day of the month";
                      }
                    }
                    mandatory true;
                    description
                      "Day of the month";
                  }
                  leaf year {
                    type uint32 {
                      range "1993..2035" {
                        description
                          "Year";
                      }
                    }
                    mandatory true;
                    description
                      "Year";
                  }
                }
                container end-time {
                  must '../start-time and not(../duration) and not(../infinite)';
                  presence "Indicates a end-time node is configured.";
                  description
                    "Configure lifetime end time";
                  leaf hour {
                    type uint32 {
                      range "0..23" {
                        description
                          "Time to end (hh:mm:ss)";
                      }
                    }
                    mandatory true;
                    description
                      "End time hour";
                  }
                  leaf minute {
                    type uint32 {
                      range "0..59" {
                        description
                          "Time to end (hh:mm:ss)";
                      }
                    }
                    mandatory true;
                    description
                      "End time minute";
                  }
                  leaf second {
                    type uint32 {
                      range "0..59" {
                        description
                          "Time to end (hh:mm:ss)";
                      }
                    }
                    mandatory true;
                    description
                      "End time second";
                  }
                  leaf month {
                    type enumeration {
                      enum january {
                        value 0;
                        description
                          "January";
                      }
                      enum february {
                        value 1;
                        description
                          "February";
                      }
                      enum march {
                        value 2;
                        description
                          "March";
                      }
                      enum april {
                        value 3;
                        description
                          "April";
                      }
                      enum may {
                        value 4;
                        description
                          "May";
                      }
                      enum june {
                        value 5;
                        description
                          "June";
                      }
                      enum july {
                        value 6;
                        description
                          "July";
                      }
                      enum august {
                        value 7;
                        description
                          "August";
                      }
                      enum september {
                        value 8;
                        description
                          "September";
                      }
                      enum october {
                        value 9;
                        description
                          "October";
                      }
                      enum november {
                        value 10;
                        description
                          "November";
                      }
                      enum december {
                        value 11;
                        description
                          "December";
                      }
                    }
                    mandatory true;
                    description
                      "Month of the year";
                  }
                  leaf day-of-month {
                    type uint32 {
                      range "1..31" {
                        description
                          "Day of the month";
                      }
                    }
                    mandatory true;
                    description
                      "Day of the month";
                  }
                  leaf year {
                    type uint32 {
                      range "1993..2035" {
                        description
                          "Year";
                      }
                    }
                    mandatory true;
                    description
                      "Year";
                  }
                }
                leaf duration {
                  type uint32 {
                    range "1..2147483646" {
                      description
                        "duration in seconds";
                    }
                  }
                  must '../start-time and not(../end-time) and not(../infinite)';
                  description
                    "Lifetime duration";
                }
                container infinite {
                  must '../start-time and not(../end-time) and not(../duration)';
                  presence "Indicates a infinite node is configured.";
                  description
                    "Never expires";
                }
              }
            }
          }
        }
        container keys {
          description
            "Configure a Key";
          list key {
            if-feature "check_input_number";
            key "key-name";
            description
              "Configure a Key";
            leaf key-name {
              type xr:Cisco-ios-xr-string {
                length "1..800" {
                  description
                    "Enter 48-bit integer [0 - 281474976710655]";
                }
                pattern '[0-9]{1,15}';
              }
              description
                "Configure a Key";
            }
            container key-string {
              description
                "Configure a key value";
              leaf password {
                type xr:Proprietary-password;
                must 'not(../password6)';
                description
                  "Encrypted key string (even number of characters with first two as digits and sum less than 53, and rest of the characters should be hex digits)";
              }
              leaf password6 {
                if-feature "check_input_hex_string_length_typ6";
                if-feature "check_input_hex_string_length";
                type xr:Type6-password;
                must 'not(../password)';
                description
                  "Enter encrypted type6 password";
              }
            }
            container send-lifetime {
              description
                "Configure send-lifetime";
              container start-time {
                must '../end-time or ../duration or ../infinite';
                presence "Indicates a start-time node is configured.";
                description
                  "Configure send-lifetime start time";
                leaf hour {
                  type uint32 {
                    range "0..23" {
                      description
                        "Time to start (hh:mm:ss)";
                    }
                  }
                  mandatory true;
                  description
                    "Start time hour";
                }
                leaf minute {
                  type uint32 {
                    range "0..59" {
                      description
                        "Time to start (hh:mm:ss)";
                    }
                  }
                  mandatory true;
                  description
                    "Start time minute";
                }
                leaf second {
                  type uint32 {
                    range "0..59" {
                      description
                        "Time to start (hh:mm:ss)";
                    }
                  }
                  mandatory true;
                  description
                    "Start time second";
                }
                leaf month {
                  type enumeration {
                    enum january {
                      value 0;
                      description
                        "January";
                    }
                    enum february {
                      value 1;
                      description
                        "February";
                    }
                    enum march {
                      value 2;
                      description
                        "March";
                    }
                    enum april {
                      value 3;
                      description
                        "April";
                    }
                    enum may {
                      value 4;
                      description
                        "May";
                    }
                    enum june {
                      value 5;
                      description
                        "June";
                    }
                    enum july {
                      value 6;
                      description
                        "July";
                    }
                    enum august {
                      value 7;
                      description
                        "August";
                    }
                    enum september {
                      value 8;
                      description
                        "September";
                    }
                    enum october {
                      value 9;
                      description
                        "October";
                    }
                    enum november {
                      value 10;
                      description
                        "November";
                    }
                    enum december {
                      value 11;
                      description
                        "December";
                    }
                  }
                  mandatory true;
                  description
                    "Month of the year";
                }
                leaf day-of-month {
                  type uint32 {
                    range "1..31" {
                      description
                        "Day of the month";
                    }
                  }
                  mandatory true;
                  description
                    "Day of the month";
                }
                leaf year {
                  type uint32 {
                    range "1993..2035" {
                      description
                        "Year";
                    }
                  }
                  mandatory true;
                  description
                    "Year";
                }
              }
              container end-time {
                must '../start-time and not(../duration) and not(../infinite)';
                presence "Indicates a end-time node is configured.";
                description
                  "Configure send-lifetime end time";
                leaf hour {
                  type uint32 {
                    range "0..23" {
                      description
                        "Time to end (hh:mm:ss)";
                    }
                  }
                  mandatory true;
                  description
                    "End time hour";
                }
                leaf minute {
                  type uint32 {
                    range "0..59" {
                      description
                        "Time to end (hh:mm:ss)";
                    }
                  }
                  mandatory true;
                  description
                    "End time minute";
                }
                leaf second {
                  type uint32 {
                    range "0..59" {
                      description
                        "Time to end (hh:mm:ss)";
                    }
                  }
                  mandatory true;
                  description
                    "End time second";
                }
                leaf month {
                  type enumeration {
                    enum january {
                      value 0;
                      description
                        "January";
                    }
                    enum february {
                      value 1;
                      description
                        "February";
                    }
                    enum march {
                      value 2;
                      description
                        "March";
                    }
                    enum april {
                      value 3;
                      description
                        "April";
                    }
                    enum may {
                      value 4;
                      description
                        "May";
                    }
                    enum june {
                      value 5;
                      description
                        "June";
                    }
                    enum july {
                      value 6;
                      description
                        "July";
                    }
                    enum august {
                      value 7;
                      description
                        "August";
                    }
                    enum september {
                      value 8;
                      description
                        "September";
                    }
                    enum october {
                      value 9;
                      description
                        "October";
                    }
                    enum november {
                      value 10;
                      description
                        "November";
                    }
                    enum december {
                      value 11;
                      description
                        "December";
                    }
                  }
                  mandatory true;
                  description
                    "Month of the year";
                }
                leaf day-of-month {
                  type uint32 {
                    range "1..31" {
                      description
                        "Day of the month";
                    }
                  }
                  mandatory true;
                  description
                    "Day of the month";
                }
                leaf year {
                  type uint32 {
                    range "1993..2035" {
                      description
                        "Year";
                    }
                  }
                  mandatory true;
                  description
                    "Year";
                }
              }
              leaf duration {
                type uint32 {
                  range "1..2147483646" {
                    description
                      "duration in seconds";
                  }
                }
                must '../start-time and not(../end-time) and not(../infinite)';
                description
                  "Lifetime duration";
              }
              container infinite {
                must '../start-time and not(../end-time) and not(../duration)';
                presence "Indicates a infinite node is configured.";
                description
                  "Never expires";
              }
            }
            container accept-lifetime {
              description
                "Configure accept-lifetime";
              container start-time {
                must '../end-time or ../duration or ../infinite';
                presence "Indicates a start-time node is configured.";
                description
                  "Configure accept-lifetime start time";
                leaf hour {
                  type uint32 {
                    range "0..23" {
                      description
                        "Time to start (hh:mm:ss)";
                    }
                  }
                  mandatory true;
                  description
                    "Start time hour";
                }
                leaf minute {
                  type uint32 {
                    range "0..59" {
                      description
                        "Time to start (hh:mm:ss)";
                    }
                  }
                  mandatory true;
                  description
                    "Start time minute";
                }
                leaf second {
                  type uint32 {
                    range "0..59" {
                      description
                        "Time to start (hh:mm:ss)";
                    }
                  }
                  mandatory true;
                  description
                    "Start time second";
                }
                leaf month {
                  type enumeration {
                    enum january {
                      value 0;
                      description
                        "January";
                    }
                    enum february {
                      value 1;
                      description
                        "February";
                    }
                    enum march {
                      value 2;
                      description
                        "March";
                    }
                    enum april {
                      value 3;
                      description
                        "April";
                    }
                    enum may {
                      value 4;
                      description
                        "May";
                    }
                    enum june {
                      value 5;
                      description
                        "June";
                    }
                    enum july {
                      value 6;
                      description
                        "July";
                    }
                    enum august {
                      value 7;
                      description
                        "August";
                    }
                    enum september {
                      value 8;
                      description
                        "September";
                    }
                    enum october {
                      value 9;
                      description
                        "October";
                    }
                    enum november {
                      value 10;
                      description
                        "November";
                    }
                    enum december {
                      value 11;
                      description
                        "December";
                    }
                  }
                  mandatory true;
                  description
                    "Month of the year";
                }
                leaf day-of-month {
                  type uint32 {
                    range "1..31" {
                      description
                        "Day of the month";
                    }
                  }
                  mandatory true;
                  description
                    "Day of the month";
                }
                leaf year {
                  type uint32 {
                    range "1993..2035" {
                      description
                        "Year";
                    }
                  }
                  mandatory true;
                  description
                    "Year";
                }
              }
              container end-time {
                must '../start-time and not(../duration) and not(../infinite)';
                presence "Indicates a end-time node is configured.";
                description
                  "Configure accept-lifetime end time";
                leaf hour {
                  type uint32 {
                    range "0..23" {
                      description
                        "Time to end (hh:mm:ss)";
                    }
                  }
                  mandatory true;
                  description
                    "End time hour";
                }
                leaf minute {
                  type uint32 {
                    range "0..59" {
                      description
                        "Time to end (hh:mm:ss)";
                    }
                  }
                  mandatory true;
                  description
                    "End time minute";
                }
                leaf second {
                  type uint32 {
                    range "0..59" {
                      description
                        "Time to end (hh:mm:ss)";
                    }
                  }
                  mandatory true;
                  description
                    "End time second";
                }
                leaf month {
                  type enumeration {
                    enum january {
                      value 0;
                      description
                        "January";
                    }
                    enum february {
                      value 1;
                      description
                        "February";
                    }
                    enum march {
                      value 2;
                      description
                        "March";
                    }
                    enum april {
                      value 3;
                      description
                        "April";
                    }
                    enum may {
                      value 4;
                      description
                        "May";
                    }
                    enum june {
                      value 5;
                      description
                        "June";
                    }
                    enum july {
                      value 6;
                      description
                        "July";
                    }
                    enum august {
                      value 7;
                      description
                        "August";
                    }
                    enum september {
                      value 8;
                      description
                        "September";
                    }
                    enum october {
                      value 9;
                      description
                        "October";
                    }
                    enum november {
                      value 10;
                      description
                        "November";
                    }
                    enum december {
                      value 11;
                      description
                        "December";
                    }
                  }
                  mandatory true;
                  description
                    "Month of the year";
                }
                leaf day-of-month {
                  type uint32 {
                    range "1..31" {
                      description
                        "Day of the month";
                    }
                  }
                  mandatory true;
                  description
                    "Day of the month";
                }
                leaf year {
                  type uint32 {
                    range "1993..2035" {
                      description
                        "Year";
                    }
                  }
                  mandatory true;
                  description
                    "Year";
                }
              }
              leaf duration {
                type uint32 {
                  range "1..2147483646" {
                    description
                      "duration in seconds";
                  }
                }
                must '../start-time and not(../end-time) and not(../infinite)';
                description
                  "Lifetime duration";
              }
              container infinite {
                must '../start-time and not(../end-time) and not(../duration)';
                presence "Indicates a infinite node is configured.";
                description
                  "Never expires";
              }
            }
            leaf cryptographic-algorithm {
              type enumeration {
                enum md5 {
                  value 3;
                  description
                    "Configure MD5 as cryptographic algorithm";
                }
                enum sha-1 {
                  value 4;
                  description
                    "Configure SHA-1-20 as cryptographic algorithm";
                }
                enum hmac-md5 {
                  value 5;
                  description
                    "Configure HMAC-MD5 as cryptographic algorithm";
                }
                enum hmac-sha1-20 {
                  value 6;
                  description
                    "Configure HMAC-SHA1-20 as cryptographic algorithm";
                }
                enum hmac-sha1-12 {
                  value 2;
                  description
                    "Configure HMAC-SHA1-12 as cryptographic algorithm";
                }
                enum hmac-sha1-96 {
                  value 9;
                  description
                    "Configure HMAC-SHA1-96 as cryptographic algorithm";
                }
                enum hmac-sha-256 {
                  value 10;
                  description
                    "Configure HMAC-SHA-256 as cryptographic algorithm";
                }
                enum aes-128-cmac-96 {
                  value 1;
                  description
                    "Configure AES-128-CMAC-96 as cryptographic algorithm";
                }
              }
              description
                "Choose cryptographic algorithm";
            }
          }
        }
        container timezone {
          description
            "Configure the timezone for the keychain";
          container local {
            must 'not(../gmt)';
            presence "Indicates a local node is configured.";
            description
              "Router Local Timezone";
          }
          container gmt {
            must 'not(../local)';
            presence "Indicates a gmt node is configured.";
            description
              "GMT (UTC) Timezone";
          }
        }
      }
    }
  }
}
