module Cisco-IOS-XR-um-router-static-cfg {

  /*** NAMESPACE / PREFIX DEFINITION ***/

  namespace "http://cisco.com/ns/yang/Cisco-IOS-XR-um-router-static-cfg";
  prefix um-router-static-cfg;

  /*** LINKAGE (IMPORTS / INCLUDES) ***/

  import cisco-semver {
    prefix semver;
  }
  import Cisco-IOS-XR-types {
    prefix xr;
  }
  import ietf-inet-types {
    prefix inet;
  }
  import ietf-yang-types {
    prefix yang;
  }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR router-static package configuration.

     This YANG module augments the
     modules with configuration data.

     Copyright (c) 2019-2025 by Cisco Systems, Inc., and/or its affiliates.
     All rights reserved.";

  revision 2025-04-17 {
    description
      "Added support for cross-AFI next-hops
       2025-02-18
         Added new field non-recurse for static route
       2023-10-18
         Added new field tunnel-opt-mode for tunnel/vxlan container
       2023-05-05
         Added support for tunnel remote-next-hop.
       2022-08-18
         Added algorithm node support under ipv6 hierarchy.
       2022-06-30
         Added leaf description under vrf-only.
       2022-01-25
         Added container srv6 under segment-routing ipv6 unicast.";
    semver:module-version "3.0.0";
  }

  revision "2021-01-19" {
    description
      "Added must constraints under list node prefix and vrf.";
    semver:module-version "2.0.0";
  }

  revision "2019-06-10" {
    description
      "Establish semantic version baseline.";
    semver:module-version "1.1.0";
  }

  revision "2019-04-04" {
    description
      "Initial version";
  }

  container router {
    description
      "Enable a routing process";
    container static {
      description
        "Static route configuration subcommands";
      container address-family {
        description
          "Static route address family configuration subcommands";
        container ipv4 {
          description
            "IPv4 commands";
          container unicast {
            description
              "Unicast commands";
            container prefixes {
              description
                "Destination prefix";
              list prefix {
                must "segment-routing/mpls/path/names/name or
                      sr-policies/sr-policy or
                      nexthop-interfaces/nexthop-interface or
                      nexthop-interface-addresses/nexthop-interface-address or
                      nexthop-addresses/nexthop-address or
                      nexthop-addresses/nexthop-address-segment-routing or
                      vrfs/vrf-only or vrfs/vrf/sr-policies/sr-policy or
                      vrfs/vrf/nexthop-interfaces/nexthop-interface or
                      vrfs/vrf/nexthop-interface-addresses/nexthop-interface-address or
                      vrfs/vrf/nexthop-addresses/nexthop-address";
                key "prefix-address prefix-length";
                description
                  "Destination prefix";
                leaf prefix-address {
                  type inet:ipv4-address-no-zone;
                  description
                    "Destination prefix";
                }
                leaf prefix-length {
                  type uint32 {
                    range "0..128";
                  }
                  description
                    "Destination prefix length";
                }
                container segment-routing {
                  description
                    "Configure Static Segment Routing";
                  container mpls {
                    description
                      "Configure mpls path name";
                    container path {
                      description
                        "Configure path name";
                      container names {
                        description
                          "Configure path name";
                        list name {
                          key "path-name";
                          description
                            "Configure path name";
                          leaf path-name {
                            type xr:Cisco-ios-xr-string {
                              length "1..1024" {
                                description
                                  "Path name";
                              }
                            }
                            description
                              "Configure path name";
                          }
                          leaf distance-metric {
                            type uint32 {
                              range "1..254" {
                                description
                                  "Distance metric for this route";
                              }
                            }
                            description
                              "Distance metric for this route";
                          }
                          leaf tag {
                            type uint32 {
                              range "1..4294967295" {
                                description
                                  "Set tag for this route";
                              }
                            }
                            description
                              "Set tag for this route";
                          }
                          leaf description {
                            type string {
                              length "1..30" {
                                description
                                  "short description of static route";
                              }
                            }
                            description
                              "description of the static route";
                          }
                          leaf metric {
                            type uint32 {
                              range "1..16777214" {
                                description
                                  "Set metric for this route";
                              }
                            }
                            description
                              "Set metric for this route";
                          }
                        }
                      }
                    }
                  }
                }
                container sr-policies {
                  description
                    "segment routing policy";
                  list sr-policy {
                    key "sr-policy-name";
                    description
                      "segment routing policy";
                    leaf sr-policy-name {
                      type xr:Cisco-ios-xr-string {
                        length "1..1024" {
                          description
                            "SR policy name";
                        }
                      }
                      description
                        "segment routing policy";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type xr:Cisco-ios-xr-string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interfaces {
                  description
                    "Forwarding interface";
                  list nexthop-interface {
                    key "interface-name";
                    description
                      "Forwarding interface";
                    leaf interface-name {
                      type xr:Interface-name;
                      description
                        "Forwarding interface";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interface-addresses {
                  description
                    "Forwarding interface";
                  list nexthop-interface-address {
                    key "interface-name address";
                    description
                      "Forwarding interface";
                    leaf interface-name {
                      type xr:Interface-name;
                      description
                        "Forwarding interface";
                    }
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-addresses {
                  description
                    "Forwarding router's address";
                  list nexthop-address {
                    key "address";
                    description
                      "Forwarding router's address";
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                        container multihop {
                          presence "Indicates a multihop node is configured.";
                          description
                            "Enable BFD Multihop";
                          leaf address {
                            type inet:ipv4-address-no-zone;
                            mandatory true;
                            description
                              "Source address";
                          }
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                  list nexthop-address-segment-routing {
                    key "address mpls-path-name";
                    description
                      "Forwarding router's address";
                    leaf address {
                      type inet:ipv4-address-no-zone;
                      description
                        "Forwarding router's address";
                    }
                    leaf mpls-path-name {
                      type xr:Cisco-ios-xr-string {
                        length "1..1024" {
                          description
                            "Path name";
                        }
                      }
                      description
                        "Configure path name";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    leaf description {
                      type string {
                        length "1..30" {
                          description
                            "short description of static route";
                        }
                      }
                      description
                        "description of the static route";
                    }
                    leaf metric {
                      type uint32 {
                        range "1..16777214" {
                          description
                            "Set metric for this route";
                        }
                      }
                      description
                        "Set metric for this route";
                    }
                  }
                }
                container vrfs {
                  description
                    "Destination VRF";
                  list vrf-only {
                    key "vrf-name";
                    description
                      "Destination only VRF";
                    leaf vrf-name {
                      type xr:Cisco-ios-xr-string {
                        length "1..32" {
                          description
                            "VRF name";
                        }
                      }
                      description
                        "Destination VRF";
                    }
                    leaf description {
                      type string {
                        length "1..254" {
                          description
                            "short description of static route";
                        }
                      }
                      description
                        "description of the static route";
                    }
                  }
                  list vrf {
                    must "sr-policies/sr-policy or
                          nexthop-interfaces/nexthop-interface or
                          nexthop-interface-addresses/nexthop-interface-address or
                          nexthop-addresses/nexthop-address";
                    key "vrf-name";
                    description
                      "Destination VRF";
                    leaf vrf-name {
                      type xr:Cisco-ios-xr-string {
                        length "1..32" {
                          description
                            "VRF name";
                        }
                      }
                      description
                        "Destination VRF";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv4-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                  }
                }
              }
            }
            container topologies {
              description
                "Topology static route configuration subcommands";
              list topology {
                key "topology-name";
                description
                  "Topology static route configuration subcommands";
                leaf topology-name {
                  type xr:Cisco-ios-xr-string {
                    length "1..63" {
                      description
                        "Topology name";
                    }
                  }
                  description
                    "Topology static route configuration subcommands";
                }
              }
            }
          }
          container multicast {
            description
              "Multicast commands";
            container prefixes {
              description
                "Destination prefix";
              list prefix {
                must "segment-routing/mpls/path/names/name or
                      sr-policies/sr-policy or
                      nexthop-interfaces/nexthop-interface or
                      nexthop-interface-addresses/nexthop-interface-address or
                      nexthop-addresses/nexthop-address or
                      nexthop-addresses/nexthop-address-segment-routing or
                      vrfs/vrf-only or vrfs/vrf/sr-policies/sr-policy or
                      vrfs/vrf/nexthop-interfaces/nexthop-interface or
                      vrfs/vrf/nexthop-interface-addresses/nexthop-interface-address or
                      vrfs/vrf/nexthop-addresses/nexthop-address";
                key "prefix-address prefix-length";
                description
                  "Destination prefix";
                leaf prefix-address {
                  type inet:ipv4-address-no-zone;
                  description
                    "Destination prefix";
                }
                leaf prefix-length {
                  type uint32 {
                    range "0..128";
                  }
                  description
                    "Destination prefix length";
                }
                container segment-routing {
                  description
                    "Configure Static Segment Routing";
                  container mpls {
                    description
                      "Configure mpls path name";
                    container path {
                      description
                        "Configure path name";
                      container names {
                        description
                          "Configure path name";
                        list name {
                          key "path-name";
                          description
                            "Configure path name";
                          leaf path-name {
                            type xr:Cisco-ios-xr-string {
                              length "1..1024" {
                                description
                                  "Path name";
                              }
                            }
                            description
                              "Configure path name";
                          }
                          leaf distance-metric {
                            type uint32 {
                              range "1..254" {
                                description
                                  "Distance metric for this route";
                              }
                            }
                            description
                              "Distance metric for this route";
                          }
                          leaf tag {
                            type uint32 {
                              range "1..4294967295" {
                                description
                                  "Set tag for this route";
                              }
                            }
                            description
                              "Set tag for this route";
                          }
                          leaf description {
                            type string {
                              length "1..30" {
                                description
                                  "short description of static route";
                              }
                            }
                            description
                              "description of the static route";
                          }
                          leaf metric {
                            type uint32 {
                              range "1..16777214" {
                                description
                                  "Set metric for this route";
                              }
                            }
                            description
                              "Set metric for this route";
                          }
                        }
                      }
                    }
                  }
                }
                container sr-policies {
                  description
                    "segment routing policy";
                  list sr-policy {
                    key "sr-policy-name";
                    description
                      "segment routing policy";
                    leaf sr-policy-name {
                      type xr:Cisco-ios-xr-string {
                        length "1..1024" {
                          description
                            "SR policy name";
                        }
                      }
                      description
                        "segment routing policy";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interfaces {
                  description
                    "Forwarding interface";
                  list nexthop-interface {
                    key "interface-name";
                    description
                      "Forwarding interface";
                    leaf interface-name {
                      type xr:Interface-name;
                      description
                        "Forwarding interface";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interface-addresses {
                  description
                    "Forwarding interface";
                  list nexthop-interface-address {
                    key "interface-name address";
                    description
                      "Forwarding interface";
                    leaf interface-name {
                      type xr:Interface-name;
                      description
                        "Forwarding interface";
                    }
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-addresses {
                  description
                    "Forwarding router's address";
                  list nexthop-address {
                    key "address";
                    description
                      "Forwarding router's address";
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                        container multihop {
                          presence "Indicates a multihop node is configured.";
                          description
                            "Enable BFD Multihop";
                          leaf address {
                            type inet:ipv4-address-no-zone;
                            mandatory true;
                            description
                              "Source address";
                          }
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                  list nexthop-address-segment-routing {
                    key "address mpls-path-name";
                    description
                      "Forwarding router's address";
                    leaf address {
                      type inet:ipv4-address-no-zone;
                      description
                        "Forwarding router's address";
                    }
                    leaf mpls-path-name {
                      type xr:Cisco-ios-xr-string {
                        length "1..1024" {
                          description
                            "Path name";
                        }
                      }
                      description
                        "Configure path name";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    leaf description {
                      type string {
                        length "1..30" {
                          description
                            "short description of static route";
                        }
                      }
                      description
                        "description of the static route";
                    }
                    leaf metric {
                      type uint32 {
                        range "1..16777214" {
                          description
                            "Set metric for this route";
                        }
                      }
                      description
                        "Set metric for this route";
                    }
                  }
                }
                container vrfs {
                  description
                    "Destination VRF";
                  list vrf-only {
                    key "vrf-name";
                    description
                      "Destination only VRF";
                    leaf vrf-name {
                      type xr:Cisco-ios-xr-string {
                        length "1..32" {
                          description
                            "VRF name";
                        }
                      }
                      description
                        "Destination VRF";
                    }
                    leaf description {
                      type string {
                        length "1..254" {
                          description
                            "short description of static route";
                        }
                      }
                      description
                        "description of the static route";
                    }
                  }
                  list vrf {
                    must "sr-policies/sr-policy or
                          nexthop-interfaces/nexthop-interface or
                          nexthop-interface-addresses/nexthop-interface-address or
                          nexthop-addresses/nexthop-address";
                    key "vrf-name";
                    description
                      "Destination VRF";
                    leaf vrf-name {
                      type xr:Cisco-ios-xr-string {
                        length "1..32" {
                          description
                            "VRF name";
                        }
                      }
                      description
                        "Destination VRF";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv4-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                  }
                }
              }
            }
            container topologies {
              description
                "Topology static route configuration subcommands";
              list topology {
                key "topology-name";
                description
                  "Topology static route configuration subcommands";
                leaf topology-name {
                  type xr:Cisco-ios-xr-string {
                    length "1..63" {
                      description
                        "Topology name";
                    }
                  }
                  description
                    "Topology static route configuration subcommands";
                }
                container prefixes {
                  description
                    "Destination prefix";
                  list prefix {
                    must "sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv4-address-no-zone;
                      description
                        "Destination prefix";
                    }
                    leaf prefix-length {
                      type uint32 {
                        range "0..128";
                      }
                      description
                        "Destination prefix length";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv4-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv4-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv4-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
            }
          }
        }
        container ipv6 {
          description
            "IPv6 commands";
          container unicast {
            description
              "Unicast commands";
            container prefixes {
              description
                "Destination prefix";
              list prefix {
                must "segment-routing/mpls/path/names/name or
                      segment-routing/srv6/endpoint/behavior/vrf or
                      sr-policies/sr-policy or
                      nexthop-interfaces/nexthop-interface or
                      nexthop-interface-addresses/nexthop-interface-address or
                      nexthop-addresses/nexthop-address or
                      nexthop-addresses/nexthop-address-segment-routing or
                      vrfs/vrf-only or vrfs/vrf/sr-policies/sr-policy or
                      vrfs/vrf/nexthop-interfaces/nexthop-interface or
                      vrfs/vrf/nexthop-interface-addresses/nexthop-interface-address or
                      vrfs/vrf/nexthop-addresses/nexthop-address";
                key "prefix-address prefix-length";
                description
                  "Destination prefix";
                leaf prefix-address {
                  type inet:ipv6-address-no-zone;
                  description
                    "Destination prefix";
                }
                leaf prefix-length {
                  type uint32 {
                    range "0..128";
                  }
                  description
                    "Destination prefix length";
                }
                container segment-routing {
                  description
                    "Configure Static Segment Routing";
                  container mpls {
                    description
                      "Configure mpls path name";
                    container path {
                      description
                        "Configure path name";
                      container names {
                        description
                          "Configure path name";
                        list name {
                          key "path-name";
                          description
                            "Configure path name";
                          leaf path-name {
                            type xr:Cisco-ios-xr-string {
                              length "1..1024" {
                                description
                                  "Path name";
                              }
                            }
                            description
                              "Configure path name";
                          }
                          leaf distance-metric {
                            type uint32 {
                              range "1..254" {
                                description
                                  "Distance metric for this route";
                              }
                            }
                            description
                              "Distance metric for this route";
                          }
                          leaf tag {
                            type uint32 {
                              range "1..4294967295" {
                                description
                                  "Set tag for this route";
                              }
                            }
                            description
                              "Set tag for this route";
                          }
                          leaf description {
                            type string {
                              length "1..30" {
                                description
                                  "short description of static route";
                              }
                            }
                            description
                              "description of the static route";
                          }
                          leaf metric {
                            type uint32 {
                              range "1..16777214" {
                                description
                                  "Set metric for this route";
                              }
                            }
                            description
                              "Set metric for this route";
                          }
                          leaf algorithm {
                            type uint32 {
                              range "128..255" {
                                description
                                  "Set algorithm value for this route";
                              }
                            }
                            description
                              "Set algorithm value for this route";
                          }
                        }
                      }
                    }
                  }
                  container srv6 {
                    description
                      "srv6 specific commands";
                    container endpoint {
                      description
                        "srv6 endpoint for this prefix";
                      container behavior {
                        description
                          "endpoint behaviour dx4, dt4 etc.";
                        list vrf {
                          must 'udt46 or dt46';
                          key "vrf-name";
                          description
                            "vrf";
                          leaf vrf-name {
                            type union {
                              type string {
                                pattern 'default' {
                                  description
                                    "Use the default vrf";
                                }
                              }
                              type string {
                                length "1..32" {
                                  description
                                    "vrf name";
                                }
                              }
                            }
                            description
                              "vrf";
                          }
                          container udt46 {
                            must 'not(../dt46)';
                            presence "Indicates a u-dt46 node is configured.";
                            description
                              "udt46 behavior";
                          }
                          container dt46 {
                            must 'not(../dt46)';
                            presence "Indicates a dt46 node is configured.";
                            description
                              "dt46 behavior";
                          }
                        }
                      }
                    }
                  }
                }
                container sr-policies {
                  description
                    "segment routing policy";
                  list sr-policy {
                    key "sr-policy-name";
                    description
                      "segment routing policy";
                    leaf sr-policy-name {
                      type xr:Cisco-ios-xr-string {
                        length "1..1024" {
                          description
                            "SR policy name";
                        }
                      }
                      description
                        "segment routing policy";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interfaces {
                  description
                    "Forwarding interface";
                  list nexthop-interface {
                    key "interface-name";
                    description
                      "Forwarding interface";
                    leaf interface-name {
                      type xr:Interface-name;
                      description
                        "Forwarding interface";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interface-addresses {
                  description
                    "Forwarding interface";
                  list nexthop-interface-address {
                    key "interface-name address";
                    description
                      "Forwarding interface";
                    leaf interface-name {
                      type xr:Interface-name;
                      description
                        "Forwarding interface";
                    }
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-addresses {
                  description
                    "Forwarding router's address";
                  list nexthop-address {
                    key "address";
                    description
                      "Forwarding router's address";
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                        container multihop {
                          presence "Indicates a multihop node is configured.";
                          description
                            "Enable BFD Multihop";
                          leaf address {
                            type inet:ipv6-address-no-zone;
                            mandatory true;
                            description
                              "Source address";
                          }
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                  list nexthop-address-segment-routing {
                    key "address mpls-path-name";
                    description
                      "Forwarding router's address";
                    leaf address {
                      type inet:ipv6-address-no-zone;
                      description
                        "Forwarding router's address";
                    }
                    leaf mpls-path-name {
                      type xr:Cisco-ios-xr-string {
                        length "1..1024" {
                          description
                            "Path name";
                        }
                      }
                      description
                        "Configure path name";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    leaf description {
                      type string {
                        length "1..30" {
                          description
                            "short description of static route";
                        }
                      }
                      description
                        "description of the static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                  }
                }
                container vrfs {
                  description
                    "Destination VRF";
                  list vrf-only {
                    key "vrf-name";
                    description
                      "Destination only VRF";
                    leaf vrf-name {
                      type xr:Cisco-ios-xr-string {
                        length "1..32" {
                          description
                            "VRF name";
                        }
                      }
                      description
                        "Destination VRF";
                    }
                    leaf description {
                      type string {
                        length "1..254" {
                          description
                            "short description of static route";
                        }
                      }
                      description
                        "description of the static route";
                    }
                    leaf algorithm {
                      type uint32 {
                        range "128..255" {
                          description
                            "Set algorithm value for this route";
                        }
                      }
                      description
                        "Set algorithm value for this route";
                    }
                  }
                  list vrf {
                    must "sr-policies/sr-policy or
                          nexthop-interfaces/nexthop-interface or
                          nexthop-interface-addresses/nexthop-interface-address or
                          nexthop-addresses/nexthop-address";
                    key "vrf-name";
                    description
                      "Destination VRF";
                    leaf vrf-name {
                      type xr:Cisco-ios-xr-string {
                        length "1..32" {
                          description
                            "VRF name";
                        }
                      }
                      description
                        "Destination VRF";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv6-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                  }
                }
              }
            }
            container topologies {
              description
                "Topology static route configuration subcommands";
              list topology {
                key "topology-name";
                description
                  "Topology static route configuration subcommands";
                leaf topology-name {
                  type xr:Cisco-ios-xr-string {
                    length "1..63" {
                      description
                        "Topology name";
                    }
                  }
                  description
                    "Topology static route configuration subcommands";
                }
              }
            }
          }
          container multicast {
            description
              "Multicast commands";
            container prefixes {
              description
                "Destination prefix";
              list prefix {
                must "segment-routing/mpls/path/names/name or
                      sr-policies/sr-policy or
                      nexthop-interfaces/nexthop-interface or
                      nexthop-interface-addresses/nexthop-interface-address or
                      nexthop-addresses/nexthop-address or
                      nexthop-addresses/nexthop-address-segment-routing or
                      vrfs/vrf-only or vrfs/vrf/sr-policies/sr-policy or
                      vrfs/vrf/nexthop-interfaces/nexthop-interface or
                      vrfs/vrf/nexthop-interface-addresses/nexthop-interface-address or
                      vrfs/vrf/nexthop-addresses/nexthop-address";
                key "prefix-address prefix-length";
                description
                  "Destination prefix";
                leaf prefix-address {
                  type inet:ipv6-address-no-zone;
                  description
                    "Destination prefix";
                }
                leaf prefix-length {
                  type uint32 {
                    range "0..128";
                  }
                  description
                    "Destination prefix length";
                }
                container segment-routing {
                  description
                    "Configure Static Segment Routing";
                  container mpls {
                    description
                      "Configure mpls path name";
                    container path {
                      description
                        "Configure path name";
                      container names {
                        description
                          "Configure path name";
                        list name {
                          key "path-name";
                          description
                            "Configure path name";
                          leaf path-name {
                            type xr:Cisco-ios-xr-string {
                              length "1..1024" {
                                description
                                  "Path name";
                              }
                            }
                            description
                              "Configure path name";
                          }
                          leaf distance-metric {
                            type uint32 {
                              range "1..254" {
                                description
                                  "Distance metric for this route";
                              }
                            }
                            description
                              "Distance metric for this route";
                          }
                          leaf tag {
                            type uint32 {
                              range "1..4294967295" {
                                description
                                  "Set tag for this route";
                              }
                            }
                            description
                              "Set tag for this route";
                          }
                          leaf description {
                            type string {
                              length "1..30" {
                                description
                                  "short description of static route";
                              }
                            }
                            description
                              "description of the static route";
                          }
                          leaf metric {
                            type uint32 {
                              range "1..16777214" {
                                description
                                  "Set metric for this route";
                              }
                            }
                            description
                              "Set metric for this route";
                          }
                          leaf algorithm {
                            type uint32 {
                              range "128..255" {
                                description
                                  "Set algorithm value for this route";
                              }
                            }
                            description
                              "Set algorithm value for this route";
                          }
                        }
                      }
                    }
                  }
                }
                container sr-policies {
                  description
                    "segment routing policy";
                  list sr-policy {
                    key "sr-policy-name";
                    description
                      "segment routing policy";
                    leaf sr-policy-name {
                      type xr:Cisco-ios-xr-string {
                        length "1..1024" {
                          description
                            "SR policy name";
                        }
                      }
                      description
                        "segment routing policy";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interfaces {
                  description
                    "Forwarding interface";
                  list nexthop-interface {
                    key "interface-name";
                    description
                      "Forwarding interface";
                    leaf interface-name {
                      type xr:Interface-name;
                      description
                        "Forwarding interface";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-interface-addresses {
                  description
                    "Forwarding interface";
                  list nexthop-interface-address {
                    key "interface-name address";
                    description
                      "Forwarding interface";
                    leaf interface-name {
                      type xr:Interface-name;
                      description
                        "Forwarding interface";
                    }
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                }
                container nexthop-addresses {
                  description
                    "Forwarding router's address";
                  list nexthop-address {
                    key "address";
                    description
                      "Forwarding router's address";
                    leaf address {
                      type inet:ip-address-no-zone;
                      description
                        "Forwarding router's address";
                    }
                    container bfd {
                      description
                        "Configure BFD paramenters";
                      container fast-detect {
                        presence "Indicates a fast-detect node is configured.";
                        description
                          "Enable Fast detection";
                        leaf minimum-interval {
                          type uint32 {
                            range "3..30000" {
                              description
                                "interval in milli-seconds";
                            }
                          }
                          description
                            "Hello interval";
                        }
                        leaf multiplier {
                          type uint32 {
                            range "1..10" {
                              description
                                "Detect multiplier";
                            }
                          }
                          description
                            "Detect multiplier";
                        }
                        container multihop {
                          presence "Indicates a multihop node is configured.";
                          description
                            "Enable BFD Multihop";
                          leaf address {
                            type inet:ipv6-address-no-zone;
                            mandatory true;
                            description
                              "Source address";
                          }
                        }
                      }
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    container permanent {
                      presence "Indicates a permanent node is configured.";
                      description
                        "Permanent route";
                    }
                    leaf vrflabel {
                      type uint32 {
                        range "0..4294967295" {
                          description
                            "VRF label";
                        }
                      }
                      description
                        "VRF label";
                    }
                    leaf tunnel-id {
                      type uint32 {
                        range "0..4294967295" {
                          description
                            "Tunnel ID";
                        }
                      }
                      description
                        "Tunnel ID";
                    }
                    leaf description {
                      type string {
                        length "1..30" {
                          description
                            "short description of static route";
                        }
                      }
                      description
                        "description of the static route";
                    }
                    leaf track {
                      type xr:Cisco-ios-xr-string {
                        length "1..32" {
                          description
                            "Object to be tracked";
                        }
                      }
                      description
                        "Enable object tracking for static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                    container prefer-rib-over-ldp {
                      presence "Indicates a prefer-rib-over-ldp node is configured.";
                      description
                        "Flag passed to rib to prefer rib over ldp";
                    }
                    container non-recurse {
                      presence "Indicates a non-recurse node is configured.";
                      description
                        "Disable Recursive lookup of next hop for the given static route";
                    }
                  }
                  list nexthop-address-segment-routing {
                    key "address mpls-path-name";
                    description
                      "Forwarding router's address";
                    leaf address {
                      type inet:ipv6-address-no-zone;
                      description
                        "Forwarding router's address";
                    }
                    leaf mpls-path-name {
                      type xr:Cisco-ios-xr-string {
                        length "1..1024" {
                          description
                            "Path name";
                        }
                      }
                      description
                        "Configure path name";
                    }
                    leaf distance-metric {
                      type uint32 {
                        range "1..254" {
                          description
                            "Distance metric for this route";
                        }
                      }
                      description
                        "Distance metric for this route";
                    }
                    leaf tag {
                      type uint32 {
                        range "1..4294967295" {
                          description
                            "Set tag for this route";
                        }
                      }
                      description
                        "Set tag for this route";
                    }
                    leaf description {
                      type string {
                        length "1..30" {
                          description
                            "short description of static route";
                        }
                      }
                      description
                        "description of the static route";
                    }
                    leaf metric {
                      type uint32 {
                        range "1..16777214" {
                          description
                            "Set metric for this route";
                        }
                      }
                      description
                        "Set metric for this route";
                    }
                    leaf algorithm {
                      type uint32 {
                        range "128..255" {
                          description
                            "Set algorithm value for this route";
                        }
                      }
                      description
                        "Set algorithm value for this route";
                    }
                  }
                }
                container vrfs {
                  description
                    "Destination VRF";
                  list vrf-only {
                    key "vrf-name";
                    description
                      "Destination only VRF";
                    leaf vrf-name {
                      type xr:Cisco-ios-xr-string {
                        length "1..32" {
                          description
                            "VRF name";
                        }
                      }
                      description
                        "Destination VRF";
                    }
                    leaf description {
                      type string {
                        length "1..254" {
                          description
                            "short description of static route";
                        }
                      }
                      description
                        "description of the static route";
                    }
                    leaf algorithm {
                      type uint32 {
                        range "128..255" {
                          description
                            "Set algorithm value for this route";
                        }
                      }
                      description
                        "Set algorithm value for this route";
                    }
                  }
                  list vrf {
                    must "sr-policies/sr-policy or
                          nexthop-interfaces/nexthop-interface or
                          nexthop-interface-addresses/nexthop-interface-address or
                          nexthop-addresses/nexthop-address";
                    key "vrf-name";
                    description
                      "Destination VRF";
                    leaf vrf-name {
                      type xr:Cisco-ios-xr-string {
                        length "1..32" {
                          description
                            "VRF name";
                        }
                      }
                      description
                        "Destination VRF";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv6-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                  }
                }
              }
            }
            container topologies {
              description
                "Topology static route configuration subcommands";
              list topology {
                key "topology-name";
                description
                  "Topology static route configuration subcommands";
                leaf topology-name {
                  type xr:Cisco-ios-xr-string {
                    length "1..63" {
                      description
                        "Topology name";
                    }
                  }
                  description
                    "Topology static route configuration subcommands";
                }
                container prefixes {
                  description
                    "Destination prefix";
                  list prefix {
                    must "sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv6-address-no-zone;
                      description
                        "Destination prefix";
                    }
                    leaf prefix-length {
                      type uint32 {
                        range "0..128";
                      }
                      description
                        "Destination prefix length";
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv6-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv6-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                        leaf algorithm {
                          type uint32 {
                            range "128..255" {
                              description
                                "Set algorithm value for this route";
                            }
                          }
                          description
                            "Set algorithm value for this route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv6-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
            }
          }
        }
      }
      container vrfs {
        description
          "VRF Static route configuration subcommands";
        list vrf {
          key "vrf-name";
          description
            "VRF Static route configuration subcommands";
          leaf vrf-name {
            type xr:Cisco-ios-xr-string {
              length "1..32" {
                description
                  "VRF name";
              }
            }
            description
              "VRF Static route configuration subcommands";
          }
          container address-family {
            description
              "Static route address family configuration subcommands";
            container ipv4 {
              description
                "IPv4 commands";
              container unicast {
                description
                  "Unicast commands";
                container prefixes {
                  description
                    "Destination prefix";
                  list prefix {
                    must "segment-routing/mpls/path/names/name or
                          remote-next-hop/addresses/address/tunnel/vxlan/indexes/index or
                          sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv4-address-no-zone;
                      description
                        "Destination prefix";
                    }
                    leaf prefix-length {
                      type uint32 {
                        range "0..128";
                      }
                      description
                        "Destination prefix length";
                    }
                    container remote-next-hop {
                      description
                        "remote tunnel endpoint address in default VRF";
                      container addresses {
                        description
                          "Forwarding router ipv4 address";
                        list address {
                          key "address";
                          description
                            "Forwarding router ipv4 or ipv6 address";
                          leaf address {
                            type inet:ip-address-no-zone;
                            description
                              "Forwarding router ipv4 or ipv6 address";
                          }
                          container tunnel {
                            description
                              "Static tunnel commands";
                            container vxlan {
                              description
                                "VXLAN encap type";
                              container indexes {
                                description
                                  "32 bit unique index for this path";
                                list index {
                                  must 'vni or evni';
                                  key "index-id";
                                  description
                                    "32 bit unique index for this path";
                                  leaf index-id {
                                    type uint32 {
                                      range "0..4294967295" {
                                        description
                                          "32 bit unique index for this path";
                                      }
                                    }
                                    description
                                      "32 bit unique index for this path";
                                  }
                                  leaf nve {
                                    type uint32 {
                                      range "0..65535" {
                                        description
                                          "NVE ID to associate this Prefix";
                                      }
                                    }
                                    mandatory true;
                                    description
                                      "NVE ID to associate this Prefix";
                                  }
                                  leaf vni {
                                    type uint32 {
                                      range "1..16777215" {
                                        description
                                          "Ingress VNI for the tunnel prefix";
                                      }
                                    }
                                    must 'not(../evni)';
                                    description
                                      "Ingress VNI for the tunnel prefix";
                                  }
                                  leaf evni {
                                    type uint32 {
                                      range "1..16777215" {
                                        description
                                          "Engress VNI for the tunnel prefix";
                                      }
                                    }
                                    must '../src-mac';
                                    description
                                      "Engress VNI for the tunnel prefix";
                                  }
                                  leaf src-mac {
                                    type yang:mac-address;
                                    description
                                      "source mac for the VXLAN tunnel";
                                  }
                                  leaf distance-metric-for-this-route {
                                    type uint32 {
                                      range "1..254" {
                                        description
                                          "Distance metric for this route";
                                      }
                                    }
                                    description
                                      "Distance metric for this route";
                                  }
                                  leaf tag {
                                    type uint32 {
                                      range "1..4294967295" {
                                        description
                                          "Set tag for this route";
                                      }
                                    }
                                    description
                                      "Set tag for this route";
                                  }
                                  leaf description {
                                    type xr:Cisco-ios-xr-string {
                                      length "1..30" {
                                        description
                                          "short description of static route";
                                      }
                                    }
                                    description
                                      "description of the static route";
                                  }
                                  leaf track {
                                    type xr:Cisco-ios-xr-string {
                                      length "1..32" {
                                        description
                                          "Object to be tracked";
                                      }
                                    }
                                    description
                                      "Enable object tracking for static route";
                                  }
                                  leaf metric {
                                    type uint32 {
                                      range "1..16777214" {
                                        description
                                          "Set metric for this route";
                                      }
                                    }
                                    description
                                      "Set metric for this route";
                                  }
                                  container prefer-rib-over-ldp {
                                    presence "Indicates a prefer-rib-over-ldp node is configured.";
                                    description
                                      "Flag passed to rib to prefer rib over ldp";
                                  }
                                  container permanent {
                                    presence "Indicates a permanent node is configured.";
                                    description
                                      "Permanent route";
                                  }
                                  container tunnel-opt-mode {
                                    description
                                      "Tunnel optimization mode";
                                    container disable {
                                      presence "Indicates a disable node is configured.";
                                      description
                                        "Disable per path optimization";
                                    }
                                  }
                                }
                              }
                            }
                          }
                        }
                      }
                    }
                    container segment-routing {
                      description
                        "Configure Static Segment Routing";
                      container mpls {
                        description
                          "Configure mpls path name";
                        container path {
                          description
                            "Configure path name";
                          container names {
                            description
                              "Configure path name";
                            list name {
                              key "path-name";
                              description
                                "Configure path name";
                              leaf path-name {
                                type xr:Cisco-ios-xr-string {
                                  length "1..1024" {
                                    description
                                      "Path name";
                                  }
                                }
                                description
                                  "Configure path name";
                              }
                              leaf distance-metric {
                                type uint32 {
                                  range "1..254" {
                                    description
                                      "Distance metric for this route";
                                  }
                                }
                                description
                                  "Distance metric for this route";
                              }
                              leaf tag {
                                type uint32 {
                                  range "1..4294967295" {
                                    description
                                      "Set tag for this route";
                                  }
                                }
                                description
                                  "Set tag for this route";
                              }
                              leaf description {
                                type string {
                                  length "1..30" {
                                    description
                                      "short description of static route";
                                  }
                                }
                                description
                                  "description of the static route";
                              }
                              leaf metric {
                                type uint32 {
                                  range "1..16777214" {
                                    description
                                      "Set metric for this route";
                                  }
                                }
                                description
                                  "Set metric for this route";
                              }
                            }
                          }
                        }
                      }
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv4-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv4-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv4-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
              container multicast {
                description
                  "Multicast commands";
                container prefixes {
                  description
                    "Destination prefix";
                  list prefix {
                    must "segment-routing/mpls/path/names/name or
                          sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv4-address-no-zone;
                      description
                        "Destination prefix";
                    }
                    leaf prefix-length {
                      type uint32 {
                        range "0..128";
                      }
                      description
                        "Destination prefix length";
                    }
                    container segment-routing {
                      description
                        "Configure Static Segment Routing";
                      container mpls {
                        description
                          "Configure mpls path name";
                        container path {
                          description
                            "Configure path name";
                          container names {
                            description
                              "Configure path name";
                            list name {
                              key "path-name";
                              description
                                "Configure path name";
                              leaf path-name {
                                type xr:Cisco-ios-xr-string {
                                  length "1..1024" {
                                    description
                                      "Path name";
                                  }
                                }
                                description
                                  "Configure path name";
                              }
                              leaf distance-metric {
                                type uint32 {
                                  range "1..254" {
                                    description
                                      "Distance metric for this route";
                                  }
                                }
                                description
                                  "Distance metric for this route";
                              }
                              leaf tag {
                                type uint32 {
                                  range "1..4294967295" {
                                    description
                                      "Set tag for this route";
                                  }
                                }
                                description
                                  "Set tag for this route";
                              }
                              leaf description {
                                type string {
                                  length "1..30" {
                                    description
                                      "short description of static route";
                                  }
                                }
                                description
                                  "description of the static route";
                              }
                              leaf metric {
                                type uint32 {
                                  range "1..16777214" {
                                    description
                                      "Set metric for this route";
                                  }
                                }
                                description
                                  "Set metric for this route";
                              }
                            }
                          }
                        }
                      }
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv4-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv4-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv4-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
            }
            container ipv6 {
              description
                "IPv6 commands";
              container unicast {
                description
                  "Unicast commands";
                container prefixes {
                  description
                    "Destination prefix";
                  list prefix {
                    must "segment-routing/mpls/path/names/name or
                          remote-next-hop/addresses/address/tunnel/vxlan/indexes/index or
                          sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv6-address-no-zone;
                      description
                        "Destination prefix";
                    }
                    leaf prefix-length {
                      type uint32 {
                        range "0..128";
                      }
                      description
                        "Destination prefix length";
                    }
                    container segment-routing {
                      description
                        "Configure Static Segment Routing";
                      container mpls {
                        description
                          "Configure mpls path name";
                        container path {
                          description
                            "Configure path name";
                          container names {
                            description
                              "Configure path name";
                            list name {
                              key "path-name";
                              description
                                "Configure path name";
                              leaf path-name {
                                type xr:Cisco-ios-xr-string {
                                  length "1..1024" {
                                    description
                                      "Path name";
                                  }
                                }
                                description
                                  "Configure path name";
                              }
                              leaf distance-metric {
                                type uint32 {
                                  range "1..254" {
                                    description
                                      "Distance metric for this route";
                                  }
                                }
                                description
                                  "Distance metric for this route";
                              }
                              leaf tag {
                                type uint32 {
                                  range "1..4294967295" {
                                    description
                                      "Set tag for this route";
                                  }
                                }
                                description
                                  "Set tag for this route";
                              }
                              leaf description {
                                type string {
                                  length "1..30" {
                                    description
                                      "short description of static route";
                                  }
                                }
                                description
                                  "description of the static route";
                              }
                              leaf metric {
                                type uint32 {
                                  range "1..16777214" {
                                    description
                                      "Set metric for this route";
                                  }
                                }
                                description
                                  "Set metric for this route";
                              }
                              leaf algorithm {
                                type uint32 {
                                  range "128..255" {
                                    description
                                      "Set algorithm value for this route";
                                  }
                                }
                                description
                                  "Set algorithm value for this route";
                              }
                            }
                          }
                        }
                      }
                    }
                    container remote-next-hop {
                      description
                        "remote tunnel endpoint address in default VRF";
                      container addresses {
                        description
                          "Forwarding router ipv6 address";
                        list address {
                          key "address";
                          description
                            "Forwarding router ipv4 or ipv6 address";
                          leaf address {
                            type inet:ip-address-no-zone;
                            description
                              "Forwarding router ipv4 or ipv6 address";
                          }
                          container tunnel {
                            description
                              "Static tunnel commands";
                            container vxlan {
                              description
                                "VXLAN encap type";
                              container indexes {
                                description
                                  "32 bit unique index for this path";
                                list index {
                                  must 'vni or evni';
                                  key "index-id";
                                  description
                                    "32 bit unique index for this path";
                                  leaf index-id {
                                    type uint32 {
                                      range "0..4294967295" {
                                        description
                                          "32 bit unique index for this path";
                                      }
                                    }
                                    description
                                      "32 bit unique index for this path";
                                  }
                                  leaf nve {
                                    type uint32 {
                                      range "0..65535" {
                                        description
                                          "NVE ID to associate this Prefix";
                                      }
                                    }
                                    mandatory true;
                                    description
                                      "NVE ID to associate this Prefix";
                                  }
                                  leaf vni {
                                    type uint32 {
                                      range "1..16777215" {
                                        description
                                          "Ingress VNI for the tunnel prefix";
                                      }
                                    }
                                    must 'not(../evni)';
                                    description
                                      "Ingress VNI for the tunnel prefix";
                                  }
                                  leaf evni {
                                    type uint32 {
                                      range "1..16777215" {
                                        description
                                          "Engress VNI for the tunnel prefix";
                                      }
                                    }
                                    must '../src-mac';
                                    description
                                      "Engress VNI for the tunnel prefix";
                                  }
                                  leaf src-mac {
                                    type yang:mac-address;
                                    description
                                      "source mac for the VXLAN tunnel";
                                  }
                                  leaf distance-metric-for-this-route {
                                    type uint32 {
                                      range "1..254" {
                                        description
                                          "Distance metric for this route";
                                      }
                                    }
                                    description
                                      "Distance metric for this route";
                                  }
                                  leaf tag {
                                    type uint32 {
                                      range "1..4294967295" {
                                        description
                                          "Set tag for this route";
                                      }
                                    }
                                    description
                                      "Set tag for this route";
                                  }
                                  leaf description {
                                    type xr:Cisco-ios-xr-string {
                                      length "1..30" {
                                        description
                                          "short description of static route";
                                      }
                                    }
                                    description
                                      "description of the static route";
                                  }
                                  leaf track {
                                    type xr:Cisco-ios-xr-string {
                                      length "1..32" {
                                        description
                                          "Object to be tracked";
                                      }
                                    }
                                    description
                                      "Enable object tracking for static route";
                                  }
                                  leaf metric {
                                    type uint32 {
                                      range "1..16777214" {
                                        description
                                          "Set metric for this route";
                                      }
                                    }
                                    description
                                      "Set metric for this route";
                                  }
                                  container prefer-rib-over-ldp {
                                    presence "Indicates a prefer-rib-over-ldp node is configured.";
                                    description
                                      "Flag passed to rib to prefer rib over ldp";
                                  }
                                  container permanent {
                                    presence "Indicates a permanent node is configured.";
                                    description
                                      "Permanent route";
                                  }
                                  container tunnel-opt-mode {
                                    description
                                      "Tunnel optimization mode";
                                    container disable {
                                      presence "Indicates a disable node is configured.";
                                      description
                                        "Disable per path optimization";
                                    }
                                  }
                                }
                              }
                            }
                          }
                        }
                      }
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv6-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv6-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                        leaf algorithm {
                          type uint32 {
                            range "128..255" {
                              description
                                "Set algorithm value for this route";
                            }
                          }
                          description
                            "Set algorithm value for this route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv6-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
              container multicast {
                description
                  "Multicast commands";
                container prefixes {
                  description
                    "Destination prefix";
                  list prefix {
                    must "segment-routing/mpls/path/names/name or
                          sr-policies/sr-policy or
                          nexthop-interfaces/nexthop-interface or
                          nexthop-interface-addresses/nexthop-interface-address or
                          nexthop-addresses/nexthop-address or
                          nexthop-addresses/nexthop-address-segment-routing or
                          vrfs/vrf-only or vrfs/vrf/sr-policies/sr-policy or
                          vrfs/vrf/nexthop-interfaces/nexthop-interface or
                          vrfs/vrf/nexthop-interface-addresses/nexthop-interface-address or
                          vrfs/vrf/nexthop-addresses/nexthop-address";
                    key "prefix-address prefix-length";
                    description
                      "Destination prefix";
                    leaf prefix-address {
                      type inet:ipv6-address-no-zone;
                      description
                        "Destination prefix";
                    }
                    leaf prefix-length {
                      type uint32 {
                        range "0..128";
                      }
                      description
                        "Destination prefix length";
                    }
                    container segment-routing {
                      description
                        "Configure Static Segment Routing";
                      container mpls {
                        description
                          "Configure mpls path name";
                        container path {
                          description
                            "Configure path name";
                          container names {
                            description
                              "Configure path name";
                            list name {
                              key "path-name";
                              description
                                "Configure path name";
                              leaf path-name {
                                type xr:Cisco-ios-xr-string {
                                  length "1..1024" {
                                    description
                                      "Path name";
                                  }
                                }
                                description
                                  "Configure path name";
                              }
                              leaf distance-metric {
                                type uint32 {
                                  range "1..254" {
                                    description
                                      "Distance metric for this route";
                                  }
                                }
                                description
                                  "Distance metric for this route";
                              }
                              leaf tag {
                                type uint32 {
                                  range "1..4294967295" {
                                    description
                                      "Set tag for this route";
                                  }
                                }
                                description
                                  "Set tag for this route";
                              }
                              leaf description {
                                type string {
                                  length "1..30" {
                                    description
                                      "short description of static route";
                                  }
                                }
                                description
                                  "description of the static route";
                              }
                              leaf metric {
                                type uint32 {
                                  range "1..16777214" {
                                    description
                                      "Set metric for this route";
                                  }
                                }
                                description
                                  "Set metric for this route";
                              }
                              leaf algorithm {
                                type uint32 {
                                  range "128..255" {
                                    description
                                      "Set algorithm value for this route";
                                  }
                                }
                                description
                                  "Set algorithm value for this route";
                              }
                            }
                          }
                        }
                      }
                    }
                    container sr-policies {
                      description
                        "segment routing policy";
                      list sr-policy {
                        key "sr-policy-name";
                        description
                          "segment routing policy";
                        leaf sr-policy-name {
                          type xr:Cisco-ios-xr-string {
                            length "1..1024" {
                              description
                                "SR policy name";
                            }
                          }
                          description
                            "segment routing policy";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interfaces {
                      description
                        "Forwarding interface";
                      list nexthop-interface {
                        key "interface-name";
                        description
                          "Forwarding interface";
                        leaf interface-name {
                          type xr:Interface-name;
                          description
                            "Forwarding interface";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-interface-addresses {
                      description
                        "Forwarding interface";
                      list nexthop-interface-address {
                        key "interface-name address";
                        description
                          "Forwarding interface";
                        leaf interface-name {
                          type xr:Interface-name;
                          description
                            "Forwarding interface";
                        }
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                    }
                    container nexthop-addresses {
                      description
                        "Forwarding router's address";
                      list nexthop-address {
                        key "address";
                        description
                          "Forwarding router's address";
                        leaf address {
                          type inet:ip-address-no-zone;
                          description
                            "Forwarding router's address";
                        }
                        container bfd {
                          description
                            "Configure BFD paramenters";
                          container fast-detect {
                            presence "Indicates a fast-detect node is configured.";
                            description
                              "Enable Fast detection";
                            leaf minimum-interval {
                              type uint32 {
                                range "3..30000" {
                                  description
                                    "interval in milli-seconds";
                                }
                              }
                              description
                                "Hello interval";
                            }
                            leaf multiplier {
                              type uint32 {
                                range "1..10" {
                                  description
                                    "Detect multiplier";
                                }
                              }
                              description
                                "Detect multiplier";
                            }
                            container multihop {
                              presence "Indicates a multihop node is configured.";
                              description
                                "Enable BFD Multihop";
                              leaf address {
                                type inet:ipv6-address-no-zone;
                                mandatory true;
                                description
                                  "Source address";
                              }
                            }
                          }
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        container permanent {
                          presence "Indicates a permanent node is configured.";
                          description
                            "Permanent route";
                        }
                        leaf vrflabel {
                          type uint32 {
                            range "0..4294967295" {
                              description
                                "VRF label";
                            }
                          }
                          description
                            "VRF label";
                        }
                        leaf tunnel-id {
                          type uint32 {
                            range "0..4294967295" {
                              description
                                "Tunnel ID";
                            }
                          }
                          description
                            "Tunnel ID";
                        }
                        leaf description {
                          type string {
                            length "1..30" {
                              description
                                "short description of static route";
                            }
                          }
                          description
                            "description of the static route";
                        }
                        leaf track {
                          type xr:Cisco-ios-xr-string {
                            length "1..32" {
                              description
                                "Object to be tracked";
                            }
                          }
                          description
                            "Enable object tracking for static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                        container prefer-rib-over-ldp {
                          presence "Indicates a prefer-rib-over-ldp node is configured.";
                          description
                            "Flag passed to rib to prefer rib over ldp";
                        }
                        container non-recurse {
                          presence "Indicates a non-recurse node is configured.";
                          description
                            "Disable Recursive lookup of next hop for the given static route";
                        }
                      }
                      list nexthop-address-segment-routing {
                        key "address mpls-path-name";
                        description
                          "Forwarding router's address";
                        leaf address {
                          type inet:ipv6-address-no-zone;
                          description
                            "Forwarding router's address";
                        }
                        leaf mpls-path-name {
                          type xr:Cisco-ios-xr-string {
                            length "1..1024" {
                              description
                                "Path name";
                            }
                          }
                          description
                            "Configure path name";
                        }
                        leaf distance-metric {
                          type uint32 {
                            range "1..254" {
                              description
                                "Distance metric for this route";
                            }
                          }
                          description
                            "Distance metric for this route";
                        }
                        leaf tag {
                          type uint32 {
                            range "1..4294967295" {
                              description
                                "Set tag for this route";
                            }
                          }
                          description
                            "Set tag for this route";
                        }
                        leaf description {
                          type string {
                            length "1..30" {
                              description
                                "short description of static route";
                            }
                          }
                          description
                            "description of the static route";
                        }
                        leaf metric {
                          type uint32 {
                            range "1..16777214" {
                              description
                                "Set metric for this route";
                            }
                          }
                          description
                            "Set metric for this route";
                        }
                        leaf algorithm {
                          type uint32 {
                            range "128..255" {
                              description
                                "Set algorithm value for this route";
                            }
                          }
                          description
                            "Set algorithm value for this route";
                        }
                      }
                    }
                    container vrfs {
                      description
                        "Destination VRF";
                      list vrf-only {
                        key "vrf-name";
                        description
                          "Destination only VRF";
                        leaf vrf-name {
                          type xr:Cisco-ios-xr-string {
                            length "1..32" {
                              description
                                "VRF name";
                            }
                          }
                          description
                            "Destination VRF";
                        }
                        leaf description {
                          type string {
                            length "1..254" {
                              description
                                "short description of static route";
                            }
                          }
                          description
                            "description of the static route";
                        }
                        leaf algorithm {
                          type uint32 {
                            range "128..255" {
                              description
                                "Set algorithm value for this route";
                            }
                          }
                          description
                            "Set algorithm value for this route";
                        }
                      }
                      list vrf {
                        must "sr-policies/sr-policy or
                              nexthop-interfaces/nexthop-interface or
                              nexthop-interface-addresses/nexthop-interface-address or
                              nexthop-addresses/nexthop-address";
                        key "vrf-name";
                        description
                          "Destination VRF";
                        leaf vrf-name {
                          type xr:Cisco-ios-xr-string {
                            length "1..32" {
                              description
                                "VRF name";
                            }
                          }
                          description
                            "Destination VRF";
                        }
                        container sr-policies {
                          description
                            "segment routing policy";
                          list sr-policy {
                            key "sr-policy-name";
                            description
                              "segment routing policy";
                            leaf sr-policy-name {
                              type xr:Cisco-ios-xr-string {
                                length "1..1024" {
                                  description
                                    "SR policy name";
                                }
                              }
                              description
                                "segment routing policy";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                          }
                        }
                        container nexthop-interfaces {
                          description
                            "Forwarding interface";
                          list nexthop-interface {
                            key "interface-name";
                            description
                              "Forwarding interface";
                            leaf interface-name {
                              type xr:Interface-name;
                              description
                                "Forwarding interface";
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-interface-addresses {
                          description
                            "Forwarding interface";
                          list nexthop-interface-address {
                            key "interface-name address";
                            description
                              "Forwarding interface";
                            leaf interface-name {
                              type xr:Interface-name;
                              description
                                "Forwarding interface";
                            }
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                        container nexthop-addresses {
                          description
                            "Forwarding router's address";
                          list nexthop-address {
                            key "address";
                            description
                              "Forwarding router's address";
                            leaf address {
                              type inet:ip-address-no-zone;
                              description
                                "Forwarding router's address";
                            }
                            container bfd {
                              description
                                "Configure BFD paramenters";
                              container fast-detect {
                                presence "Indicates a fast-detect node is configured.";
                                description
                                  "Enable Fast detection";
                                leaf minimum-interval {
                                  type uint32 {
                                    range "3..30000" {
                                      description
                                        "interval in milli-seconds";
                                    }
                                  }
                                  description
                                    "Hello interval";
                                }
                                leaf multiplier {
                                  type uint32 {
                                    range "1..10" {
                                      description
                                        "Detect multiplier";
                                    }
                                  }
                                  description
                                    "Detect multiplier";
                                }
                                container multihop {
                                  presence "Indicates a multihop node is configured.";
                                  description
                                    "Enable BFD Multihop";
                                  leaf address {
                                    type inet:ipv6-address-no-zone;
                                    mandatory true;
                                    description
                                      "Source address";
                                  }
                                }
                              }
                            }
                            leaf distance-metric {
                              type uint32 {
                                range "1..254" {
                                  description
                                    "Distance metric for this route";
                                }
                              }
                              description
                                "Distance metric for this route";
                            }
                            leaf tag {
                              type uint32 {
                                range "1..4294967295" {
                                  description
                                    "Set tag for this route";
                                }
                              }
                              description
                                "Set tag for this route";
                            }
                            container permanent {
                              presence "Indicates a permanent node is configured.";
                              description
                                "Permanent route";
                            }
                            leaf vrflabel {
                              type uint32 {
                                range "0..4294967295" {
                                  description
                                    "VRF label";
                                }
                              }
                              description
                                "VRF label";
                            }
                            leaf tunnel-id {
                              type uint32 {
                                range "0..4294967295" {
                                  description
                                    "Tunnel ID";
                                }
                              }
                              description
                                "Tunnel ID";
                            }
                            leaf description {
                              type string {
                                length "1..30" {
                                  description
                                    "short description of static route";
                                }
                              }
                              description
                                "description of the static route";
                            }
                            leaf track {
                              type xr:Cisco-ios-xr-string {
                                length "1..32" {
                                  description
                                    "Object to be tracked";
                                }
                              }
                              description
                                "Enable object tracking for static route";
                            }
                            leaf metric {
                              type uint32 {
                                range "1..16777214" {
                                  description
                                    "Set metric for this route";
                                }
                              }
                              description
                                "Set metric for this route";
                            }
                            leaf algorithm {
                              type uint32 {
                                range "128..255" {
                                  description
                                    "Set algorithm value for this route";
                                }
                              }
                              description
                                "Set algorithm value for this route";
                            }
                            container prefer-rib-over-ldp {
                              presence "Indicates a prefer-rib-over-ldp node is configured.";
                              description
                                "Flag passed to rib to prefer rib over ldp";
                            }
                            container non-recurse {
                              presence "Indicates a non-recurse node is configured.";
                              description
                                "Disable Recursive lookup of next hop for the given static route";
                            }
                          }
                        }
                      }
                    }
                  }
                }
              }
            }
          }
        }
      }
      container maximum {
        description
          "Limit the number of static paths which may be configured";
        container path {
          description
            "Limit the number of static paths which may be configured";
          container ipv4 {
            description
              "IPv4 commands";
            leaf maximum-number {
              type uint32 {
                range "1..140000" {
                  description
                    "The maximum number of static paths which can be configured";
                }
              }
              description
                "The maximum number of static paths which can be configured";
            }
          }
          container ipv6 {
            description
              "IPv6 commands";
            leaf maximum-number {
              type uint32 {
                range "1..140000" {
                  description
                    "The maximum number of static paths which can be configured";
                }
              }
              description
                "The maximum number of static paths which can be configured";
            }
          }
        }
      }
    }
  }
}
