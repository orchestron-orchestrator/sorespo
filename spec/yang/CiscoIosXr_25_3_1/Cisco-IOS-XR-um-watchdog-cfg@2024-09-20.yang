module Cisco-IOS-XR-um-watchdog-cfg {
  namespace "http://cisco.com/ns/yang/Cisco-IOS-XR-um-watchdog-cfg";
  prefix Cisco-IOS-XR-um-watchdog-cfg;

  import Cisco-IOS-XR-types {
    prefix xr;
  }
  import Cisco-IOS-XR-um-location-cfg {
    prefix location-cfg;
  }

  import cisco-semver { prefix "semver"; }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco watchd package configuration.
     Copyright (c) 2024 by Cisco Systems, Inc.
     All rights reserved.";

  revision 2024-09-20 {
    description
      "Initial UM2 release";
    semver:module-version "1.0.0";
  }

  revision "2022-07-11" {
    description
      "Added missing description statement to nodes";
  }

  revision "2022-04-20" {
    description
      "Updated range for severe and critical nodes under threshold/memory";
  }

  revision "2021-11-09" {
    description
      "Initial release";
  }

  grouping GROUP-LOCATION-CFG-WATCHDOG-BODY {
    description
      "Grouping for location";
    container watchdog {
      description
        "Watchdog configuration commands";
      container threshold {
        description
          "Watchdog threshold configuration";
        container shmwin {
          description
            "shmwin thresholds";
          leaf minor {
            type uint32 {
              range "1..97" {
                description
                  "memory consumption in percentage";
              }
            }
            must '../severe and ../critical';
            description
              "Threshold for minor state";
          }
          leaf severe {
            type uint32 {
              range "1..98" {
                description
                  "memory consumption in percentage";
              }
            }
            must '../minor and ../critical and . >= ../minor';
            description
              "Threshold for severe state";
          }
          leaf critical {
            type uint32 {
              range "1..99" {
                description
                  "memory consumption in percentage";
              }
            }
            must '../minor and ../severe and . >= ../severe';
            description
              "Threshold for critical state";
          }
        }
        container disk {
          description
            "Disk thresholds";
          leaf minor {
            type uint32 {
              range "1..97" {
                description
                  "disk consumption in percentage";
              }
            }
            must '../severe and ../critical';
            description
              "disk consumption in percentage";
          }
          leaf severe {
            type uint32 {
              range "1..98" {
                description
                  "disk consumption in percentage";
              }
            }
            must '../minor and ../critical and . >= ../minor';
            description
              "Threshold for severe state";
          }
          leaf critical {
            type uint32 {
              range "1..99" {
                description
                  "disk consumption in percentage";
              }
            }
            must '../minor and ../severe and . >= ../severe';
            description
              "Threshold for critical state";
          }
        }
        container memory {
          description
            "Memory thresholds";
          leaf minor {
            type uint32 {
              range "5..40" {
                description
                  "Available memory in percentage";
              }
            }
            must '../severe and ../critical';
            description
              "Threshold for minor state";
          }
          leaf severe {
            type uint32 {
              range "4..40" {
                description
                  "Available memory in percentage";
              }
            }
            must '../minor and ../critical and . >= ../minor';
            description
              "Threshold for severe state";
          }
          leaf critical {
            type uint32 {
              range "3..40" {
                description
                  "Available memory in percentage";
              }
            }
            must '../minor and ../severe and . >= ../severe';
            description
              "Threshold for critical state";
          }
        }
      }
      container resource-utilisation {
        description
          "System resources to be monitored for utilization";
        container cpu {
          description
            "System CPU monitoring, cpu usage is calculated as average cpu utilization for each minute";
          leaf set-threshold {
            type uint32 {
              range "1..99" {
                description
                  "Range for setting set-threshold value";
              }
            }
            must '../clear-threshold';
            description
              "Upper threshold value in percentage used for monitoring, when resource utilization crosses this value user will be notified";
          }
          leaf clear-threshold {
            type uint32 {
              range "1..99" {
                description
                  "Range for setting clear-threshold, this value should not be greater than set-threshold";
              }
            }
            must '../set-threshold and . <= ../set-threshold';
            description
              "lower threshold value in percentage used for monitoring, when resource utilization drops below this value user will be notified";
          }
        }
        container disk0 {
          description
            "Disk0 filesystem monitoring";
          leaf set-threshold {
            type uint32 {
              range "1..99" {
                description
                  "Range for setting set-threshold value";
              }
            }
            must '../clear-threshold';
            description
              "Upper threshold value in percentage used for monitoring, when resource utilization crosses this value user will be notified";
          }
          leaf clear-threshold {
            type uint32 {
              range "1..99" {
                description
                  "Range for setting clear-threshold, this value should not be greater than set-threshold";
              }
            }
            must '../set-threshold and . <= ../set-threshold';
            description
              "lower threshold value in percentage used for monitoring, when resource utilization drops below this value user will be notified";
          }
        }
        container memory {
          description
            "System RAM memory monitoring";
          leaf set-threshold {
            type uint32 {
              range "1..99" {
                description
                  "Range for setting set-threshold value";
              }
            }
            must '../clear-threshold';
            description
              "Upper threshold value in percentage used for monitoring, when resource utilization crosses this value user will be notified";
          }
          leaf clear-threshold {
            type uint32 {
              range "1..99" {
                description
                  "Range for setting clear-threshold, this value should not be greater than set-threshold";
              }
            }
            must '../set-threshold and . <= ../set-threshold';
            description
              "lower threshold value in percentage used for monitoring, when resource utilization drops below this value user will be notified";
          }
        }
        container harddisk {
          description
            "Harddisk filesystem monitoring";
          leaf set-threshold {
            type uint32 {
              range "1..99" {
                description
                  "Range for setting set-threshold value";
              }
            }
            must '../clear-threshold';
            description
              "Upper threshold value in percentage used for monitoring, when resource utilization crosses this value user will be notified";
          }
          leaf clear-threshold {
            type uint32 {
              range "1..99" {
                description
                  "Range for setting clear-threshold, this value should not be greater than set-threshold";
              }
            }
            must '../set-threshold and . <= ../set-threshold';
            description
              "lower threshold value in percentage used for monitoring, when resource utilization drops below this value user will be notified";
          }
        }
      }
    }
    container process-state-monitor {
      presence "Monitor processes for death notification";
      description
        "Monitor processes for death notification";
      container process-names {
        description
          "Process name to monitor for death notification";
        list process-name {
          key "process-name-string";
          description
            "Process name to monitor for death notification";
          leaf process-name-string {
            type xr:Cisco-ios-xr-string {
              length "1..1024" {
                description
                  "Process Name";
              }
            }
            description
              "Process Name";
          }
        }
      }
    }
  }

  augment "/location-cfg:locations/location-cfg:location" {
    description
      "This augment extends the configuration data of Cisco-IOS-XR-um-location-cfg";
    uses GROUP-LOCATION-CFG-WATCHDOG-BODY;
  }

  augment "/location-cfg:locations/location-cfg:preconfigured-location" {
    description
      "This augment extends the configuration data of Cisco-IOS-XR-um-location-cfg";
    uses GROUP-LOCATION-CFG-WATCHDOG-BODY;
  }

  container watchd {
    description
      "Watchdog configuration commands";
    leaf timeout {
      type uint32 {
        range "1..10" {
          description
            "Length of timeout in seconds";
        }
      }
      description
        "Timeout";
    }
  }
  container process-state-monitor {
    description
      "Monitor processes for death notification";
    container location {
      description
        "Specify the location where process has to be monitored";
      container all {
        presence "all locations";
        description
          "all locations";
        container process-names {
          description
            "Process name to monitor for death notification";
          list process-name {
            key "process-name-string";
            description
              "Process name to monitor for death notification";
            leaf process-name-string {
              type xr:Cisco-ios-xr-string {
                length "1..1024" {
                  description
                    "Process Name";
                }
              }
              description
                "Process Name";
            }
          }
        }
      }
    }
  }
  container watchdog {
    description
      "Watchdog configuration commands";
    container resource-utilisation {
      description
        "System resources to be monitored for utilization";
      container cpu {
        description
          "System CPU monitoring, cpu usage is calculated as average cpu utilization for each minute";
        leaf set-threshold {
          type uint32 {
            range "1..99" {
              description
                "Range for setting set-threshold value";
            }
          }
          must '../clear-threshold';
          description
            "Upper threshold value in percentage used for monitoring, when resource utilization crosses this value user will be notified";
        }
        leaf clear-threshold {
          type uint32 {
            range "1..99" {
              description
                "Range for setting clear-threshold, this value should not be greater than set-threshold";
            }
          }
          must '../set-threshold and . <= ../set-threshold';
          description
            "lower threshold value in percentage used for monitoring, when resource utilization drops below this value user will be notified";
        }
      }
      container disk0 {
        description
          "Disk0 filesystem monitoring";
        leaf set-threshold {
          type uint32 {
            range "1..99" {
              description
                "Range for setting set-threshold value";
            }
          }
          must '../clear-threshold';
          description
            "Upper threshold value in percentage used for monitoring, when resource utilization crosses this value user will be notified";
        }
        leaf clear-threshold {
          type uint32 {
            range "1..99" {
              description
                "Range for setting clear-threshold, this value should not be greater than set-threshold";
            }
          }
          must '../set-threshold and . <= ../set-threshold';
          description
            "lower threshold value in percentage used for monitoring, when resource utilization drops below this value user will be notified";
        }
      }
      container memory {
        description
          "System RAM memory monitoring";
        leaf set-threshold {
          type uint32 {
            range "1..99" {
              description
                "Range for setting set-threshold value";
            }
          }
          must '../clear-threshold';
          description
            "Upper threshold value in percentage used for monitoring, when resource utilization crosses this value user will be notified";
        }
        leaf clear-threshold {
          type uint32 {
            range "1..99" {
              description
                "Range for setting clear-threshold, this value should not be greater than set-threshold";
            }
          }
          must '../set-threshold and . <=../set-threshold';
          description
            "lower threshold value in percentage used for monitoring, when resource utilization drops below this value user will be notified";
        }
      }
      container harddisk {
        description
          "Harddisk filesystem monitoring";
        leaf set-threshold {
          type uint32 {
            range "1..99" {
              description
                "Range for setting set-threshold value";
            }
          }
          must '../clear-threshold';
          description
            "Upper threshold value in percentage used for monitoring, when resource utilization crosses this value user will be notified";
        }
        leaf clear-threshold {
          type uint32 {
            range "1..99" {
              description
                "Range for setting clear-threshold, this value should not be greater than set-threshold";
            }
          }
          must '../set-threshold and . <=../set-threshold';
          description
            "lower threshold value in percentage used for monitoring, when resource utilization drops below this value user will be notified";
        }
      }
    }
    container threshold {
      description
        "Watchdog threshold configuration";
      container shmwin {
        description
          "shmwin thresholds";
        leaf minor {
          type uint32 {
            range "1..97" {
              description
                "memory consumption in percentage";
            }
          }
          must '../severe and ../critical';
          description
            "Threshold for minor state";
        }
        leaf severe {
          type uint32 {
            range "1..98" {
              description
                "memory consumption in percentage";
            }
          }
          must '../minor and ../critical and . >= ../minor';
          description
            "Threshold for severe state";
        }
        leaf critical {
          type uint32 {
            range "1..99" {
              description
                "memory consumption in percentage";
            }
          }
          must '../minor and ../severe and . >= ../severe';
          description
            "Threshold for critical state";
        }
      }
      container disk {
        description
          "Disk thresholds";
        leaf minor {
          type uint32 {
            range "1..97" {
              description
                "disk consumption in percentage";
            }
          }
          must '../severe and ../critical';
          description
            "disk consumption in percentage";
        }
        leaf severe {
          type uint32 {
            range "1..98" {
              description
                "disk consumption in percentage";
            }
          }
          must '../minor and ../critical and . >= ../minor';
          description
            "Threshold for severe state";
        }
        leaf critical {
          type uint32 {
            range "1..99" {
              description
                "disk consumption in percentage";
            }
          }
          must '../minor and ../severe and . >= ../severe';
          description
            "Threshold for critical state";
        }
      }
      container memory {
        description
          "Memory thresholds";
        leaf switchover {
          type enumeration {
            enum minor {
              value 2;
              description
                "Perform RPFO on minor memory state if standby is ready";
            }
            enum severe {
              value 3;
              description
                "Perform RPFO on severe memory state if standby is ready";
            }
            enum critical {
              value 4;
              description
                "Perform RPFO on critical memory state if standby is ready (recommended)";
            }
          }
          description
            "Switchover the RP at configured memory state";
        }
        container minor {
          description
            "Threshold for minor state";
          leaf minor-number {
            type uint32 {
              range "5..40" {
                description
                  "Available memory in percentage";
              }
            }
            must '../severe and ../critical';
            description
              "Available memory in percentage";
          }
          leaf severe {
            type uint32 {
              range "4..40" {
                description
                  "Available memory in percentage";
              }
            }
            must '../minor-number and ../critical and . >= ../minor-number';
            description
              "Threshold for severe state";
          }
          leaf critical {
            type uint32 {
              range "3..40" {
                description
                  "Available memory in percentage";
              }
            }
            must '../minor-number and ../severe and . >= ../severe';
            description
              "Threshold for critical state";
          }
        }
      }
    }
    container overload {
      description
        "Watchdog monitor configurations";
      container notification {
        description
          "Critical event notification configuration";
        leaf disable {
          type empty;
          description
            "Disable critical event notification";
        }
      }
      leaf throttle-timeout {
        type uint32 {
          range "5..120" {
            description
              "Length of timeout in seconds";
          }
        }
        description
          "Watchdog overload throttle timeout configuration";
      }
    }
    container restart {
      description
        "Watchdog restart configurations";
      container deadlock {
        description
          "Watchdog restart deadlock configuration";
        leaf disable {
          type empty;
          description
            "Disable watchdog restart deadlock";
        }
      }
      container memory-hog {
        description
          "Watchdog restart memory-hog configuration";
        leaf disable {
          type empty;
          description
            "Disable watchdog restart memory-hog";
        }
      }
    }
  }
}
