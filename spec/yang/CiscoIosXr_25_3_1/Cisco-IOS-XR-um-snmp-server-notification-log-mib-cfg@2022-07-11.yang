module Cisco-IOS-XR-um-snmp-server-notification-log-mib-cfg {

  /*** NAMESPACE / PREFIX DEFINITION ***/

  namespace "http://cisco.com/ns/yang/Cisco-IOS-XR-um-snmp-server-notification-log-mib-cfg";
  prefix um-snmp-server-notification-log-mib-cfg;

  /*** LINKAGE (IMPORTS / INCLUDES) ***/

  import Cisco-IOS-XR-um-snmp-server-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR snmp-server-notification-log-mib package configuration.

     This YANG module augments the
     modules with configuration data.

     Copyright (c) 2020-2025 by Cisco Systems, Inc., and/or its affiliates.
     All rights reserved.";

  revision 2022-07-11 {
    description
      "Added missing description statement to nodes";
    semver:module-version "1.0.0";
  }

  revision "2020-12-14" {
    description
      "Initial release";
    semver:module-version "1.0.0";
  }

  augment "/a1:snmp-server-mibs" {
    description
      "This augment extends snmp-server-mibs nodes
       configuration";
    container notification-log-mib {
      description
        "Configuare the notification-log-mib";
      container default {
        presence "Indicates a default node is configured.";
        description
          "To create a default log";
      }
      leaf global-age-out {
        type uint32 {
          range "1..4294967295" {
            description
              "Time for GlobalAgeOut in min, must be greater then 0";
          }
        }
        description
          "GlobalAgeOut is the minutes associated with the mib";
      }
      leaf global-size {
        type uint32 {
          range "1..15000" {
            description
              "How many notifications should be logged in all logs";
          }
        }
        description
          "GlobalSize, max number of notifications that can be logged in all logs";
      }
      container disable {
        presence "Indicates a disable node is configured.";
        description
          "disable, to disable the logging in default log";
      }
      leaf size {
        type uint32 {
          range "1..15000" {
            description
              "How many notifications should be logged in this log";
          }
        }
        description
          "size, The max number of notifications that this log (default) can hold";
      }
    }
  }
}
