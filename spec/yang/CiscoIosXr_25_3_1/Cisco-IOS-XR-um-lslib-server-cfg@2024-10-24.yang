module Cisco-IOS-XR-um-lslib-server-cfg {
  namespace "http://cisco.com/ns/yang/Cisco-IOS-XR-um-lslib-server-cfg";
  prefix um-lslib-server-cfg;

  import cisco-semver { prefix "semver"; }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco lslib-server package configuration.
     Copyright (c) 2024 by Cisco Systems, Inc.
     All rights reserved.";

  revision 2024-10-24 {
    description
      "Initial UM2 release";
    semver:module-version "1.0.0";
  }


  container lslib-server {
    presence "LSLIB Server configuration";
    description
      "LSLIB Server configuration";
  }
}
