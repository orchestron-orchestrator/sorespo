module Cisco-IOS-XR-um-mpls-oam-cfg {

  /*** NAMESPACE / PREFIX DEFINITION ***/

  namespace "http://cisco.com/ns/yang/Cisco-IOS-XR-um-mpls-oam-cfg";
  prefix um-mpls-oam-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-oam package configuration.

     This YANG module augments the
     modules with configuration data.

     Copyright (c) 2020-2025 by Cisco Systems, Inc., and/or its affiliates.
     All rights reserved.";

  revision "2025-06-12" {
    description
      "Added rfc8029 (initial) option to revision node
       2022-06-11
         Added revision node and downstream-ecmp-faults node support";
    semver:module-version "1.1.0";
  }

  revision "2020-04-10" {
    description
      "Initial release";
    semver:module-version "1.0.0";
  }

  container mpls {
    description
      "Global MPLS configuration subcommands";
    container oam {
      presence "Indicates a oam node is configured.";
      description
        "OAM configuration";
      container echo {
        description
          "Echo request attributes";
        container disable-vendor-extension {
          presence "Indicates a disable-vendor-extension node is configured.";
          description
            "Disable sending vendor extension TLV with echo req";
        }
        container reply-mode {
          description
            "Echo request reply mode attributes";
          container control-channel {
            description
              "Configure control channel reply mode";
            container allow-reverse-lsp {
              presence "Indicates a allow-reverse-lsp node is configured.";
              description
                "Use Reverse LSP as the control channel";
            }
          }
        }
        container revision {
          description
            "Echo packet default revision";
          container one {
            must 'not(../two or ../three
or ../four or ../five)';
            presence "Indicates a one node is configured.";
            description
              "draft-ietf-mpls-lsp-ping-03 (initial)";
          }
          container two {
            must 'not(../one or ../three
or ../four or ../five)';
            presence "Indicates a two node is configured.";
            description
              "draft-ietf-mpls-lsp-ping-03 (rev 1)";
          }
          container three {
            must 'not(../one or ../two
or ../four or ../five)';
            presence "Indicates a three node is configured.";
            description
              "draft-ietf-mpls-lsp-ping-03 (rev 2)";
          }
          container four {
            must 'not(../one or ../two
or ../three or ../five)';
            presence "Indicates a four node is configured.";
            description
              "draft-ietf-mpls-lsp-ping-09 (initial)";
          }
          container five {
            must 'not(../one or ../two
or ../three or ../four)';
            presence "Indicates a five node is configured.";
            description
              "rfc8029 (initial)";
          }
        }
      }
      container dpm {
        presence "Indicates a dpm node is configured.";
        description
          "data plane monitoring";
        leaf pps {
          type uint32 {
            range "1..250" {
              description
                "Rate limit in packets per second - default is 50pps";
            }
          }
          description
            "DPM packets per second rate - default is 50pps";
        }
        leaf interval {
          type uint32 {
            range "1..3600" {
              description
                "Gap in minutes - default is 30 mins";
            }
          }
          description
            "Wait time between each iteration of DPM - default is 30mins";
        }
        container downstream-ecmp-faults {
          presence "Indicates a downstream-ecmp-faults node is configured.";
          description
            "Report downstream mismatches";
        }
      }
    }
  }
}
