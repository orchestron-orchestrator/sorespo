module Cisco-IOS-XR-um-router-rip-cfg {

  /*** NAMESPACE / PREFIX DEFINITION ***/

  namespace "http://cisco.com/ns/yang/Cisco-IOS-XR-um-router-rip-cfg";
  prefix um-router-rip-cfg;

  /*** LINKAGE (IMPORTS / INCLUDES) ***/

  import Cisco-IOS-XR-types {
    prefix xr;
  }
  import ietf-inet-types {
    prefix inet;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR router-rip package configuration.

     This YANG module augments the
     modules with configuration data.

     Copyright (c) 2022-2025 by Cisco Systems, Inc., and/or its affiliates.
     All rights reserved.";

  revision 2021-12-27 {
    description
      "Added in and out support for route-policy to routing updates
       2021-11-30
         Initial release";
    semver:module-version "2.0.0";
  }

  revision "2021-05-02" {
    description
      "Initial release";
    semver:module-version "1.0.0";
  }

  container router {
    description
      "Enable a routing process";
    container rip {
      presence "Indicates a rip node is configured.";
      description
        "RIP configuration subcommands";
      container vrfs {
        description
          "Enter the RIP vrf configuration submode";
        list vrf {
          key "vrf-name";
          description
            "Enter the RIP vrf configuration submode";
          leaf vrf-name {
            type xr:Cisco-ios-xr-string {
              length "1..1024" {
                description
                  "VRF name";
              }
            }
            description
              "Enter the RIP vrf configuration submode";
          }
          container broadcast-for-v2 {
            presence "Indicates a broadcast-for-v2 node is configured.";
            description
              "Send RIP v2 output packets to broadcast address";
          }
          container default-information {
            description
              "Control distribution of default information";
            container originate {
              presence "Indicates a originate node is configured.";
              description
                "Distribute a default route";
              leaf route-policy {
                type xr:Route-policy-name;
                description
                  "Route policy to specify criteria to originate default";
              }
            }
          }
          leaf default-metric {
            type uint32 {
              range "1..15" {
                description
                  "Default metric";
              }
            }
            description
              "Set metric of redistributed routes";
          }
          leaf maximum-paths {
            type uint32 {
              range "1..128" {
                description
                  "Number of paths";
              }
            }
            description
              "Maximum number of paths allowed per route";
          }
          container neighbors {
            description
              "Specify a neighbor router";
            list neighbor {
              key "address";
              description
                "Specify a neighbor router";
              leaf address {
                type inet:ipv4-address-no-zone;
                description
                  "Specify a neighbor router";
              }
            }
          }
          container route-policy {
            description
              "Apply route policy to routing updates";
            leaf in {
              type xr:Route-policy-name;
              description
                "Apply route policy to inbound routing updates";
            }
            leaf out {
              type xr:Route-policy-name;
              description
                "Apply route policy to outbound routing updates";
            }
          }
          container nsf {
            presence "Indicates a nsf node is configured.";
            description
              "Enable Cisco Non Stop Forwarding";
          }
          leaf output-delay {
            type uint32 {
              range "8..50" {
                description
                  "Delay in milliseconds";
              }
            }
            description
              "Interpacket delay for RIP updates";
          }
          container timers {
            description
              "Adjust routing timers";
            leaf basic {
              type uint32 {
                range "5..50000" {
                  description
                    "Interval between updates";
                }
              }
              must '../invalid and ../holddown and ../flush';
              description
                "Basic routing protocol update timers";
            }
            leaf invalid {
              type uint32 {
                range "15..200000" {
                  description
                    "Invalid";
                }
              }
              must '../basic and ../holddown and ../flush';
              description
                "Invalid";
            }
            leaf holddown {
              type uint32 {
                range "15..200000" {
                  description
                    "Holddown";
                }
              }
              must '../invalid and ../basic and ../flush';
              description
                "Holddown";
            }
            leaf flush {
              type uint32 {
                range "16..250000" {
                  description
                    "Flush";
                }
              }
              must '../invalid and ../holddown and ../basic';
              description
                "Flush";
            }
          }
          leaf distance {
            type uint32 {
              range "0..255" {
                description
                  "Administrative distance";
              }
            }
            description
              "Define an administrative distance";
          }
          container validate-update-source {
            description
              "Validate source address of routing updates";
            container disable {
              presence "Indicates a disable node is configured.";
              description
                "Do not validate source address of routing updates";
            }
          }
          container auto-summary {
            presence "Indicates a auto-summary node is configured.";
            description
              "Enable automatic network number summarization";
          }
          container redistribute {
            description
              "Redistribute information from another routing protocol";
            list ospf {
              key "instance-name";
              description
                "Open Shortest Path First (OSPF)";
              leaf instance-name {
                type xr:Cisco-ios-xr-string {
                  length "1..32" {
                    description
                      "Process ID for the OSPF instance";
                  }
                }
                description
                  "Open Shortest Path First (OSPF)";
              }
              leaf route-policy {
                type xr:Route-policy-name;
                description
                  "Route policy reference";
              }
              container match {
                description
                  "Redistribution of OSPF routes";
                container internal {
                  presence "Indicates a internal node is configured.";
                  description
                    "Redistribute OSPF internal routes";
                }
                container external {
                  presence "Indicates a external node is configured.";
                  description
                    "Redistribute OSPF external routes";
                  container one {
                    must 'not(../two)';
                    presence "Indicates a one node is configured.";
                    description
                      "Redistribute external type 1 routes only";
                  }
                  container two {
                    must 'not(../one)';
                    presence "Indicates a two node is configured.";
                    description
                      "Redistribute external type 2 routes only";
                  }
                }
                container nssa-external {
                  presence "Indicates a nssa-external node is configured.";
                  description
                    "Redistribute OSPF NSSA external routes";
                  container one {
                    must 'not(../two)';
                    presence "Indicates a one node is configured.";
                    description
                      "Redistribute NSSA external type 1 routes";
                  }
                  container two {
                    must 'not(../one)';
                    presence "Indicates a two node is configured.";
                    description
                      "Redistribute NSSA external type 2 routes";
                  }
                }
              }
            }
            container connected {
              presence "Indicates a connected node is configured.";
              description
                "Connected";
              leaf route-policy {
                type xr:Route-policy-name;
                description
                  "Route policy reference";
              }
            }
            container static {
              presence "Indicates a static node is configured.";
              description
                "Static";
              leaf route-policy {
                type xr:Route-policy-name;
                description
                  "Route policy reference";
              }
            }
            list eigrp {
              key "as-number";
              description
                "Enhanced Interior Gateway Routing Protocol (EIGRP)";
              leaf as-number {
                type uint32 {
                  range "1..65535" {
                    description
                      "Autonomous system number";
                  }
                }
                description
                  "Enhanced Interior Gateway Routing Protocol (EIGRP)";
              }
              leaf route-policy {
                type xr:Route-policy-name;
                description
                  "Route policy reference";
              }
            }
            list isis {
              key "instance-name";
              description
                "ISO IS-IS";
              leaf instance-name {
                type xr:Cisco-ios-xr-string {
                  length "1..32" {
                    description
                      "IS-IS instance name";
                  }
                }
                description
                  "ISO IS-IS";
              }
              leaf route-policy {
                type xr:Route-policy-name;
                description
                  "Route policy reference";
              }
              leaf level {
                type enumeration {
                  enum level-1 {
                    value 1;
                    description
                      "IS-IS level-1 routes only";
                  }
                  enum level-2 {
                    value 2;
                    description
                      "IS-IS level-2 routes only";
                  }
                  enum level-1-2 {
                    value 3;
                    description
                      "IS-IS level-1 and level-2 routes";
                  }
                }
                description
                  "configure this node";
              }
            }
            container bgp {
              description
                "Border Gateway Protocol (BGP)";
              list as {
                key "as-number";
                description
                  "bgp as-number";
                leaf as-number {
                  type xr:Bgp-as-number;
                  description
                    "bgp as-number";
                }
                leaf route-policy {
                  type xr:Route-policy-name;
                  description
                    "Route policy reference";
                }
                leaf bgp-routes-only {
                  type enumeration {
                    enum internal {
                      value 512;
                      description
                        "BGP internal routes only";
                    }
                    enum external {
                      value 1024;
                      description
                        "BGP external routes only";
                    }
                    enum local {
                      value 2048;
                      description
                        "BGP local routes only";
                    }
                  }
                  description
                    "configure this node";
                }
              }
            }
          }
          container interfaces {
            description
              "Enter the RIP interface configuration submode";
            list interface {
              key "interface-name";
              description
                "Enter the RIP interface configuration submode";
              leaf interface-name {
                type xr:Interface-name;
                description
                  "Enter the RIP interface configuration submode";
              }
              container send {
                description
                  "Advertisement transmission";
                container version {
                  description
                    "Version control";
                  container one {
                    presence "Indicates a one node is configured.";
                    description
                      "RIP version 1";
                  }
                  container two {
                    presence "Indicates a two node is configured.";
                    description
                      "RIP version 2";
                  }
                }
              }
              container receive {
                description
                  "Advertisement reception";
                container version {
                  description
                    "Version control";
                  container one {
                    presence "Indicates a one node is configured.";
                    description
                      "RIP version 1";
                  }
                  container two {
                    presence "Indicates a two node is configured.";
                    description
                      "RIP version 2";
                  }
                }
              }
              container site-of-origin {
                presence "Indicates a site-of-origin node is configured.";
                description
                  "SOO community for prefixes learned over this interface";
                leaf node-type {
                  type enumeration {
                    enum 2-byte-as {
                      value 0;
                      description
                        "2-byte AS format";
                    }
                    enum 4-byte-as {
                      value 2;
                      description
                        "4-byte AS format";
                    }
                    enum ipv4-address {
                      value 1;
                      description
                        "ipv4 address";
                    }
                  }
                  must '../as or ../ip-address';
                  mandatory true;
                  description
                    "site of origin";
                }
                leaf as {
                  type xr:Bgp-as-number;
                  must '../asn2-index';
                  description
                    "bgp as-number";
                }
                leaf asn2-index {
                  type uint32 {
                    range "0..4294967295" {
                      description
                        "ASN2:index (hex or decimal format)";
                    }
                  }
                  must '../as';
                  description
                    "ASN2:index (hex or decimal format)";
                }
                leaf ip-address {
                  type inet:ipv4-address-no-zone;
                  must '../ipv4address-index';
                  description
                    "IPv4 address";
                }
                leaf ipv4address-index {
                  type uint32 {
                    range "0..65535" {
                      description
                        "IPv4Address:index (hex or decimal format)";
                    }
                  }
                  must '../ip-address';
                  description
                    "IPv4Address:index (hex or decimal format)";
                }
              }
              container authentication {
                description
                  "Authentication control";
                leaf keychain {
                  type xr:Cisco-ios-xr-string {
                    length "1..32" {
                      description
                        "Name of the key chain";
                    }
                  }
                  description
                    "Configure an authentication key chain";
                }
                leaf mode {
                  type enumeration {
                    enum text {
                      value 2;
                      description
                        "Clear text authentication";
                    }
                    enum md5 {
                      value 3;
                      description
                        "Keyed message digest";
                    }
                  }
                  description
                    "Authentication mode";
                }
              }
              container broadcast-for-v2 {
                presence "Indicates a broadcast-for-v2 node is configured.";
                description
                  "Specify broadcast address for RIP v2 output packet";
              }
              container metric-zero-accept {
                presence "Indicates a metric-zero-accept node is configured.";
                description
                  "Accept rip update with metric 0";
              }
              container split-horizon {
                description
                  "Disable split horizon";
                container disable {
                  presence "Indicates a disable node is configured.";
                  description
                    "Disable split horzon";
                }
              }
              container poison-reverse {
                presence "Indicates a poison-reverse node is configured.";
                description
                  "Enable poison reverse";
              }
              container passive-interface {
                presence "Indicates a passive-interface node is configured.";
                description
                  "Suppress routing updates on this interface";
              }
              container route-policy {
                description
                  "Apply route policy to routing updates";
                leaf in {
                  type xr:Route-policy-name;
                  description
                    "Apply route policy to inbound routing updates";
                }
                leaf out {
                  type xr:Route-policy-name;
                  description
                    "Apply route policy to outbound routing updates";
                }
              }
            }
          }
          container address-family {
            description
              "RIP VRF address-family configuration submode";
            container ipv6 {
              presence "Indicates a ipv6 node is configured.";
              description
                "IPv6 Address Family";
              container default-information {
                description
                  "Control distribution of default information";
                container originate {
                  presence "Indicates a originate node is configured.";
                  description
                    "Distribute a default route";
                  leaf route-policy {
                    type xr:Route-policy-name;
                    description
                      "Route policy to specify criteria to originate default";
                  }
                }
              }
              leaf default-metric {
                type uint32 {
                  range "1..15" {
                    description
                      "Default metric";
                  }
                }
                description
                  "Set metric of redistributed routes";
              }
              leaf maximum-paths {
                type uint32 {
                  range "1..128" {
                    description
                      "Number of paths";
                  }
                }
                description
                  "Maximum number of paths allowed per route";
              }
              container neighbors {
                description
                  "Specify a neighbor router";
                list neighbor {
                  key "address";
                  description
                    "Specify a neighbor router";
                  leaf address {
                    type inet:ipv6-address-no-zone;
                    description
                      "Specify a neighbor router";
                  }
                }
              }
              container route-policy {
                description
                  "Apply route policy to routing updates";
                leaf in {
                  type xr:Route-policy-name;
                  description
                    "Apply route policy to inbound routing updates";
                }
                leaf out {
                  type xr:Route-policy-name;
                  description
                    "Apply route policy to outbound routing updates";
                }
              }
              leaf distance {
                type uint32 {
                  range "0..255" {
                    description
                      "Administrative distance";
                  }
                }
                description
                  "Define an administrative distance";
              }
              container ipv6-addresses {
                description
                  "IPv6 prefix/length";
                list ipv6-address {
                  must 'distance';
                  key "address length";
                  description
                    "IPv6 prefix/length";
                  leaf address {
                    type inet:ipv6-address-no-zone;
                    description
                      "IPv6 prefix/length";
                  }
                  leaf length {
                    type uint32 {
                      range "0..128";
                    }
                    description
                      "IPv6 prefix/length";
                  }
                  leaf distance {
                    type uint32 {
                      range "0..255" {
                        description
                          "Administrative distance";
                      }
                    }
                    description
                      "Define an administrative distance";
                  }
                }
              }
              container redistribute {
                description
                  "Redistribute information from another routing protocol";
                container ospfv3s {
                  description
                    "Open Shortest Path First (OSPFv3)";
                  list ospfv3 {
                    key "instance-name";
                    description
                      "Open Shortest Path First (OSPFv3)";
                    leaf instance-name {
                      type xr:Cisco-ios-xr-string {
                        length "1..32" {
                          description
                            "Process ID for the OSPFv3 instance";
                        }
                      }
                      description
                        "Open Shortest Path First (OSPFv3)";
                    }
                    leaf route-policy {
                      type xr:Route-policy-name;
                      description
                        "Route policy reference";
                    }
                    container match {
                      description
                        "Redistribution of OSPFv3 routes";
                      container internal {
                        presence "Indicates a internal node is configured.";
                        description
                          "Redistribute OSPFv3 internal routes";
                      }
                      container external {
                        presence "Indicates a external node is configured.";
                        description
                          "Redistribute OSPFv3 external routes";
                        container one {
                          must 'not(../two)';
                          presence "Indicates a one node is configured.";
                          description
                            "Redistribute external type 1 routes only";
                        }
                        container two {
                          must 'not(../one)';
                          presence "Indicates a two node is configured.";
                          description
                            "Redistribute external type 2 routes only";
                        }
                      }
                      container nssa-external {
                        presence "Indicates a nssa-external node is configured.";
                        description
                          "Redistribute OSPFv3 NSSA external routes";
                        container one {
                          must 'not(../two)';
                          presence "Indicates a one node is configured.";
                          description
                            "Redistribute NSSA external type 1 routes";
                        }
                        container two {
                          must 'not(../one)';
                          presence "Indicates a two node is configured.";
                          description
                            "Redistribute NSSA external type 2 routes";
                        }
                      }
                    }
                  }
                }
                container connected {
                  presence "Indicates a connected node is configured.";
                  description
                    "Connected";
                  leaf route-policy {
                    type xr:Route-policy-name;
                    description
                      "Route policy reference";
                  }
                }
                container static {
                  presence "Indicates a static node is configured.";
                  description
                    "Static";
                  leaf route-policy {
                    type xr:Route-policy-name;
                    description
                      "Route policy reference";
                  }
                }
                list eigrp {
                  key "as-number";
                  description
                    "Enhanced Interior Gateway Routing Protocol (EIGRP)";
                  leaf as-number {
                    type uint32 {
                      range "1..65535" {
                        description
                          "Autonomous system number";
                      }
                    }
                    description
                      "Enhanced Interior Gateway Routing Protocol (EIGRP)";
                  }
                  leaf route-policy {
                    type xr:Route-policy-name;
                    description
                      "Route policy reference";
                  }
                }
                list isis {
                  key "instance-name";
                  description
                    "ISO IS-IS";
                  leaf instance-name {
                    type xr:Cisco-ios-xr-string {
                      length "1..32" {
                        description
                          "IS-IS instance name";
                      }
                    }
                    description
                      "ISO IS-IS";
                  }
                  leaf route-policy {
                    type xr:Route-policy-name;
                    description
                      "Route policy reference";
                  }
                  leaf level {
                    type enumeration {
                      enum level-1 {
                        value 1;
                        description
                          "IS-IS level-1 routes only";
                      }
                      enum level-2 {
                        value 2;
                        description
                          "IS-IS level-2 routes only";
                      }
                      enum level-1-2 {
                        value 3;
                        description
                          "IS-IS level-1 and level-2 routes";
                      }
                    }
                    description
                      "configure this node";
                  }
                }
                container bgp {
                  description
                    "Border Gateway Protocol (BGP)";
                  list as {
                    key "as-number";
                    description
                      "bgp as-number";
                    leaf as-number {
                      type xr:Bgp-as-number;
                      description
                        "bgp as-number";
                    }
                    leaf route-policy {
                      type xr:Route-policy-name;
                      description
                        "Route policy reference";
                    }
                    leaf bgp-routes-only {
                      type enumeration {
                        enum internal {
                          value 512;
                          description
                            "BGP internal routes only";
                        }
                        enum external {
                          value 1024;
                          description
                            "BGP external routes only";
                        }
                        enum local {
                          value 2048;
                          description
                            "BGP local routes only";
                        }
                      }
                      description
                        "configure this node";
                    }
                  }
                }
              }
              container interfaces {
                description
                  "Enter the RIP interface configuration submode";
                list interface {
                  key "interface-name";
                  description
                    "Enter the RIP interface configuration submode";
                  leaf interface-name {
                    type xr:Interface-name;
                    description
                      "Enter the RIP interface configuration submode";
                  }
                  container metric-zero-accept {
                    presence "Indicates a metric-zero-accept node is configured.";
                    description
                      "Accept rip update with metric 0";
                  }
                  container split-horizon {
                    description
                      "Disable split horizon";
                    container disable {
                      presence "Indicates a disable node is configured.";
                      description
                        "Disable split horzon";
                    }
                  }
                  container poison-reverse {
                    presence "Indicates a poison-reverse node is configured.";
                    description
                      "Enable poison reverse";
                  }
                  container passive-interface {
                    presence "Indicates a passive-interface node is configured.";
                    description
                      "Suppress routing updates on this interface";
                  }
                  container route-policy {
                    description
                      "Apply route policy to routing updates";
                    leaf in {
                      type xr:Route-policy-name;
                      description
                        "Apply route policy to inbound routing updates";
                    }
                    leaf out {
                      type xr:Route-policy-name;
                      description
                        "Apply route policy to outbound routing updates";
                    }
                  }
                }
              }
            }
          }
        }
      }
      container broadcast-for-v2 {
        presence "Indicates a broadcast-for-v2 node is configured.";
        description
          "Send RIP v2 output packets to broadcast address";
      }
      container default-information {
        description
          "Control distribution of default information";
        container originate {
          presence "Indicates a originate node is configured.";
          description
            "Distribute a default route";
          leaf route-policy {
            type xr:Route-policy-name;
            description
              "Route policy to specify criteria to originate default";
          }
        }
      }
      leaf default-metric {
        type uint32 {
          range "1..15" {
            description
              "Default metric";
          }
        }
        description
          "Set metric of redistributed routes";
      }
      leaf maximum-paths {
        type uint32 {
          range "1..128" {
            description
              "Number of paths";
          }
        }
        description
          "Maximum number of paths allowed per route";
      }
      container neighbors {
        description
          "Specify a neighbor router";
        list neighbor {
          key "address";
          description
            "Specify a neighbor router";
          leaf address {
            type inet:ipv4-address-no-zone;
            description
              "Specify a neighbor router";
          }
        }
      }
      container route-policy {
        description
          "Apply route policy to routing updates";
        leaf in {
          type xr:Route-policy-name;
          description
            "Apply route policy to inbound routing updates";
        }
        leaf out {
          type xr:Route-policy-name;
          description
            "Apply route policy to outbound routing updates";
        }
      }
      container nsf {
        presence "Indicates a nsf node is configured.";
        description
          "Enable Cisco Non Stop Forwarding";
      }
      leaf output-delay {
        type uint32 {
          range "8..50" {
            description
              "Delay in milliseconds";
          }
        }
        description
          "Interpacket delay for RIP updates";
      }
      container timers {
        description
          "Adjust routing timers";
        leaf basic {
          type uint32 {
            range "5..50000" {
              description
                "Interval between updates";
            }
          }
          must '../invalid and ../holddown and ../flush';
          description
            "Basic routing protocol update timers";
        }
        leaf invalid {
          type uint32 {
            range "15..200000" {
              description
                "Invalid";
            }
          }
          must '../basic and ../holddown and ../flush';
          description
            "Invalid";
        }
        leaf holddown {
          type uint32 {
            range "15..200000" {
              description
                "Holddown";
            }
          }
          must '../invalid and ../basic and ../flush';
          description
            "Holddown";
        }
        leaf flush {
          type uint32 {
            range "16..250000" {
              description
                "Flush";
            }
          }
          must '../invalid and ../holddown and ../basic';
          description
            "Flush";
        }
      }
      leaf distance {
        type uint32 {
          range "0..255" {
            description
              "Administrative distance";
          }
        }
        description
          "Define an administrative distance";
      }
      container validate-update-source {
        description
          "Validate source address of routing updates";
        container disable {
          presence "Indicates a disable node is configured.";
          description
            "Do not validate source address of routing updates";
        }
      }
      container auto-summary {
        presence "Indicates a auto-summary node is configured.";
        description
          "Enable automatic network number summarization";
      }
      container redistribute {
        description
          "Redistribute information from another routing protocol";
        list ospf {
          key "instance-name";
          description
            "Open Shortest Path First (OSPF)";
          leaf instance-name {
            type xr:Cisco-ios-xr-string {
              length "1..32" {
                description
                  "Process ID for the OSPF instance";
              }
            }
            description
              "Open Shortest Path First (OSPF)";
          }
          leaf route-policy {
            type xr:Route-policy-name;
            description
              "Route policy reference";
          }
          container match {
            description
              "Redistribution of OSPF routes";
            container internal {
              presence "Indicates a internal node is configured.";
              description
                "Redistribute OSPF internal routes";
            }
            container external {
              presence "Indicates a external node is configured.";
              description
                "Redistribute OSPF external routes";
              container one {
                must 'not(../two)';
                presence "Indicates a one node is configured.";
                description
                  "Redistribute external type 1 routes only";
              }
              container two {
                must 'not(../one)';
                presence "Indicates a two node is configured.";
                description
                  "Redistribute external type 2 routes only";
              }
            }
            container nssa-external {
              presence "Indicates a nssa-external node is configured.";
              description
                "Redistribute OSPF NSSA external routes";
              container one {
                must 'not(../two)';
                presence "Indicates a one node is configured.";
                description
                  "Redistribute NSSA external type 1 routes";
              }
              container two {
                must 'not(../one)';
                presence "Indicates a two node is configured.";
                description
                  "Redistribute NSSA external type 2 routes";
              }
            }
          }
        }
        container connected {
          presence "Indicates a connected node is configured.";
          description
            "Connected";
          leaf route-policy {
            type xr:Route-policy-name;
            description
              "Route policy reference";
          }
        }
        container static {
          presence "Indicates a static node is configured.";
          description
            "Static";
          leaf route-policy {
            type xr:Route-policy-name;
            description
              "Route policy reference";
          }
        }
        list eigrp {
          key "as-number";
          description
            "Enhanced Interior Gateway Routing Protocol (EIGRP)";
          leaf as-number {
            type uint32 {
              range "1..65535" {
                description
                  "Autonomous system number";
              }
            }
            description
              "Enhanced Interior Gateway Routing Protocol (EIGRP)";
          }
          leaf route-policy {
            type xr:Route-policy-name;
            description
              "Route policy reference";
          }
        }
        list isis {
          key "instance-name";
          description
            "ISO IS-IS";
          leaf instance-name {
            type xr:Cisco-ios-xr-string {
              length "1..32" {
                description
                  "IS-IS instance name";
              }
            }
            description
              "ISO IS-IS";
          }
          leaf route-policy {
            type xr:Route-policy-name;
            description
              "Route policy reference";
          }
          leaf level {
            type enumeration {
              enum level-1 {
                value 1;
                description
                  "IS-IS level-1 routes only";
              }
              enum level-2 {
                value 2;
                description
                  "IS-IS level-2 routes only";
              }
              enum level-1-2 {
                value 3;
                description
                  "IS-IS level-1 and level-2 routes";
              }
            }
            description
              "configure this node";
          }
        }
        container bgp {
          description
            "Border Gateway Protocol (BGP)";
          list as {
            key "as-number";
            description
              "bgp as-number";
            leaf as-number {
              type xr:Bgp-as-number;
              description
                "bgp as-number";
            }
            leaf route-policy {
              type xr:Route-policy-name;
              description
                "Route policy reference";
            }
            leaf bgp-routes-only {
              type enumeration {
                enum internal {
                  value 512;
                  description
                    "BGP internal routes only";
                }
                enum external {
                  value 1024;
                  description
                    "BGP external routes only";
                }
                enum local {
                  value 2048;
                  description
                    "BGP local routes only";
                }
              }
              description
                "configure this node";
            }
          }
        }
      }
      container interfaces {
        description
          "Enter the RIP interface configuration submode";
        list interface {
          key "interface-name";
          description
            "Enter the RIP interface configuration submode";
          leaf interface-name {
            type xr:Interface-name;
            description
              "Enter the RIP interface configuration submode";
          }
          container send {
            description
              "Advertisement transmission";
            container version {
              description
                "Version control";
              container one {
                presence "Indicates a one node is configured.";
                description
                  "RIP version 1";
              }
              container two {
                presence "Indicates a two node is configured.";
                description
                  "RIP version 2";
              }
            }
          }
          container receive {
            description
              "Advertisement reception";
            container version {
              description
                "Version control";
              container one {
                presence "Indicates a one node is configured.";
                description
                  "RIP version 1";
              }
              container two {
                presence "Indicates a two node is configured.";
                description
                  "RIP version 2";
              }
            }
          }
          container site-of-origin {
            presence "Indicates a site-of-origin node is configured.";
            description
              "SOO community for prefixes learned over this interface";
            leaf node-type {
              type enumeration {
                enum 2-byte-as {
                  value 0;
                  description
                    "2-byte AS format";
                }
                enum 4-byte-as {
                  value 2;
                  description
                    "4-byte AS format";
                }
                enum ipv4-address {
                  value 1;
                  description
                    "ipv4 address";
                }
              }
              must '../as or ../ip-address';
              mandatory true;
              description
                "site of origin";
            }
            leaf as {
              type xr:Bgp-as-number;
              must '../asn2-index';
              description
                "bgp as-number";
            }
            leaf asn2-index {
              type uint32 {
                range "0..4294967295" {
                  description
                    "ASN2:index (hex or decimal format)";
                }
              }
              must '../as';
              description
                "ASN2:index (hex or decimal format)";
            }
            leaf ip-address {
              type inet:ipv4-address-no-zone;
              must '../ipv4address-index';
              description
                "IPv4 address";
            }
            leaf ipv4address-index {
              type uint32 {
                range "0..65535" {
                  description
                    "IPv4Address:index (hex or decimal format)";
                }
              }
              must '../ip-address';
              description
                "IPv4Address:index (hex or decimal format)";
            }
          }
          container authentication {
            description
              "Authentication control";
            leaf keychain {
              type xr:Cisco-ios-xr-string {
                length "1..32" {
                  description
                    "Name of the key chain";
                }
              }
              description
                "Configure an authentication key chain";
            }
            leaf mode {
              type enumeration {
                enum text {
                  value 2;
                  description
                    "Clear text authentication";
                }
                enum md5 {
                  value 3;
                  description
                    "Keyed message digest";
                }
              }
              description
                "Authentication mode";
            }
          }
          container broadcast-for-v2 {
            presence "Indicates a broadcast-for-v2 node is configured.";
            description
              "Specify broadcast address for RIP v2 output packet";
          }
          container metric-zero-accept {
            presence "Indicates a metric-zero-accept node is configured.";
            description
              "Accept rip update with metric 0";
          }
          container split-horizon {
            description
              "Disable split horizon";
            container disable {
              presence "Indicates a disable node is configured.";
              description
                "Disable split horzon";
            }
          }
          container poison-reverse {
            presence "Indicates a poison-reverse node is configured.";
            description
              "Enable poison reverse";
          }
          container passive-interface {
            presence "Indicates a passive-interface node is configured.";
            description
              "Suppress routing updates on this interface";
          }
          container route-policy {
            description
              "Apply route policy to routing updates";
            leaf in {
              type xr:Route-policy-name;
              description
                "Apply route policy to inbound routing updates";
            }
            leaf out {
              type xr:Route-policy-name;
              description
                "Apply route policy to outbound routing updates";
            }
          }
        }
      }
      container address-family {
        description
          "RIP address-family configuration submode";
        container ipv6 {
          presence "Indicates a ipv6 node is configured.";
          description
            "IPv6 Address Family";
          container default-information {
            description
              "Control distribution of default information";
            container originate {
              presence "Indicates a originate node is configured.";
              description
                "Distribute a default route";
              leaf route-policy {
                type xr:Route-policy-name;
                description
                  "Route policy to specify criteria to originate default";
              }
            }
          }
          leaf default-metric {
            type uint32 {
              range "1..15" {
                description
                  "Default metric";
              }
            }
            description
              "Set metric of redistributed routes";
          }
          leaf maximum-paths {
            type uint32 {
              range "1..128" {
                description
                  "Number of paths";
              }
            }
            description
              "Maximum number of paths allowed per route";
          }
          container neighbors {
            description
              "Specify a neighbor router";
            list neighbor {
              key "address";
              description
                "Specify a neighbor router";
              leaf address {
                type inet:ipv6-address-no-zone;
                description
                  "Specify a neighbor router";
              }
            }
          }
          container route-policy {
            description
              "Apply route policy to routing updates";
            leaf in {
              type xr:Route-policy-name;
              description
                "Apply route policy to inbound routing updates";
            }
            leaf out {
              type xr:Route-policy-name;
              description
                "Apply route policy to outbound routing updates";
            }
          }
          leaf distance {
            type uint32 {
              range "0..255" {
                description
                  "Administrative distance";
              }
            }
            description
              "Define an administrative distance";
          }
          container ipv6-addresses {
            description
              "IPv6 prefix/length";
            list ipv6-address {
              must 'distance';
              key "address length";
              description
                "IPv6 prefix/length";
              leaf address {
                type inet:ipv6-address-no-zone;
                description
                  "IPv6 prefix/length";
              }
              leaf length {
                type uint32 {
                  range "0..128";
                }
                description
                  "IPv6 prefix/length";
              }
              leaf distance {
                type uint32 {
                  range "0..255" {
                    description
                      "Administrative distance";
                  }
                }
                description
                  "Define an administrative distance";
              }
            }
          }
          container redistribute {
            description
              "Redistribute information from another routing protocol";
            container ospfv3s {
              description
                "Open Shortest Path First (OSPFv3)";
              list ospfv3 {
                key "instance-name";
                description
                  "Open Shortest Path First (OSPFv3)";
                leaf instance-name {
                  type xr:Cisco-ios-xr-string {
                    length "1..32" {
                      description
                        "Process ID for the OSPFv3 instance";
                    }
                  }
                  description
                    "Open Shortest Path First (OSPFv3)";
                }
                leaf route-policy {
                  type xr:Route-policy-name;
                  description
                    "Route policy reference";
                }
                container match {
                  description
                    "Redistribution of OSPFv3 routes";
                  container internal {
                    presence "Indicates a internal node is configured.";
                    description
                      "Redistribute OSPFv3 internal routes";
                  }
                  container external {
                    presence "Indicates a external node is configured.";
                    description
                      "Redistribute OSPFv3 external routes";
                    container one {
                      must 'not(../two)';
                      presence "Indicates a one node is configured.";
                      description
                        "Redistribute external type 1 routes only";
                    }
                    container two {
                      must 'not(../one)';
                      presence "Indicates a two node is configured.";
                      description
                        "Redistribute external type 2 routes only";
                    }
                  }
                  container nssa-external {
                    presence "Indicates a nssa-external node is configured.";
                    description
                      "Redistribute OSPFv3 NSSA external routes";
                    container one {
                      must 'not(../two)';
                      presence "Indicates a one node is configured.";
                      description
                        "Redistribute NSSA external type 1 routes";
                    }
                    container two {
                      must 'not(../one)';
                      presence "Indicates a two node is configured.";
                      description
                        "Redistribute NSSA external type 2 routes";
                    }
                  }
                }
              }
            }
            container connected {
              presence "Indicates a connected node is configured.";
              description
                "Connected";
              leaf route-policy {
                type xr:Route-policy-name;
                description
                  "Route policy reference";
              }
            }
            container static {
              presence "Indicates a static node is configured.";
              description
                "Static";
              leaf route-policy {
                type xr:Route-policy-name;
                description
                  "Route policy reference";
              }
            }
            list eigrp {
              key "as-number";
              description
                "Enhanced Interior Gateway Routing Protocol (EIGRP)";
              leaf as-number {
                type uint32 {
                  range "1..65535" {
                    description
                      "Autonomous system number";
                  }
                }
                description
                  "Enhanced Interior Gateway Routing Protocol (EIGRP)";
              }
              leaf route-policy {
                type xr:Route-policy-name;
                description
                  "Route policy reference";
              }
            }
            list isis {
              key "instance-name";
              description
                "ISO IS-IS";
              leaf instance-name {
                type xr:Cisco-ios-xr-string {
                  length "1..32" {
                    description
                      "IS-IS instance name";
                  }
                }
                description
                  "ISO IS-IS";
              }
              leaf route-policy {
                type xr:Route-policy-name;
                description
                  "Route policy reference";
              }
              leaf level {
                type enumeration {
                  enum level-1 {
                    value 1;
                    description
                      "IS-IS level-1 routes only";
                  }
                  enum level-2 {
                    value 2;
                    description
                      "IS-IS level-2 routes only";
                  }
                  enum level-1-2 {
                    value 3;
                    description
                      "IS-IS level-1 and level-2 routes";
                  }
                }
                description
                  "configure this node";
              }
            }
            container bgp {
              description
                "Border Gateway Protocol (BGP)";
              list as {
                key "as-number";
                description
                  "bgp as-number";
                leaf as-number {
                  type xr:Bgp-as-number;
                  description
                    "bgp as-number";
                }
                leaf route-policy {
                  type xr:Route-policy-name;
                  description
                    "Route policy reference";
                }
                leaf bgp-routes-only {
                  type enumeration {
                    enum internal {
                      value 512;
                      description
                        "BGP internal routes only";
                    }
                    enum external {
                      value 1024;
                      description
                        "BGP external routes only";
                    }
                    enum local {
                      value 2048;
                      description
                        "BGP local routes only";
                    }
                  }
                  description
                    "configure this node";
                }
              }
            }
          }
          container interfaces {
            description
              "Enter the RIP interface configuration submode";
            list interface {
              key "interface-name";
              description
                "Enter the RIP interface configuration submode";
              leaf interface-name {
                type xr:Interface-name;
                description
                  "Enter the RIP interface configuration submode";
              }
              container metric-zero-accept {
                presence "Indicates a metric-zero-accept node is configured.";
                description
                  "Accept rip update with metric 0";
              }
              container split-horizon {
                description
                  "Disable split horizon";
                container disable {
                  presence "Indicates a disable node is configured.";
                  description
                    "Disable split horzon";
                }
              }
              container poison-reverse {
                presence "Indicates a poison-reverse node is configured.";
                description
                  "Enable poison reverse";
              }
              container passive-interface {
                presence "Indicates a passive-interface node is configured.";
                description
                  "Suppress routing updates on this interface";
              }
              container route-policy {
                description
                  "Apply route policy to routing updates";
                leaf in {
                  type xr:Route-policy-name;
                  description
                    "Apply route policy to inbound routing updates";
                }
                leaf out {
                  type xr:Route-policy-name;
                  description
                    "Apply route policy to outbound routing updates";
                }
              }
            }
          }
        }
      }
    }
  }
}
