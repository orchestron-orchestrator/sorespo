module Cisco-IOS-XR-um-filesystem-inventory-cfg {

  /*** NAMESPACE / PREFIX DEFINITION ***/

  namespace "http://cisco.com/ns/yang/Cisco-IOS-XR-um-filesystem-inventory-cfg";
  prefix um-filesystem-inventory-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR filesystem-inventory package configuration.

     This YANG module augments the
     modules with configuration data.

     Copyright (c) 2021-2025 by Cisco Systems, Inc., and/or its affiliates.
     All rights reserved.";

  revision 2021-11-15 {
    description
      "Initial release";
    semver:module-version "1.0.0";
  }


  container filesystem-inventory {
    presence "Indicates a filesystem-inventory node is configured.";
    description
      "filesystem inventory configuration commands";
    leaf snapshot-interval {
      type uint32 {
        range "1..720" {
          description
            "Snapshot Time interval in 1 hour blocks(e.g, 2 is 120 minutes)";
        }
      }
      description
        "Time interval for generating snapshot";
    }
    container snapshot-type {
      description
        "Type of snapshot to be taken at periodic intervals. Default is incremental";
      container full {
        must 'not(../incremental)';
        presence "Indicates a full node is configured.";
        description
          "Full snapshot generation at periodic intervals";
      }
      container incremental {
        must 'not(../full)';
        presence "Indicates a incremental node is configured.";
        description
          "Incremental snapshot generation at periodic intervals";
      }
    }
    container on-demand {
      description
        "Set of directories to generate on-demand snapshot";
      container dir-sets {
        description
          "Directory set number for on demand";
        list dir-set {
          key "dir-set-number";
          description
            "Directory set number for on demand";
          leaf dir-set-number {
            type uint32 {
              range "1..5" {
                description
                  "Dir set id";
              }
            }
            description
              "Directory set number for on demand";
          }
          leaf value {
            type string {
              length "1..800" {
                description
                  "Space separated directory set(enclosed in quotes)";
              }
            }
            mandatory true;
            description
              "List of directories to generate on-demand snapshot for";
          }
        }
      }
    }
    leaf skip-list {
      type string {
        length "1..800" {
          description
            "List of directories to be skipped. Directory names should be space separated and enclosed in quotes";
        }
      }
      description
        "List of directories to be skipped while generating snapshot. Directory names should be space separated and enclosed in quotes";
    }
    leaf skip-files {
      type string {
        length "1..800" {
          description
            "List of files to be skipped. File names should be space separated and enclosed in quotes";
        }
      }
      description
        "List of files to be skipped while generating snapshot. File names should be space separated and enclosed in quotes";
    }
  }
}
