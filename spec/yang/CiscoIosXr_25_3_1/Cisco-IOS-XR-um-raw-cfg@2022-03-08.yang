module Cisco-IOS-XR-um-raw-cfg {

  /*** NAMESPACE / PREFIX DEFINITION ***/

  namespace "http://cisco.com/ns/yang/Cisco-IOS-XR-um-raw-cfg";
  prefix um-raw-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR raw package configuration.

     This YANG module augments the
     modules with configuration data.

     Copyright (c) 2020-2025 by Cisco Systems, Inc., and/or its affiliates.
     All rights reserved.";

  revision 2022-03-08 {
    description
      "Removed Cisco-IOS-XR-types import";
    semver:module-version "1.1.0";
  }

  revision "2020-12-16" {
    description
      "Initial release";
    semver:module-version "1.0.0";
  }

  container raw {
    description
      "Global RAW configuration command";
    container debug-file {
      presence "Indicates a debug-file node is configured.";
      description
        "Configure debug file attributes";
      leaf directory {
        type string {
          length "1..800" {
            description
              "Place debug files in this directory";
          }
        }
        mandatory true;
        description
          "Specify RAW debug directory location";
      }
      leaf files {
        type uint32 {
          range "1..18000" {
            description
              "Maximum debug files (default: 256)";
          }
        }
        mandatory true;
        description
          "Set maximum debug files";
      }
      leaf size {
        type uint32 {
          range "1024..4294967295" {
            description
              "Maximum file size in bytes";
          }
        }
        mandatory true;
        description
          "Set maximum file size";
      }
    }
    leaf receive-queue {
      type uint32 {
        range "40..800" {
          description
            "Number of packets in receive queue";
        }
      }
      description
        "RAW receive packet queue size";
    }
    container num-thread {
      presence "Indicates a num-thread node is configured.";
      description
        "Set number of threads (takes effect only on process restart)";
      leaf threads {
        type uint32 {
          range "1..16" {
            description
              "Ingress threads created by RAW (default: 8)";
          }
        }
        mandatory true;
        description
          "Set number of threads (takes effect only on process restart)";
      }
      leaf max-threads {
        type uint32 {
          range "1..16" {
            description
              "max threads in thread pool created by RAW (default: 8)";
          }
        }
        mandatory true;
        description
          "max threads in thread pool created by RAW (default: 8)";
      }
    }
  }
}
