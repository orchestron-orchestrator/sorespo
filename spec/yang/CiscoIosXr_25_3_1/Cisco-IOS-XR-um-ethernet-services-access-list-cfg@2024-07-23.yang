module Cisco-IOS-XR-um-ethernet-services-access-list-cfg {
  namespace "http://cisco.com/ns/yang/Cisco-IOS-XR-um-ethernet-services-access-list-cfg";
  prefix um-es-acl-cfg;

  import cisco-semver {
    prefix semver;
  }
  import ietf-yang-types {
    prefix yang;
  }
  import Cisco-IOS-XR-types {
    prefix xr2;
  }
  import Cisco-IOS-XR-um-access-list-datatypes {
    prefix um-acl-types;
  }

  organization
    "Cisco Systems, Inc.";
  contact
    "
     Cisco Systems, Inc.
     Customer Service

     Postal: 170 W Tasman Drive
     San Jose, CA 95134

     Tel: +1 1800 553-NETS

     E-mail: cs-yang@cisco.com
    ";
  description
    "
     This module contains a collection of IOS-XR YANG model derived from CLI.

     Copyright (c) 2019-2025 by Cisco Systems, Inc., and/or its affiliates.
     All rights reserved.
    ";

  revision 2024-07-23 {
    description
      "Increasing acl name length to 128 characters
       2022-09-19
         Added ethertype leaf
       2022-07-11
         Added missing description statement to nodes";
    semver:module-version "2.1.0";
  }

  revision "2020-12-03" {
    description
      "Limit length of remark string";
    semver:module-version "2.0.0";
  }

  revision "2019-06-10" {
    description
      "Establish semantic version baseline.";
    semver:module-version "1.0.0";
  }

  revision "2019-04-01" {
    description
      "Initial version";
  }

  /*
   * ----------------------------------------------------------------
   *  All comments in this file are only for internal review.
   *  These will be removed before publishing
   * ----------------------------------------------------------------
   */
  /* 
   * These feature names are temporary and are taken from the macro names 
   * as it is (for review with ACL team so that they can know where I took
   * them from).
   * Will change to something more appropriate later.
   *
   * Also, we need to advertise supported features in capability. 
   * For YFW to obtain the feature list, we will add a file containing 
   * supported features (ex. Cisco-ios-xr-ipv4-access-list-cfg.features) and 
   * it will be exported from PD component so that we can manage one single 
   * yang file while managing platform dependencies with .features file 
   * created per platform.
   */

  feature es_acl_supported {
    description
      "Access list for ethernet services";
  }

  feature es_acl_capture_implemented {
    description
      "Capture matched packet";
  }

  feature es_acl_log_option_supported {
    description
      "Log matches against access-list entry";
  }

  grouping source-address {
    description
      "Grouping for source-address";
    leaf mac-address {
      /*
       * Although the format used by CLI is different, we shall use the ietf 
       * mac-address type, per yang authoring guidelines
       * 
       *   CLI : HHHH.HHHH.HHHH
       *   IETF: HH:HH:HH:HH:HH:HH
       */
      type yang:mac-address;
      description
        "48-bit source MAC address";
    }
    leaf mac-address-mask {
      type yang:mac-address;
      description
        "48-bit source wildcard bits";
    }
    container any {
      presence "Any source host";
      description
        "Any host";
    }
    leaf host {
      type yang:mac-address;
      description
        "A single source host";
    }
  }

  grouping destination-address {
    description
      "Grouping for destination-address";
    leaf mac-address {
      /*
       * Although the format used by CLI is different, we shall use the ietf 
       * mac-address type, per yang authoring guidelines
       * 
       *   CLI : HHHH.HHHH.HHHH
       *   IETF: HH:HH:HH:HH:HH:HH
       */
      type yang:mac-address;
      description
        "48-bit destination MAC address";
    }
    leaf mac-address-mask {
      type yang:mac-address;
      description
        "48-bit destination wildcard bits";
    }
    container any {
      presence "Any destination host";
      description
        "Any host";
    }
    leaf host {
      type yang:mac-address;
      description
        "A single destination host";
    }
  }

  grouping match-option-common {
    description
      "Grouping for match-option-common";
    container capture {
      if-feature "es_acl_capture_implemented";
      presence "Capture matched packet";
      description
        "Capture matched packet";
    }
    container log {
      if-feature "es_acl_log_option_supported";
      presence "Log matches against this entry";
      description
        "Log matches against this entry";
    }
  }

  grouping ace-common {
    description
      "Grouping for ace-common";
    container source {
      must '(mac-address and mac-address-mask) or any or host';
      description
        "source address";
      uses source-address;
    }
    container destination {
      must '(mac-address and mac-address-mask) or any or host';
      description
        "destination address";
      uses destination-address;
    }
    leaf vlan {
      type um-acl-types:vlan-id;
      description
        "a vlan id or range of vlan ids";
    }
    leaf inner-vlan {
      type um-acl-types:vlan-id;
      description
        "A vlan id or range of vlan ids of the Inner Header";
    }
    leaf cos {
      type uint8 {
        range "0..7" {
          description
            "CoS value for this entry";
        }
      }
      description
        "Class of Service";
    }
    leaf inner-cos {
      type uint8 {
        range "0..7" {
          description
            "CoS value for the Inner Header";
        }
      }
      description
        "Class of Service of Inner Header";
    }
    container dei {
      presence "Discard Eligibility Indication";
      description
        "Discard Eligibility Indication";
    }
    container inner-dei {
      presence "Discard Eligibility Indication for Inner Header";
      description
        "Discard Eligibility Indication for Inner Header";
    }
  }

  container ethernet-services {
    if-feature "es_acl_supported";
    description
      "Configure ethernet-services access-list";
    /*
     * NOTE: I wanted to define these below under access-list but I would 
     *       then need to add a list node for acl entries. So to keep what  
     *       seems more frequently used be more cli-like, placed these
     *       out of access-list node 
     */
    container access-list-options {
      description
        "Control access lists options";
      container log-update {
        description
          "Control access lists log updates";
        leaf threshold {
          type uint32 {
            range "1..2147483647" {
              description
                "Log update threshold (number of hits)";
            }
          }
          description
            "Set access-list logging threshold";
        }
      }
    }
    container access-lists {
      description
        "Access-lists";
      list access-list {
        key "access-list-name";
        description
          "Access-list configuration";
        leaf access-list-name {
          type string {
            length "1..128";
          }
          description
            "Access list name - maximum  128 characters";
        }
        container sequences {
          description
            "Access list entries";
          list sequence {
            must 'deny or permit or remark';
            key "sequence-number";
            description
              "access list entry";
            leaf sequence-number {
              type uint32 {
                range "1..2147483643";
              }
              description
                "Sequence number for this entry";
            }
            container deny {
              must 'source and destination';
              presence "Grant type Deny";
              description
                "Access list deny";
              uses ace-common;
              uses match-option-common;
            }
            container permit {
              must 'source and destination';
              presence "Grant type Permit";
              description
                "Access list permit";
              uses ace-common;
              uses match-option-common;
            }
            leaf ether-type-number {
               type xr2:Hex-integer-16;
               description "Ethernet type Number in Hex. Any value not in the
                            permissible range will be rejected.";
            }
            leaf remark {
              type string {
                length "0..255";
              }
              description
                "Comment for access list";
            }
          }
        }
      }
    }
  }
}
