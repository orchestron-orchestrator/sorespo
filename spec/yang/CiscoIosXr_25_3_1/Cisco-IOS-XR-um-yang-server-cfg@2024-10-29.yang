module Cisco-IOS-XR-um-yang-server-cfg {

  /*** NAMESPACE / PREFIX DEFINITION ***/

  namespace "http://cisco.com/ns/yang/Cisco-IOS-XR-um-yang-server-cfg";
  prefix um-yang-server-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR yang-server package configuration.

     This YANG module augments the
     modules with configuration data.

     Copyright (c) 2020-2025 by Cisco Systems, Inc., and/or its affiliates.
     All rights reserved.";

  revision "2024-10-29" {
    description
      "Added 'all' and 'UM-preferred-plus' options to 'module-set' and added its default as 'all'";
    semver:module-version "1.1.0";
  }

  revision "2021-04-28" {
    description
      "Initial release";
    semver:module-version "1.0.0";
  }

  container yang-server {
    description
      "yang-server configuration commands";
    leaf module-set {
      type enumeration {
        enum UM-preferred {
          value 1;
          description
            "This set use as many unified native models as applicable (no external models)";
        }
        enum XR-only {
          value 2;
          description
            "This set uses only old native models (no external models)";
        }
        enum UM-preferred-plus {
          value 3;
          description "This set use as many unified native models as applicable plus external models";
        }
        enum all {
          value 4;
          description "This set uses all available models (native/unified/external)";
        }
      }
      default all;
      description
        "Use only the yang modules listed in a module-set.";
    }
  }
}
