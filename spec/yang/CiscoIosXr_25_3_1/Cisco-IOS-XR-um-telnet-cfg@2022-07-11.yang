module Cisco-IOS-XR-um-telnet-cfg {

  /*** NAMESPACE / PREFIX DEFINITION ***/

  namespace "http://cisco.com/ns/yang/Cisco-IOS-XR-um-telnet-cfg";
  prefix um-telnet-cfg;

  /*** LINKAGE (IMPORTS / INCLUDES) ***/

  import Cisco-IOS-XR-types {
    prefix xr;
  }
  import Cisco-IOS-XR-um-line-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR telnet package configuration.

     This YANG module augments the
     modules with configuration data.

     Copyright (c) 2020-2025 by Cisco Systems, Inc., and/or its affiliates.
     All rights reserved.";

  revision 2022-07-11 {
    description
      "Added missing description statement to nodes";
    semver:module-version "1.0.0";
  }

  revision "2020-09-16" {
    description
      "Initial release";
    semver:module-version "1.0.0";
  }

  augment "/a1:line/a1:console" {
    description
      "This augment extends line console nodes
       configuration";
    container telnet {
      description
        "Telnet protocol-specific configuration";
      container transparent {
        presence "Indicates a transparent node is configured.";
        description
          "Send a CR as a CR followed by a NULL instead of a CR followed by a LF";
      }
    }
  }

  augment "/a1:line/a1:default" {
    description
      "This augment extends line default nodes
       configuration";
    container telnet {
      description
        "Telnet protocol-specific configuration";
      container transparent {
        presence "Indicates a transparent node is configured.";
        description
          "Send a CR as a CR followed by a NULL instead of a CR followed by a LF";
      }
    }
  }

  augment "/a1:line/a1:templates/a1:template" {
    description
      "This augment extends line template nodes
       configuration";
    container telnet {
      description
        "Telnet protocol-specific configuration";
      container transparent {
        presence "Indicates a transparent node is configured.";
        description
          "Send a CR as a CR followed by a NULL instead of a CR followed by a LF";
      }
    }
  }

  container telnet {
    description
      "Global Telnet configuration commands";
    container ipv4 {
      description
        "IPv4 configuration";
      container client {
        description
          "Telnet client configuration commands";
        leaf source-interface {
          type xr:Interface-name;
          description
            "Source interface for telnet sessions";
        }
      }
    }
    container ipv6 {
      description
        "IPv6 configuration";
      container client {
        description
          "Telnet client configuration commands";
        leaf source-interface {
          type xr:Interface-name;
          description
            "Source interface for telnet sessions";
        }
      }
    }
    container vrfs {
      description
        "VRF name for telnet server";
      list vrf {
        must 'ipv4/server/max-servers or ipv6/server/max-servers';
        key "vrf-name";
        description
          "Name of VRF";
        leaf vrf-name {
          type union {
            type string {
              pattern 'default' {
                description
                  "Default VRF";
              }
            }
            type xr:Cisco-ios-xr-string {
              length "1..1024" {
                description
                  "Name of VRF";
              }
            }
          }
          description
            "Name of VRF";
        }
        container ipv4 {
          description
            "IPv4 configuration";
          container server {
            description
              "Telnet server configuration commands";
            leaf max-servers {
              type uint32 {
                range "1..100" {
                  description
                    "Set number of allowable telnet sessions";
                }
              }
              description
                "Set number of allowable telnet sessions";
            }
            leaf access-list {
              type xr:Cisco-ios-xr-string {
                length "1..64" {
                  description
                    "Name of access list";
                }
              }
              must '../max-servers';
              description
                "Access list for telnet server";
            }
          }
        }
        container ipv6 {
          description
            "IPv6 configuration";
          container server {
            description
              "Telnet server configuration commands";
            leaf max-servers {
              type uint32 {
                range "1..100" {
                  description
                    "Set number of allowable telnet sessions";
                }
              }
              description
                "Set number of allowable telnet sessions";
            }
            leaf access-list {
              type xr:Cisco-ios-xr-string {
                length "1..64" {
                  description
                    "Name of access list";
                }
              }
              must '../max-servers';
              description
                "Access list for telnet server";
            }
          }
        }
      }
      list vrf-dscp {
        key "vrf-name";
        description
          "Name of VRF";
        leaf vrf-name {
          type union {
            type string {
              pattern 'default' {
                description
                  "Default VRF";
              }
            }
            type xr:Cisco-ios-xr-string {
              length "1..1024" {
                description
                  "Name of VRF";
              }
            }
          }
          description
            "Name of VRF";
        }
        container ipv4 {
          description
            "IPv4 configuration";
          leaf dscp {
            type uint32 {
              range "0..63" {
                description
                  "dscp value";
              }
            }
            mandatory true;
            description
              "dscp";
          }
        }
      }
    }
  }
}
