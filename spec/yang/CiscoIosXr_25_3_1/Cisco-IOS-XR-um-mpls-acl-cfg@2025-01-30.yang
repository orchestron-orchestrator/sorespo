module Cisco-IOS-XR-um-mpls-acl-cfg {

  /*** NAMESPACE / PREFIX DEFINITION ***/

  namespace "http://cisco.com/ns/yang/Cisco-IOS-XR-um-mpls-acl-cfg";
  prefix um-mpls-acl-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco mpls-acl package configuration.
     This YANG module augments and other modules configuration data.
     Copyright (c) 2024-2025 by Cisco Systems, Inc., and/or its affiliates.
     All rights reserved.";

  /*** Internal Version ***/
  /*** Component ***/

  revision 2025-01-30 {
    description
      "Increasing acl name length to 128 characters";
    semver:module-version "1.0.0";
  }

  revision "2024-04-17" {
    description
      "Initial UM2 release";
  }

  /*** Macros ***/

  container mpls {
    description
      "mpls access-list";
    container access-lists {
      description
        "Access-list commands";
      list access-list {
        key "access-list-string";
        description
          "Access-list commands";
        grouping MPLS-VALUES {
          description
            "MPLS Values";
          leaf specifies-packet {
            type enumeration {
              enum deny {
                value 0;
                description
                  "Specifies packets to reject";
              }
              enum permit {
                value 1;
                description
                  "Specifies packets to forward";
              }
            }
            description
              "Packet";
          }
          container label-one {
            description
              "the mpls label1 value(s)";
            choice LABEL-ONE {
              description
                "the mpls label1 value(s)";
              case EQ {
                container eq {
                  presence "Match only packets with a given Label1  value";
                  description
                    "Match only packets with a given Label1  value";
                  leaf label-one-value {
                    type uint32 {
                      range "0..1048575" {
                        description
                          "label1 value";
                      }
                    }
                    mandatory true;
                    description
                      "label1 value";
                  }
                }
              }
              case LABEL-ONE-RANGE {
                container label-one-range {
                  presence "Match only packets with Label1 values from a given range";
                  description
                    "Match only packets with Label1 values from a given range";
                  leaf label-one-value-one {
                    type uint32 {
                      range "0..1048575" {
                        description
                          "label1 value1";
                      }
                    }
                    mandatory true;
                    description
                      "label1 value1";
                  }
                  leaf label-one-value-two {
                    type uint32 {
                      range "0..1048575" {
                        description
                          "label1 value2";
                      }
                    }
                    mandatory true;
                    description
                      "label1 value2";
                  }
                }
              }
            }
          }
          container label-two {
            description
              "the mpls label2 value(s)";
            choice LABEL-TWO {
              description
                "the mpls label2 value(s)";
              case EQ {
                container eq {
                  presence "Match only packets with a given Label2  value";
                  description
                    "Match only packets with a given Label2  value";
                  leaf label-two-value {
                    type uint32 {
                      range "0..1048575" {
                        description
                          "label2 value";
                      }
                    }
                    mandatory true;
                    description
                      "label2 value";
                  }
                }
              }
              case LABEL-TWO-RANGE {
                container label-two-range {
                  presence "Match only packets with Label1 values from a given range";
                  description
                    "Match only packets with Label1 values from a given range";
                  leaf label-two-value-one {
                    type uint32 {
                      range "0..1048575" {
                        description
                          "label2 value1";
                      }
                    }
                    mandatory true;
                    description
                      "label2 value1";
                  }
                  leaf label-two-value-two {
                    type uint32 {
                      range "0..1048575" {
                        description
                          "label2 value2";
                      }
                    }
                    mandatory true;
                    description
                      "label2 value2";
                  }
                }
              }
            }
          }
          container label-three {
            description
              "the mpls label3 value(s)";
            choice LABEL-THREE {
              description
                "the mpls label3 value(s)";
              case EQ {
                container eq {
                  presence "Match only packets with a given Label3  value";
                  description
                    "Match only packets with a given Label3  value";
                  leaf label-three-value {
                    type uint32 {
                      range "0..1048575" {
                        description
                          "label3 value";
                      }
                    }
                    mandatory true;
                    description
                      "label3 value";
                  }
                }
              }
              case LABEL-THREE-RANGE {
                container label-three-range {
                  presence "Match only packets with Label1 values from a given range";
                  description
                    "Match only packets with Label1 values from a given range";
                  leaf label-three-value-one {
                    type uint32 {
                      range "0..1048575" {
                        description
                          "label3 value1";
                      }
                    }
                    mandatory true;
                    description
                      "label3 value1";
                  }
                  leaf label-three-value-two {
                    type uint32 {
                      range "0..1048575" {
                        description
                          "label3 value2";
                      }
                    }
                    mandatory true;
                    description
                      "label3 value2";
                  }
                }
              }
            }
          }
          leaf exp-one {
            type uint32 {
              range "0..7" {
                description
                  "exp1 values range 0-7";
              }
            }
            description
              "the mpls exp1 value";
          }
          leaf exp-two {
            type uint32 {
              range "0..7" {
                description
                  "exp2 values range 0-7";
              }
            }
            description
              "the mpls exp2 value";
          }
          leaf exp-three {
            type uint32 {
              range "0..7" {
                description
                  "exp3 values range 0-7";
              }
            }
            description
              "the mpls exp3 value";
          }
        }

        leaf access-list-string {
          type xr:Cisco-ios-xr-string {
            length "1..128" {
              description
                "Access list name - maximum 128 characters";
            }
            pattern '[a-z0-9A-Z][-_.:a-z0-9A-Z]*';
          }
          description
            "Access list name - maximum 128 characters";
        }
        container sequence-numbers {
          description
            "Sequence number";
          list sequence-number {
            must 'specifies-packet and (exp-one or label-one/eq or label-one/label-one-range or exp-two or label-two/eq or label-two/label-two-range or exp-three or label-three/eq or label-three/label-three-range)';
            key "seq-number";
            description
              "Sequence number";
            leaf seq-number {
              type uint32 {
                range "1..2147483646" {
                  description
                    "Sequence number";
                }
              }
              description
                "Sequence number";
            }
            uses MPLS-VALUES;
          }
        }
        container default-sequence {
          must 'specifies-packet and (exp-one or label-one/eq or label-one/label-one-range or exp-two or label-two/eq or label-two/label-two-range or exp-three or label-three/eq or label-three/label-three-range)';
          presence "Default sequence";
          description
            "Default sequence";
          uses MPLS-VALUES;
        }
      }
    }
  }
}
