module Cisco-IOS-XR-um-crypto-cfg {

  /*** NAMESPACE / PREFIX DEFINITION ***/

  namespace "http://cisco.com/ns/yang/Cisco-IOS-XR-um-crypto-cfg";
  prefix um-crypto-cfg;

  /*** LINKAGE (IMPORTS / INCLUDES) ***/

  import Cisco-IOS-XR-types {
    prefix xr;
  }
  import ietf-inet-types {
    prefix inet;
  }
  import Cisco-IOS-XR-um-snmp-server-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto package configuration.

     This YANG module augments the
     modules with configuration data.

     Copyright (c) 2022-2025 by Cisco Systems, Inc., and/or its affiliates.
     All rights reserved.";

  revision 2024-11-15 {                                                        
    description
      "Adding UM support for local enrollment method
       2024-10-10
         Adding UM support of client authentication and SSL profiles, removed credential and certificate nodes
       2024-08-26
         Adding new configs for certificate enrollment using EST protocol. Adding UM support for extended-key-usage config
       2024-02-07
         Fixed missing leafs from trustpoint container and corrected key-usage container for ca-certificates
       2024-02-06
         Added support to configure Subject Alternative Name under trustpoint.
       2023-04-11
         Changed top level schema path
       2022-11-25
         Added skip-challenge-password and message-digest support under trustpoint
       2022-07-11
         Added missing description statement to nodes
       2022-05-30
         Added openssh, rsa1024, fqdn-check and crl support under ca
       2022-05-25
         Added presence statement for node serial-number
       2022-04-05
         Added generate-keys in key/generate/rsa/label
       2022-03-21
         Added auto-enroll support";
    semver:module-version "3.0.0";
  }

  revision "2021-06-17" {
    description
      "Fixed missing leaf subject-name and combined subject-name ca-cartificate for ca-certificate
      2021-04-22
          Initial release";
    semver:module-version "2.0.0";
  }

  revision "2021-04-02" {
    description
      "Initial release";
    semver:module-version "1.0.0";
  }

  augment "/a1:snmp-server/a1:traps" {
    description
      "This augment extends snmp-server traps nodes
       configuration";
    container pki {
      presence "Indicates a pki node is configured.";
      description
        "Enable SNMP traps for certificate expiry";
    }
  }

  container ssl {
    description
      "Configure TLS/SSL handshake related parameters";
    container profiles {
      description
        "Template that will be pinned to applications";
      list profile {
        key "profile-name";
        description
          "Template that will be pinned to applications";
        leaf profile-name {
          type xr:Cisco-ios-xr-string {
            length "1..800" {
              description
                "Profile Name";
            }
          }
          description
            "Template that will be pinned to applications";
        }
        leaf certificate {
          type xr:Cisco-ios-xr-string {
            length "1..800" {
              description
                "Trustpoint name whose leaf(router) certificate will be used";
            }
          }
          description
            "Router certificate to be used in mTLS session, only during enrollment or bootstrap phase.";
        }
      }
    }
  }
  container client-authentication {
    description
      "Configure various authentication methods for authenticating the router(client)";
    container profiles {
      description
        "Template that will be pinned to applications";
      list profile {
        key "profile-name";
        description
          "Template that will be pinned to applications";
        leaf profile-name {
          type xr:Cisco-ios-xr-string {
            length "1..800" {
              description
                "Profile Name";
            }
          }
          description
            "Template that will be pinned to applications";
        }
        leaf username {
          type xr:Cisco-ios-xr-string {
            length "1..800" {
              description
                "Username";
            }
          }
          must '../password';
          description
            "Configure Username";
        }
        container password {
          must '../username';
          description
            "Challenge password to authenticate client(router)";
          leaf six {
            type xr:Type6-password;
            description
              "Specifies that an clear text key will follow";
          }
        }
      }
    }
  }
  container crypto {
    description
      "Global Crypto configuration command";
    container ca {
      description
        "Certification authority";
      container trustpoint {
        description
          "  Config a trustpoint";
        container system-trustpoint {
          presence "Indicates a system-trustpoint node is configured.";
          description
            "Default System trustpoint";
          leaf description {
            type string {
              length "1..80" {
                description
                  "Description for this trustpoint";
              }
            }
            description
              "Description for the trustpoint";
          }
          container enrollment {
            description
              "Enrollment parameters";
            container retry {
              description
                "Polling parameters";
              leaf count {
                type uint32 {
                  range "1..100" {
                    description
                      "Number of times to poll a CA for a certificate";
                  }
                }
                description
                  "How many times to poll CA for our certificate";
              }
              leaf period {
                type uint32 {
                  range "1..60" {
                    description
                      "Period in minutes between attempts to contact a CA";
                  }
                }
                description
                  "How long to wait between requests to CA for our certificate";
              }
            }
            leaf url {
              type string {
                length "1..800" {
                  description
                    "URL";
                }
              }
              description
                "CA server enrollment URL";
            }
            container terminal {
              must 'not(../self or ../local)';
              presence "Indicates a terminal node is configured.";
              description
                "Enroll via the terminal (cut-and-paste)";
            }
            container self {
              must 'not(../terminal or ../local)';
              presence "Indicates a self node is configured.";
              description
                "Enroll self create self signed CA cert and the router cert signed using the same";
            }
            container local {
                must 'not(../terminal or ../self)';
                presence "Indicates a local node is configured.";
                description
                    "Enroll via file present on local filesystem";
            }
          }
          container sftp-password {
            description
              "Secure FTP password";
            leaf password {
              type xr:Proprietary-password;
              description
                "Enter password in encrypted form";
            }
          }
          leaf sftp-username {
            type xr:Cisco-ios-xr-string {
              length "1..800" {
                description
                  "username";
              }
            }
            description
              "Secure FTP username";
          }
          leaf auto-enroll {
            type uint32 {
              range "1..99" {
                description
                  "auto-enroll percentage";
              }
            }
            description
              "Set auto-enroll percentage at which renewal will be triggered";
          }
          container renewal-message-type {
            description
              "Set renewal message type for SCEP auto-renewal feature";
            container pkcsreq {
              must 'not(../renewalreq)';
              presence "Indicates a pkcsreq node is configured.";
              description
                "Message type PKCSReq(Default)";
            }
            container renewalreq {
              must 'not(../pkcsreq)';
              presence "Indicates a renewalreq node is configured.";
              description
                "Message type RenewalReq";
            }
          }
          container skip-challenge-password {
            presence "Indicates a skip-challenge-password node is configured.";
            description
              "Skip challenge password attribute for manual enrollment request";
          }
          leaf rsakeypair {
            type xr:Cisco-ios-xr-string {
              length "1..800" {
                description
                  "Key pair label";
              }
            }
            description
              "RSA key pair";
          }
          container ca-keypair {
            description
              "Self enrollment, key pair ca cert";
            leaf rsa {
              type xr:Cisco-ios-xr-string {
                length "1..800" {
                  description
                    "rsa key pair label";
                }
              }
              must "not(../ecdsanistp256 or ../ecdsanistp384
                    or ../ecdsanistp521 or ../dsa
                    or ../ed25519)";
              description
                "Self enrollment, rsa key pair";
            }
            leaf ecdsanistp256 {
              type xr:Cisco-ios-xr-string {
                length "1..800" {
                  description
                    "Ecdsa key pair label";
                }
              }
              must "not(../rsa or ../ecdsanistp384
                    or ../ecdsanistp521 or ../dsa
                    or ../ed25519)";
              description
                "Self enrollment, ecdsa key pair";
            }
            leaf ecdsanistp384 {
              type xr:Cisco-ios-xr-string {
                length "1..800" {
                  description
                    "Ecdsa key pair label";
                }
              }
              must "not(../rsa or ../ecdsanistp256
                    or ../ecdsanistp521 or ../dsa
                    or ../ed25519)";
              description
                "Self enrollment, ecdsa key pair";
            }
            leaf ecdsanistp521 {
              type xr:Cisco-ios-xr-string {
                length "1..800" {
                  description
                    "Ecdsa key pair label";
                }
              }
              must "not(../rsa or ../ecdsanistp256
                    or ../ecdsanistp384 or ../dsa
                    or ../ed25519)";
              description
                "Self enrollment, ecdsa key pair";
            }
            leaf dsa {
              type xr:Cisco-ios-xr-string {
                length "1..800" {
                  description
                    "Dsa key pair label";
                }
              }
              must "not(../rsa or ../ecdsanistp256
                    or ../ecdsanistp384 or ../ecdsanistp521
                    or ../ed25519)";
              description
                "Self enrollment, dsa key pair label";
            }
            leaf ed25519 {
              type xr:Cisco-ios-xr-string {
                length "1..800" {
                  description
                    "ed25519 key pair label";
                }
              }
              must "not(../rsa or ../ecdsanistp256
                    or ../ecdsanistp384 or ../ecdsanistp521
                    or ../dsa)";
              description
                "ed25519 key pair label";
            }
          }
          container keypair {
            description
              "key pair for router/leaf cert";
            leaf rsa {
              type xr:Cisco-ios-xr-string {
                length "1..800" {
                  description
                    "rsa key pair label";
                }
              }
              must "not(../ecdsanistp256 or ../ecdsanistp384
                    or ../ecdsanistp521 or ../dsa
                    or ../ed25519)";
              description
                "Rsa key pair";
            }
            leaf ecdsanistp256 {
              type xr:Cisco-ios-xr-string {
                length "1..800" {
                  description
                    "Ecdsa key pair label";
                }
              }
              must "not(../rsa or ../ecdsanistp384
                    or ../ecdsanistp521 or ../dsa
                    or ../ed25519)";
              description
                "Ecdsa key pair";
            }
            leaf ecdsanistp384 {
              type xr:Cisco-ios-xr-string {
                length "1..800" {
                  description
                    "Ecdsa key pair label";
                }
              }
              must "not(../rsa or ../ecdsanistp256
                    or ../ecdsanistp521 or ../dsa
                    or ../ed25519)";
              description
                "Self enrollment, ecdsa key pair";
            }
            leaf ecdsanistp521 {
              type xr:Cisco-ios-xr-string {
                length "1..800" {
                  description
                    "Ecdsa key pair label";
                }
              }
              must "not(../rsa or ../ecdsanistp256
                    or ../ecdsanistp384 or ../dsa
                    or ../ed25519)";
              description
                "Self enrollment, ecdsa key pair";
            }
            leaf dsa {
              type xr:Cisco-ios-xr-string {
                length "1..800" {
                  description
                    "Dsa key pair label";
                }
              }
              must "not(../rsa or ../ecdsanistp256
                    or ../ecdsanistp384 or ../ecdsanistp521
                    or ../ed25519)";
              description
                "Dsa key pair label";
            }
            leaf ed25519 {
              type xr:Cisco-ios-xr-string {
                length "1..800" {
                  description
                    "ed25519 key pair label";
                }
              }
              must "not(../rsa or ../ecdsanistp256
                    or ../ecdsanistp384 or ../ecdsanistp521
                    or ../dsa)";
              description
                "ed25519 key pair label";
            }
          }
          container crl {
            description
              "CRL options";
            container optional {
              presence "Indicates a optional node is configured.";
              description
                "CRL verification as optional";
            }
          }
          container query {
            description
              "Query parameters";
            leaf url {
              type string {
                length "1..800" {
                  description
                    "URL";
                }
              }
              description
                "CA server query URL";
            }
          }
          container ip-address {
            description
              "include ip address";
            leaf ipv4-address {
              type inet:ipv4-address-no-zone;
              must 'not(../none)';
              description
                "ip address";
            }
            container none {
              must 'not(../ipv4-address)';
              presence "Indicates a none node is configured.";
              description
                "do not include ip address";
            }
          }
          leaf subject-name {
            type string {
              length "1..800" {
                description
                  "Subject Name";
              }
            }
            description
              "Subject Name";
          }
          leaf subject-alternative-name {
            type string {
              length "1..800" {
                description
                  "Subject Alternative Name to be included in CSR request, example: DNS:test.example.com,IP:192.168.1.1,email:info@example.com";
              }
            }
            description
              "Include Subject Alternative Name(SAN) in CSR request";
          }
          leaf subject-name-ca-certificate {
            type string {
              length "1..800" {
                description
                  "Subject Name";
              }
            }
            description
              "Ca Certificate subject name for self enrollment";
          }
          container serial-number {
            presence "Indicates a serial-number node is configured.";
            description
              "include serial number";
            container none {
              presence "Indicates a none node is configured.";
              description
                "do not include serial number";
            }
          }
          leaf vrf {
            type xr:Cisco-ios-xr-string {
              length "1..32" {
                description
                  "VRF name (max:32 chars)";
              }
            }
            description
              "Source interface VRF ";
          }
          container lifetime {
            description
              "lifetime for certificate valid for self enrollment";
            leaf ca-certificate {
              type uint32 {
                range "30..5475" {
                  description
                    "Validity of CA certficate in days";
                }
              }
              description
                "lifetime for ca-certificate valid for self enrollemnt";
            }
            leaf certificate {
              type uint32 {
                range "30..5474" {
                  description
                    "Validity of certficate in days";
                }
              }
              description
                "lifetime for ertificate valid for self enrollemnt";
            }
          }
          container key-usage {
            description
              "key usage field for the certificate self enrollment";
            container ca-certificate {
              must 'digitalsignature or keycertsign or crlsign or nonrepudiation';
              presence "Indicates a ca-certificate node is configured.";
              description
                "key usage field for the CA certificate";
              leaf digitalsignature {
                type boolean;
                description
                  "Key usage field as digital-signature for CA certificate";
              }
              leaf keycertsign {
                type boolean;
                description
                  "Key usage field as key-certsign for CA certificate";
              }
              leaf crlsign {
                type boolean;
                description
                  "Key usage field as crl-sign for CA certificate";
              }
              leaf nonrepudiation {
                type boolean;
                description
                  "Key usage field as non-repudiation for CA certificate";
              }
            }
            container certificate {
              must 'digitalsignature or keyagreement or nonrepudiation or dataencipherment or keyencipherment';
              presence "Indicates a certificate node is configured.";
              description
                "key usage field for the leaf certificates";
              container digitalsignature {
                presence "Indicates a digitalsignature node is configured.";
                description
                  "Key usage field as digital-signature for certificate";
              }
              container keyagreement {
                presence "Indicates a keyagreement node is configured.";
                description
                  "Key usage field as key-agreement for certificate";
              }
              container nonrepudiation {
                presence "Indicates a nonrepudiation node is configured.";
                description
                  "Key usage field as non-repudiation for certificate";
              }
              container dataencipherment {
                presence "Indicates a dataencipherment node is configured.";
                description
                  "Key usage field as data-encipherment for certificate";
              }
              container keyencipherment {
                presence "Indicates a keyencipherment node is configured.";
                description
                  "Key usage field as key-encipherment for certificate";
              }
            }
          }
          leaf message-digest {
            type enumeration {
              enum md5 {
                value 1;
                description
                  "md5 algorithm for message digest.(1)";
              }
              enum sha1 {
                value 2;
                description
                  "sha1 algorithm for message digest.(2)";
              }
              enum sha256 {
                value 3;
                description
                  "sha256 algorithm for message digest.(3)";
              }
              enum sha384 {
                value 4;
                description
                  "sha384 algorithm for message digest.(4)";
              }
              enum sha512 {
                value 5;
                description
                  "sha512 algorithm for message digest.(5)";
              }
            }
            description
              "Certificate message digesti self enrollment";
          }
        }
        container trustpoints {
          description
            "Config a trustpoint";
          list trustpoint {
            key "trustpoint-name";
            description
              "Trustpoint";
            leaf trustpoint-name {
              type xr:Cisco-ios-xr-string {
                length "1..1024" {
                  description
                    "Trustpoint Name";
                }
              }
              description
                "Trustpoint Name";
            }
            leaf description {
              type string {
                length "1..80" {
                  description
                    "Description for this trustpoint";
                }
              }
              description
                "Description for the trustpoint";
            }
            container enrollment {
              description
                "Enrollment parameters";
              container retry {
                description
                  "Polling parameters";
                leaf count {
                  type uint32 {
                    range "1..100" {
                      description
                        "Number of times to poll a CA for a certificate";
                    }
                  }
                  description
                    "How many times to poll CA for our certificate";
                }
                leaf period {
                  type uint32 {
                    range "1..60" {
                      description
                        "Period in minutes between attempts to contact a CA";
                    }
                  }
                  description
                    "How long to wait between requests to CA for our certificate";
                }
              }
              leaf url {
                type string {
                  length "1..800" {
                    description
                      "URL";
                  }
                }
                description
                  "CA server enrollment URL";
              }
              container terminal {
                must 'not(../local)';
                presence "Indicates a terminal node is configured.";
                description
                  "Enroll via the terminal (cut-and-paste)";
              }
              container local {
                  must 'not(../terminal)';
                  presence "Indicates a local node is configured.";
                  description
                      "Enroll via file present on local filesystem";
              }
              leaf authentication-profile {
                type xr:Cisco-ios-xr-string {
                  length "1..800" {
                    description
                      "Profile Name";
                  }
                }
                description
                  "Authentication profile used during certificate enrollment";
              }
            }
            container re-enrollment {
              description
                "Re-enrollment parameters";
              leaf authentication-profile {
                type xr:Cisco-ios-xr-string {
                  length "1..800" {
                    description
                      "Profile Name";
                  }
                }
                description
                  "Authentication profile used during certificate re-enrollment";
              }
            }
            leaf ssl-profile {
              type xr:Cisco-ios-xr-string {
                length "1..800" {
                  description
                    "Profile Name";
                }
              }
              description
                "SSL profile parameters used during TLS/mTLS handshake";
            }
            container sftp-password {
              description
                "Secure FTP password";
              leaf password {
                type xr:Proprietary-password;
                description
                  "Enter password in encrypted form";
              }
            }
            leaf sftp-username {
              type xr:Cisco-ios-xr-string {
                length "1..800" {
                  description
                    "username";
                }
              }
              description
                "Secure FTP username";
            }
            leaf auto-enroll {
              type uint32 {
                range "1..99" {
                  description
                    "auto-enroll percentage";
                }
              }
              description
                "Set auto-enroll percentage at which renewal will be triggered";
            }
            container renewal-message-type {
              description
                "Set renewal message type for SCEP auto-renewal feature";
              container pkcsreq {
                must 'not(../renewalreq)';
                presence "Indicates a pkcsreq node is configured.";
                description
                  "Message type PKCSReq(Default)";
              }
              container renewalreq {
                must 'not(../pkcsreq)';
                presence "Indicates a renewalreq node is configured.";
                description
                  "Message type RenewalReq";
              }
            }
            container skip-challenge-password {
              presence "Indicates a skip-challenge-password node is configured.";
              description
                "Skip challenge password attribute for manual enrollment request";
            }
            leaf rsakeypair {
              type xr:Cisco-ios-xr-string {
                length "1..800" {
                  description
                    "Key pair label";
                }
              }
              description
                "RSA key pair";
            }
            container crl {
              description
                "CRL options";
              container optional {
                presence "Indicates a optional node is configured.";
                description
                  "CRL verification as optional";
              }
            }
            container query {
              description
                "Query parameters";
              leaf url {
                type string {
                  length "1..800" {
                    description
                      "URL";
                  }
                }
                description
                  "CA server query URL";
              }
            }
            container ip-address {
              description
                "include ip address";
              leaf ipv4-address {
                type inet:ipv4-address-no-zone;
                must 'not(../none)';
                description
                  "ip address";
              }
              container none {
                must 'not(../ipv4-address)';
                presence "Indicates a none node is configured.";
                description
                  "do not include ip address";
              }
            }
            leaf subject-name {
              type string {
                length "1..800" {
                  description
                    "Subject Name";
                }
              }
              description
                "Subject Name";
            }
            leaf subject-alternative-name {
              type string {
                length "1..800" {
                  description
                    "Subject Alternative Name to be included in CSR request, example: DNS:test.example.com,IP:192.168.1.1,email:info@example.com";
                }
              }
              description
                "Include Subject Alternative Name(SAN) in CSR request";
            }
            container serial-number {
              presence "Indicates a serial-number node is configured.";
              description
                "include serial number";
              container none {
                presence "Indicates a none node is configured.";
                description
                  "do not include serial number";
              }
            }
            leaf vrf {
              type xr:Cisco-ios-xr-string {
                length "1..32" {
                  description
                    "VRF name (max:32 chars)";
                }
              }
              description
                "Source interface VRF ";
            }
            leaf message-digest {
              type enumeration {
                enum md5 {
                  value 1;
                  description
                    "md5 algorithm for message digest.(1)";
                }
                enum sha1 {
                  value 2;
                  description
                    "sha1 algorithm for message digest.(2)";
                }
                enum sha256 {
                  value 3;
                  description
                    "sha256 algorithm for message digest.(3)";
                }
                enum sha384 {
                  value 4;
                  description
                    "sha384 algorithm for message digest.(4)";
                }
                enum sha512 {
                  value 5;
                  description
                    "sha512 algorithm for message digest.(5)";
                }
              }
              description
                "Certificate message digesti self enrollment";
            }
            container extended-key-usage {
              description
                "Extended Key Usage field for the certificate";
              container match {
                must 'server-auth or client-auth';
                presence "Indicates a match node is configured.";
                description
                  "Validates a peer certificate only if specified attributes are present.";
                leaf server-auth {
                  type boolean;
                  description
                    "Indicates that the certificate can be used to authenticate a web server to clients in SSL/TLS sessions.";
                }
                leaf client-auth {
                  type boolean;
                  description
                    "Indicates that the certificate can be used to authenticate a client to servers in SSL/TLS sessions.";
                }
              }
            }
            container method {
              description
                "Indicates mode of enrollment for leaf certificate";
              container est {
                presence "Indicates a est node is configured.";
                description
                  "EST enrollment method";
              }
            }
          }
        }
      }
      container openssh {
        description
          "Openssh certificates";
        container trustpoints {
          description
            "  Config a trustpoint";
          list trustpoint {
            key "trustpoint-name";
            description
              "  Config a trustpoint";
            leaf trustpoint-name {
              type xr:Cisco-ios-xr-string {
                length "1..128" {
                  description
                    "Trustpoint Name";
                }
              }
              description
                "  Config a trustpoint";
            }
            leaf rsakeypair {
              type xr:Cisco-ios-xr-string {
                length "1..800" {
                  description
                    "Key pair label";
                }
              }
              description
                "RSA key pair";
            }
          }
        }
      }
      leaf http-proxy {
        type xr:Cisco-ios-xr-string {
          length "1..64" {
            description
              "Http proxy server";
          }
        }
        must '../port';
        description
          "Specify proxy server for http request";
      }
      leaf port {
        type uint32 {
          range "1..65535" {
            description
              "http proxy server port number";
          }
        }
        must '../http-proxy';
        description
          "proxy server port number";
      }
      container source-interface {
        description
          "Cisco source-interface name";
        leaf ipv4 {
          type xr:Interface-name;
          must 'not(../ipv6)';
          description
            "Choose Ipv4 address from interface";
        }
        leaf ipv6 {
          type xr:Interface-name;
          must 'not(../ipv4)';
          description
            "Choose Ipv6 address from interface";
        }
      }
      container rsa {
        description
          "allow/disable RSA key bits modulus size";
        container one-thousand-twenty-four {
          description
            "Disable 1024 key bits modulus size";
          container disable {
            presence "Indicates a disable node is configured.";
            description
              "Disable Trustpool certificates with RSA modulus 1024";
          }
        }
      }
      container fqdn-check {
        description
          " If the CN name contains the IP address instead of a FQDN, disable rejecting the TLS connection, to allow the connection to established (this is less secure).";
        container ip-address {
          description
            "allow ip-address in the Common Name";
          container allow {
            presence "Indicates a allow node is configured.";
            description
              "allow TLS connection when CN contains IP address ";
          }
        }
      }
      container trustpool {
        description
          "  Config a trustpool";
        container policy {
          presence "Indicates a policy node is configured.";
          description
            " Config a trustpool policy";
          leaf description {
            type string {
              length "1..80" {
                description
                  "Description for this trustpoint";
              }
            }
            description
              "Description for the trustpoint";
          }
          container cabundle {
            description
              "certificate bundle";
            leaf url {
              type string {
                length "1..800" {
                  description
                    "URL";
                }
              }
              description
                "CA bundle download parameters";
            }
          }
          container crl {
            description
              "CRL options";
            container optional {
              presence "Indicates a optional node is configured.";
              description
                "CRL verification as optional";
            }
          }
          leaf vrf {
            type string {
              length "1..32" {
                description
                  "Enter the vrf name";
              }
            }
            description
              "Cisco vrf name";
          }
        }
      }
      container crl {
        description
          "Certification revocation list";
        leaf curl-timeout {
          type uint32 {
            range "5..50" {
              description
                "timeout value in seconds for a CURL request to timeout";
            }
          }
          description
            "timeout value in seconds for a CURL request to timeout";
        }
      }
    }
    container fips-mode {
      presence "Indicates a fips-mode node is configured.";
      description
        "Enable FIPS mode";
    }
    container key {
      description
        "Keys to be generated";
      container generate {
        description
          "Generate new keys";
        container rsa {
          description
            "Generate RSA key";
          list label {
            must 'general-keys or usage-keys';
            key "label-name";
            description
              "Label name";
            leaf label-name {
              type union {
                type string {
                  pattern 'the_default' {
                    description
                      "Default label name";
                  }
                }
                type xr:Cisco-ios-xr-string {
                  length "1..800" {
                    description
                      "Label name";
                  }
                }
              }
              description
                "Label name";
            }
            leaf key-module-size {
              type uint32 {
                range "512..4096" {
                  description
                    "Size of key modulus";
                }
              }
              mandatory true;
              description
                "Size of key modulus";
            }
            container general-keys {
              must 'not(../usage-keys)';
              presence "Indicates a general-keys node is configured.";
              description
                "Generate a general purpose RSA key pair for signing and encryption";
            }
            container usage-keys {
              must 'not(../general-keys)';
              presence "Indicates a usage-keys node is configured.";
              description
                "Generate usage-keys";
            }
            leaf pubkey {
              type string {
                length "1..1024" {
                  description
                    "Generated keys in pem format";
                }
              }
              mandatory true;
              description
                "Public key";
            }
          }
        }
        container ed25519 {
          presence "Indicates a ed25519 node is configured.";
          description
            "Generate ED25519 keys";
        }
        container dsa {
          description
            "Generate dsa keys";
          leaf number-of-bits {
            type uint32 {
              range "512..2048" {
                description
                  "Number of bits";
              }
            }
            description
              "Number of bits";
          }
        }
        container ecdsa {
          description
            "Generate ecdsa keys";
          container nistp256 {
            presence "Indicates a nistp256 node is configured.";
            description
              " Generate a ECDSA key of curve type nistp256";
          }
          container nistp384 {
            presence "Indicates a nistp384 node is configured.";
            description
              "Generate a ECDSA key of curve type nist384";
          }
          container nistp521 {
            presence "Indicates a nistp521 node is configured.";
            description
              "Generate a ECDSA key of curve type nist521";
          }
        }
      }
    }
  }
}
