module Cisco-IOS-XR-um-line-general-cfg {

  /*** NAMESPACE / PREFIX DEFINITION ***/

  namespace "http://cisco.com/ns/yang/Cisco-IOS-XR-um-line-general-cfg";
  prefix um-line-general-cfg;

  /*** LINKAGE (IMPORTS / INCLUDES) ***/

  import Cisco-IOS-XR-um-line-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR line-general package configuration.

     This YANG module augments the
     modules with configuration data.

     Copyright (c) 2020-2025 by Cisco Systems, Inc., and/or its affiliates.
     All rights reserved.";

  revision 2022-07-11 {
    description
      "Added missing description statement to nodes";
    semver:module-version "1.0.0";
  }

  revision "2020-08-24" {
    description
      "Initial release";
    semver:module-version "1.0.0";
  }

  augment "/a1:line/a1:console" {
    description
      "This augment extends line console nodes
       configuration";
    leaf absolute-timeout {
      type uint32 {
        range "0..10000" {
          description
            "Absolute timeout interval in minutes.";
        }
      }
      description
        "Set absolute timeout for line disconnection.";
    }
    leaf width {
      type uint32 {
        range "0..512" {
          description
            "Number of characters on a screen line.";
        }
      }
      description
        "Set width of the display terminal.";
    }
    leaf length {
      type uint32 {
        range "0..512" {
          description
            "Number of lines on screen (0 for no pausing).";
        }
      }
      description
        "Set number of lines on a screen.";
    }
  }

  augment "/a1:line/a1:default" {
    description
      "This augment extends line default nodes
       configuration";
    leaf absolute-timeout {
      type uint32 {
        range "0..10000" {
          description
            "Absolute timeout interval in minutes.";
        }
      }
      description
        "Set absolute timeout for line disconnection.";
    }
    leaf width {
      type uint32 {
        range "0..512" {
          description
            "Number of characters on a screen line.";
        }
      }
      description
        "Set width of the display terminal.";
    }
    leaf length {
      type uint32 {
        range "0..512" {
          description
            "Number of lines on screen (0 for no pausing).";
        }
      }
      description
        "Set number of lines on a screen.";
    }
  }

  augment "/a1:line/a1:templates/a1:template" {
    description
      "This augment extends line template nodes
       configuration";
    leaf absolute-timeout {
      type uint32 {
        range "0..10000" {
          description
            "Absolute timeout interval in minutes.";
        }
      }
      description
        "Set absolute timeout for line disconnection.";
    }
    leaf width {
      type uint32 {
        range "0..512" {
          description
            "Number of characters on a screen line.";
        }
      }
      description
        "Set width of the display terminal.";
    }
    leaf length {
      type uint32 {
        range "0..512" {
          description
            "Number of lines on screen (0 for no pausing).";
        }
      }
      description
        "Set number of lines on a screen.";
    }
  }
}
