module Cisco-IOS-XR-um-if-mac-address-cfg {

  /*** NAMESPACE / PREFIX DEFINITION ***/

  namespace "http://cisco.com/ns/yang/Cisco-IOS-XR-um-if-mac-address-cfg";
  prefix um-if-mac-address-cfg;

  /*** LINKAGE (IMPORTS / INCLUDES) ***/

  import ietf-yang-types {
    prefix yang;
  }
  import Cisco-IOS-XR-um-interface-cfg {
    prefix a1;
  }
  import tailf-common {
    prefix tailf;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if-mac-address package configuration.

     This YANG module augments the
     modules with configuration data.

     Copyright (c) 2021-2025 by Cisco Systems, Inc., and/or its affiliates.
     All rights reserved.";

  revision 2022-07-11 {
    description
      "Added missing description statement to nodes";
    semver:module-version "1.1.0";
  }

  revision "2021-02-26" {
    description
      "Initial release";
    semver:module-version "1.0.0";
  }

  grouping IF-BODY {
    description
      "Grouping for interface";
    leaf mac-address {
      when "../a1:interface-name[starts-with(text(),'FastEthernet')]"
         + " or ../a1:interface-name[starts-with(text(),'GigabitEthernet')]"
         + " or ../a1:interface-name[starts-with(text(),'TenGigE')]"
         + " or ../a1:interface-name[starts-with(text(),'FortyGigE')]"
         + " or ../a1:interface-name[starts-with(text(),'HundredGigE')]"
         + " or ../a1:interface-name[starts-with(text(),'TwoHundredGigE')]"
         + " or ../a1:interface-name[starts-with(text(),'FourHundredGigE')]"
         + " or ../a1:interface-name[starts-with(text(),'EightHundredGigE')]"
         + " or ../a1:interface-name[starts-with(text(),'TwentyFiveGigE')]"
         + " or ../a1:interface-name[starts-with(text(),'FiftyGigE')]"
         + " or ../a1:interface-name[starts-with(text(),'MgmtEth')]"
         + " or ../a1:interface-name[starts-with(text(),'Bundle-Ether')]"
         + " or ../a1:interface-name[starts-with(text(),'PW-Ether')]"
         + " or ../a1:interface-name[starts-with(text(),'BVI')]"
         + " or ../a1:interface-name[starts-with(text(),'InterflexLeft')]"
         + " or ../a1:interface-name[starts-with(text(),'InterflexRight')]"
         + " or ../a1:interface-name[starts-with(text(),'CSI-Ether')]"
         + " or ../a1:interface-name[starts-with(text(),'PW-P2P')]"
         + " or ../a1:interface-name[starts-with(text(),'SRP')]"
         + " or ../a1:interface-name[starts-with(text(),'CPRIoE')]" {
        tailf:dependency "../a1:interface-name";
      }
      type yang:mac-address;
      description
        "Set the Mac address(xxxx.xxxx.xxxx) on an interface";
    }
  }

  augment "/a1:interfaces/a1:interface" {
    description
      "This augment extends active nodes configuration";
    uses IF-BODY;
  }

  augment "/a1:interfaces/a1:interface-preconfigure" {
    description
      "This augment extends preconfigured nodes
       configuration";
    uses IF-BODY;
  }
}
