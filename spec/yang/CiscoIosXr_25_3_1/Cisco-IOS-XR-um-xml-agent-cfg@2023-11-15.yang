module Cisco-IOS-XR-um-xml-agent-cfg {

  /*** NAMESPACE / PREFIX DEFINITION ***/

  namespace "http://cisco.com/ns/yang/Cisco-IOS-XR-um-xml-agent-cfg";
  prefix um-xml-agent-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR xml-agent package configuration.

     This YANG module augments the
     modules with configuration data.

     Copyright (c) 2021-2025 by Cisco Systems, Inc., and/or its affiliates.
     All rights reserved.";

  revision "2023-11-15" {
    description
      "Changes to remove unsupported feature ipv4/disable from xml tty/ssl";
    semver:module-version "2.0.0";
  }

  revision "2021-05-10" {
    description
      "Initial release";
    semver:module-version "1.0.0";
  }

  container xr-xml {
    description
      "Configuration for XML related services";
    container agent {
      description
        "Enable agent for XML requests";
      container enable {
        presence "Indicates a agent node is configured.";
        description
          "Enable default agent for XML requests";
      }
      container tty {
        presence "Indicates a tty node is configured.";
        description
          "Enable tty agent for XML requests";
        container streaming {
          description
            "Streaming of the xml response";
          container on {
            description
              "Turn on the xml response streaming";
            leaf size {
              type uint32 {
                range "1..100000" {
                  description
                    "Size of the Streaming in Kbytes";
                }
              }
              description
                "Streaming size of the xml response";
            }
          }
        }
        container iteration {
          description
            "Iterator of the xml response";
          leaf size {
            type union {
              type uint32 {
                range "1..100000" {
                  description
                    "Size of the Iteration in Kbytes (default 48 Kbytes)";
                }
              }
              type enumeration {
                enum off {
                  value 0;
                  description
                    "Turn off the xml response iterator";
                }
              }
            }
            description
              "Iterator size of the xml response";
          }
        }
        container throttle {
          description
            "Configuration for throttling XML agent";
          leaf process-rate {
            type uint32 {
              range "1000..30000" {
                description
                  "Number of tags to process per sec";
              }
            }
            description
              "Process rate";
          }
          leaf memory {
            type uint32 {
              range "100..1024" {
                description
                  "Size of the memory usage in Mbytes per session (default 300 Mbytes)";
              }
            }
            description
              "Memory usage";
          }
        }
        container session {
          description
            "session timeout for transport agents";
          leaf timeout {
            type uint32 {
              range "1..1440" {
                description
                  "Timeout in minutes";
              }
            }
            description
              "session timeout for agents";
          }
        }
      }
      container ssl {
        presence "Indicates a ssl node is configured.";
        description
          "Enable ssl agent for XML requests";
        container streaming {
          description
            "Streaming of the xml response";
          container on {
            description
              "Turn on the xml response streaming";
            leaf size {
              type uint32 {
                range "1..100000" {
                  description
                    "Size of the Streaming in Kbytes";
                }
              }
              description
                "Streaming size of the xml response";
            }
          }
        }
        container iteration {
          description
            "Iterator of the xml response";
          leaf size {
            type union {
              type uint32 {
                range "1..100000" {
                  description
                    "Size of the Iteration in Kbytes (default 48 Kbytes)";
                }
              }
              type enumeration {
                enum off {
                  value 0;
                  description
                    "Turn off the xml response iterator";
                }
              }
            }
            description
              "Iterator size of the xml response";
          }
        }
        container throttle {
          description
            "Configuration for throttling XML agent";
          leaf process-rate {
            type uint32 {
              range "1000..30000" {
                description
                  "Number of tags to process per sec";
              }
            }
            description
              "Process rate";
          }
          leaf memory {
            type uint32 {
              range "100..1024" {
                description
                  "Size of the memory usage in Mbytes per session (default 300 Mbytes)";
              }
            }
            description
              "Memory usage";
          }
        }
        container session {
          description
            "session timeout for transport agents";
          leaf timeout {
            type uint32 {
              range "1..1440" {
                description
                  "Timeout in minutes";
              }
            }
            description
              "session timeout for agents";
          }
        }
        container vrfs {
          description
            "VRF configuration commands";
          list vrf {
            key "vrf-name";
            description
              "VRF name";
            leaf vrf-name {
              type union {
                type string {
                  pattern 'default' {
                    description
                      "VRF default";
                  }
                }
                type xr:Cisco-ios-xr-string {
                  length "1..32" {
                    description
                      "VRF Name";
                  }
                  pattern '[a-zA-Z0-9._-]+';
                }
              }
              description
                "VRF name";
            }
            container shutdown {
              presence "Indicates a shutdown node is configured.";
              description
                "Shutdown VRF default configuration";
            }
            container ipv4 {
              description
                "IPv4 transport";
              leaf access-list {
                type xr:Cisco-ios-xr-string {
                  length "1..32" {
                    description
                      "Name of access-list for IPv4 transport for xml agent.";
                  }
                  pattern '[a-z0-9A-Z][-_.:a-z0-9A-Z]*';
                }
                description
                  "IPv4 access list name";
              }
            }
          }
        }
      }
      container ipv6 {
        description
          "IPv6 Transport";
        container enable {
          presence "Indicates a enable node is configured.";
          description
            "Enable IPv6 Transport";
        }
      }
      container ipv4 {
        description
          "IPv4 Transport";
        container disable {
          presence "Indicates a disable node is configured.";
          description
            "Disable IPv4 Transport";
        }
      }
      container streaming {
        description
          "Streaming of the xml response";
        container on {
          description
            "Turn on the xml response streaming";
          leaf size {
            type uint32 {
              range "1..100000" {
                description
                  "Size of the Streaming in Kbytes";
              }
            }
            description
              "Streaming size of the xml response";
          }
        }
      }
      container iteration {
        description
          "Iterator of the xml response";
        leaf size {
          type union {
            type uint32 {
              range "1..100000" {
                description
                  "Size of the Iteration in Kbytes (default 48 Kbytes)";
              }
            }
            type enumeration {
              enum off {
                value 0;
                description
                  "Turn off the xml response iterator";
              }
            }
          }
          description
            "Iterator size of the xml response";
        }
      }
      container throttle {
        description
          "Configuration for throttling XML agent";
        leaf process-rate {
          type uint32 {
            range "1000..30000" {
              description
                "Number of tags to process per sec";
            }
          }
          description
            "Process rate";
        }
        leaf memory {
          type uint32 {
            range "100..1024" {
              description
                "Size of the memory usage in Mbytes per session (default 300 Mbytes)";
            }
          }
          description
            "Memory usage";
        }
      }
      container session {
        description
          "session timeout for transport agents";
        leaf timeout {
          type uint32 {
            range "1..1440" {
              description
                "Timeout in minutes";
            }
          }
          description
            "session timeout for agents";
        }
      }
      container vrfs {
        description
          "VRF configuration commands";
        list vrf {
          key "vrf-name";
          description
            "VRF name";
          leaf vrf-name {
            type union {
              type string {
                pattern 'default' {
                  description
                    "VRF default";
                }
              }
              type xr:Cisco-ios-xr-string {
                length "1..32" {
                  description
                    "VRF Name";
                }
                pattern '[a-zA-Z0-9._-]+';
              }
            }
            description
              "VRF name";
          }
          container shutdown {
            presence "Indicates a shutdown node is configured.";
            description
              "Shutdown VRF default configuration";
          }
          container ipv6 {
            description
              "IPv6 transport";
            leaf access-list {
              type xr:Cisco-ios-xr-string {
                length "1..32" {
                  description
                    "Name of access-list for IPv6 transport for xml agent.";
                }
                pattern '[a-z0-9A-Z][-_.:a-z0-9A-Z]*';
              }
              description
                "IPv6 access list name";
            }
          }
          container ipv4 {
            description
              "IPv4 transport";
            leaf access-list {
              type xr:Cisco-ios-xr-string {
                length "1..32" {
                  description
                    "Name of access-list for IPv4 transport for xml agent.";
                }
                pattern '[a-z0-9A-Z][-_.:a-z0-9A-Z]*';
              }
              description
                "IPv4 access list name";
            }
          }
        }
      }
    }
  }
  container netconf {
    description
      "NETCONF configuration commands";
    container agent {
      description
        "NETCONF agent configuration commands";
      container tty {
        presence "Indicates a tty node is configured.";
        description
          "Enable NETCONF agent over TTY";
        container throttle {
          description
            "Configuration for throttling NETCONF agent";
          leaf process-rate {
            type uint32 {
              range "1000..30000" {
                description
                  "Number of tags to process per sec";
              }
            }
            description
              "Process rate";
          }
          leaf memory {
            type uint32 {
              range "100..1024" {
                description
                  "Size of the memory usage in Mbytes per session (default 300 Mbytes)";
              }
            }
            description
              "Memory usage";
          }
          leaf offload-memory {
            type uint32 {
              range "0..12000" {
                description
                  "Size of the memory that can be offloaded to clients(default 0 Mbytes)";
              }
            }
            description
              "Memory offload to clients";
          }
        }
        container session {
          description
            "Session timeout for transport agents";
          leaf timeout {
            type uint32 {
              range "1..1440" {
                description
                  "Timeout in minutes";
              }
            }
            description
              "Session timeout for agents";
          }
        }
      }
    }
  }
}
