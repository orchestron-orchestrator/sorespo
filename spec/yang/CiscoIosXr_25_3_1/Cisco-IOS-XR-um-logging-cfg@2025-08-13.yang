module Cisco-IOS-XR-um-logging-cfg {
  namespace "http://cisco.com/ns/yang/Cisco-IOS-XR-um-logging-cfg";
  prefix um-logging-cfg;

  import Cisco-IOS-XR-um-service-cfg {
    prefix service-cfg;
  }
  import Cisco-IOS-XR-types {
    prefix xr;
  }
  import ietf-inet-types {
    prefix inet;
  }

  import cisco-semver { prefix "semver"; }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco timestamps package configuration.
     This YANG module augments and other modules configuration data.

     Copyright (c) 2024-2025 by Cisco Systems, Inc., and/or its affiliates.
     All rights reserved.";

  revision 2025-08-13 {
    description
      "Changed help string for tls1.1 and tls1.0 to indicate that they are deprecated
       2025-03-14
         localfilesize CLI upper limit reduced from 4Gb to 125Mb
       2024-10-21
         Initial UM2 release
       2023-04-28
         Buffered Logging Entries Count Changes
       2023-03-08
         Removed non-standard logging facility enum members
       2023-01-27
         Added facility and source address for per remotehost entry
       2022-07-22
         Added fetch-timestamp
       2022-07-11
         Added missing description statement to nodes
       2022-02-28
         Added leaf yang";
    semver:module-version "3.0.0";
  }

  revision "2021-10-29" {
    description
      "Added the container monitor-discriminator
      2021-10-18
          Changed sch-type for the node ipv6-address under container host-ipv6-addresses";
    semver:module-version "2.0.0";
  }

  revision "2021-03-08" {
    description
      "Initial release";
    semver:module-version "1.0.0";
  }

  grouping GROUP-SERVICE-CFG-SERVICE-BODY {
    description
      "Group for timestamps";
    container timestamps {
      description
        "Timestamp debug/log messages";
      container log {
        description
          "Timestamp log messages";
        leaf uptime {
          type empty;
          description
            "Timestamp with systime uptime";
        }
        leaf disable {
          type empty;
          description
            "Disable timestamp log messages";
        }
        container datetime {
          must 'localtime or msec or usec or show-timezone or year';
          presence "Timestamp with date and time";
          description
            "Timestamp with date and time";
          leaf localtime {
            type empty;
            description
              "Use local time zone for timestamps";
          }
          choice INCLUDE-MILLISECOND-TIMESTAMP {
            description
              "timestamp units";
            case MSEC {
              leaf msec {
                type empty;
                description
                  "Include milliseconds in timestamp";
              }
            }
            case USEC {
              leaf usec {
                type empty;
                description
                  "Include microseconds in timestamp";
              }
            }
          }
          leaf show-timezone {
            type empty;
            description
              "Add time zone information to timestamp";
          }
          leaf year {
            type empty;
            description
              "Add Year to timestamp";
          }
        }
      }
      container debug {
        description
          "Timestamp debug messages";
        leaf uptime {
          type empty;
          description
            "Timestamp with systime uptime";
        }
        leaf disable {
          type empty;
          description
            "Disable timestamp debug messages";
        }
        container datetime {
          must 'localtime or msec or usec or show-timezone or year';
          presence "Timestamp with date and time";
          description
            "Timestamp with date and time";
          leaf localtime {
            type empty;
            description
              "Use local time zone for timestamps";
          }
          choice INCLUDE-MILLISECOND-TIMESTAMP {
            description
              "timestamp units";
            case MSEC {
              leaf msec {
                type empty;
                description
                  "Include milliseconds in timestamp";
              }
            }
            case USEC {
              leaf usec {
                type empty;
                description
                  "Include microseconds in timestamp";
              }
            }
          }
          leaf show-timezone {
            type empty;
            description
              "Add time zone information to timestamp";
          }
          leaf year {
            type empty;
            description
              "Add Year to timestamp";
          }
        }
      }
    }
  }

  augment "/service-cfg:service" {
    description
      "This augment extends the configuration data of Cisco-IOS-XR-um-service-cfg";
    uses GROUP-SERVICE-CFG-SERVICE-BODY;
  }

  container logging {
    description
      "Modify message logging facilities";
    grouping HOSTNAME-OPTIONS {
      description
        "hostname options";
      leaf severity {
        type enumeration {
          enum alerts {
            value 1;
            description
              "Immediate action needed           (severity=1)";
          }
          enum critical {
            value 2;
            description
              "Critical conditions               (severity=2)";
          }
          enum debugging {
            value 7;
            description
              "Debugging messages                (severity=7)";
          }
          enum emergencies {
            value 0;
            description
              "System is unusable                (severity=0)";
          }
          enum errors {
            value 3;
            description
              "Error conditions                  (severity=3)";
          }
          enum informational {
            value 6;
            description
              "Informational messages            (severity=6)";
          }
          enum notifications {
            value 5;
            description
              "Normal but significant conditions (severity=5)";
          }
          enum warning {
            value 4;
            description
              "Warning conditions                (severity=4)";
          }
          enum all {
            value 8;
            description
              "All severity messages             (severity=8)";
          }
          enum none {
            value 9;
            description
              "None of serverity messages        (severity=9)";
          }
        }
        description
          "severity";
      }
      leaf port {
        type union {
          type uint32 {
            range "0..65535" {
              description
                "non-default Port";
            }
          }
          type enumeration {
            enum default {
              value 514;
              description
                "default port";
            }
          }
        }
        description
          "Set UDP port for this remote host/vrf";
      }
      leaf operator {
        type enumeration {
          enum equals-or-higher {
            value 0;
            description
              "Log messages equal to or higher than severity";
          }
          enum equals {
            value 1;
            description
              "Log messages equal to severity";
          }
          enum not-equals {
            value 2;
            description
              "Log messages not equal to severity";
          }
        }
        description
          "Set severity operator of  messages for particular remote host/vrf";
      }
      leaf facility {
        type enumeration {
          enum kern {
            value 0;
            description
              "Kernel";
          }
          enum user {
            value 8;
            description
              "User process";
          }
          enum mail {
            value 16;
            description
              "Mail system";
          }
          enum daemon {
            value 24;
            description
              "System daemons";
          }
          enum auth {
            value 32;
            description
              "Authorization system";
          }
          enum syslog {
            value 40;
            description
              "Syslog itself";
          }
          enum authpriv {
            value 80;
            description
              "Privileged authorization messages";
          }
          enum ntp {
            value 96;
            description
              "NTP subsystem";
          }
          enum audit {
            value 104;
            description
              "log audit";
          }
          enum console {
            value 112;
            description
              "log alert messages";
          }
          enum local0 {
            value 128;
            description
              "Local use";
          }
          enum local1 {
            value 136;
            description
              "Local use";
          }
          enum local2 {
            value 144;
            description
              "Local use";
          }
          enum local3 {
            value 152;
            description
              "Local use";
          }
          enum local4 {
            value 160;
            description
              "Local use";
          }
          enum local5 {
            value 168;
            description
              "Local use";
          }
          enum local6 {
            value 176;
            description
              "Local use";
          }
          enum local7 {
            value 184;
            description
              "Local use";
          }
          enum all {
            value 192;
            description
              "All supported facilities";
          }
        }
        description
          "Modify message logging facilities";
      }
      leaf source-address {
        type inet:ip-address-no-zone;
        description
          "Specify source address of the logging host";
      }
    }

    container monitor {
      description
        "Set monitor logging";
      container discriminator {
        description
          "Set monitor logging discriminator";
        leaf match1 {
          type string {
            length "1..32" {
              description
                "match discriminator 1";
            }
          }
          description
            "Set match discriminator 1";
        }
        leaf match2 {
          type string {
            length "1..32" {
              description
                "match discriminator 2";
            }
          }
          description
            "Set match discriminator 2";
        }
        leaf match3 {
          type string {
            length "1..32" {
              description
                "match discriminator 3";
            }
          }
          description
            "Set match discriminator 3";
        }
        leaf nomatch1 {
          type string {
            length "1..32" {
              description
                "no-match discriminator 1";
            }
          }
          description
            "Set no-match discriminator 1";
        }
        leaf nomatch2 {
          type string {
            length "1..32" {
              description
                "no-match discriminator 2";
            }
          }
          description
            "Set no-match discriminator 2";
        }
        leaf nomatch3 {
          type string {
            length "1..32" {
              description
                "no-match discriminator 3";
            }
          }
          description
            "Set no-match discriminator 3";
        }
      }
      leaf monitor-level {
        type enumeration {
          enum alerts {
            value 1;
            description
              "Immediate action needed           (severity=1)";
          }
          enum critical {
            value 2;
            description
              "Critical conditions               (severity=2)";
          }
          enum debugging {
            value 7;
            description
              "Debugging messages                (severity=7)";
          }
          enum emergencies {
            value 0;
            description
              "System is unusable                (severity=0)";
          }
          enum errors {
            value 3;
            description
              "Error conditions                  (severity=3)";
          }
          enum informational {
            value 6;
            description
              "Informational messages            (severity=6)";
          }
          enum notifications {
            value 5;
            description
              "Normal but significant conditions (severity=5)";
          }
          enum warning {
            value 4;
            description
              "Warning conditions                (severity=4)";
          }
          enum disable {
            value 15;
            description
              "Disable logging";
          }
        }
        description
          "Set monitor logging";
      }
    }
    leaf trap {
      type enumeration {
        enum alerts {
          value 1;
          description
            "Immediate action needed           (severity=1)";
        }
        enum critical {
          value 2;
          description
            "Critical conditions               (severity=2)";
        }
        enum debugging {
          value 7;
          description
            "Debugging messages                (severity=7)";
        }
        enum emergencies {
          value 0;
          description
            "System is unusable                (severity=0)";
        }
        enum errors {
          value 3;
          description
            "Error conditions                  (severity=3)";
        }
        enum informational {
          value 6;
          description
            "Informational messages            (severity=6)";
        }
        enum notifications {
          value 5;
          description
            "Normal but significant conditions (severity=5)";
        }
        enum warning {
          value 4;
          description
            "Warning conditions                (severity=4)";
        }
        enum disable {
          value 15;
          description
            "Disable logging";
        }
      }
      description
        "Set trap logging";
    }
    container console {
      description
        "Set console logging";
      container discriminator {
        description
          "Set console logging discriminator";
        leaf match1 {
          type string {
            length "1..32" {
              description
                "match discriminator 1";
            }
          }
          description
            "Set match discriminator 1";
        }
        leaf match2 {
          type string {
            length "1..32" {
              description
                "match discriminator 2";
            }
          }
          description
            "Set match discriminator 2";
        }
        leaf match3 {
          type string {
            length "1..32" {
              description
                "match discriminator 3";
            }
          }
          description
            "Set match discriminator 3";
        }
        leaf nomatch1 {
          type string {
            length "1..32" {
              description
                "no-match discriminator 1";
            }
          }
          description
            "Set no-match discriminator 1";
        }
        leaf nomatch2 {
          type string {
            length "1..32" {
              description
                "no-match discriminator 2";
            }
          }
          description
            "Set no-match discriminator 2";
        }
        leaf nomatch3 {
          type string {
            length "1..32" {
              description
                "no-match discriminator 3";
            }
          }
          description
            "Set no-match discriminator 3";
        }
      }
      leaf console-level {
        type enumeration {
          enum alerts {
            value 1;
            description
              "Immediate action needed           (severity=1)";
          }
          enum critical {
            value 2;
            description
              "Critical conditions               (severity=2)";
          }
          enum debugging {
            value 7;
            description
              "Debugging messages                (severity=7)";
          }
          enum emergencies {
            value 0;
            description
              "System is unusable                (severity=0)";
          }
          enum errors {
            value 3;
            description
              "Error conditions                  (severity=3)";
          }
          enum informational {
            value 6;
            description
              "Informational messages            (severity=6)";
          }
          enum notifications {
            value 5;
            description
              "Normal but significant conditions (severity=5)";
          }
          enum warning {
            value 4;
            description
              "Warning conditions                (severity=4)";
          }
          enum disable {
            value 15;
            description
              "Disable logging";
          }
        }
        description
          "console level";
      }
      container facility {
        description
          "Modify console message logging facilities";
        leaf all {
          type enumeration {
            enum all {
              value 192;
              description
                "All supported facilities";
            }
          }
          description
            "All supported facilities";
        }
      }
    }
    container ipv6 {
      description
        "Mark the dscp/precedence bit for ipv6 packets";
      choice IPV6 {
        description
          "Mark the dscp/precedence bit for ipv6 packets";
        case DSCP {
          container dscp {
            must 'dscp-value';
            presence "Set IP DSCP (DiffServ CodePoint)";
            description
              "Set IP DSCP (DiffServ CodePoint)";
            leaf dscp-value {
              type union {
                type uint32 {
                  range "0..63" {
                    description
                      "Differentiated services codepoint value";
                  }
                }
                type enumeration {
                  enum af11 {
                    value 10;
                    description
                      "Match packets with AF11 (DSCP 001010)";
                  }
                  enum af12 {
                    value 12;
                    description
                      "Match packets with AF12 (DSCP 001100)";
                  }
                  enum af13 {
                    value 14;
                    description
                      "Match packets with AF13 (DSCP 001110)";
                  }
                  enum af21 {
                    value 18;
                    description
                      "Match packets with AF21 (DSCP 010010)";
                  }
                  enum af22 {
                    value 20;
                    description
                      "Match packets with AF22 (DSCP 010100)";
                  }
                  enum af23 {
                    value 22;
                    description
                      "Match packets with AF23 (DSCP 010110)";
                  }
                  enum af31 {
                    value 26;
                    description
                      "Match packets with AF31 (DSCP 011010)";
                  }
                  enum af32 {
                    value 28;
                    description
                      "Match packets with AF32 (DSCP 011100)";
                  }
                  enum af33 {
                    value 30;
                    description
                      "Match packets with AF33 (DSCP 011110)";
                  }
                  enum af41 {
                    value 34;
                    description
                      "Match packets with AF41 (DSCP 100010)";
                  }
                  enum af42 {
                    value 36;
                    description
                      "Match packets with AF42 (DSCP 100100)";
                  }
                  enum af43 {
                    value 38;
                    description
                      "Match packets with AF43 (DSCP 100110)";
                  }
                  enum cs1 {
                    value 8;
                    description
                      "Match packets with CS1 (Precedence 1) (DSCP 001000)";
                  }
                  enum cs2 {
                    value 16;
                    description
                      "Match packets with CS2 (Precedence 2) (DSCP 010000)";
                  }
                  enum cs3 {
                    value 24;
                    description
                      "Match packets with CS3 (Precedence 3) (DSCP 011000)";
                  }
                  enum cs4 {
                    value 32;
                    description
                      "Match packets with CS4 (Precedence 4) (DSCP 100000)";
                  }
                  enum cs5 {
                    value 40;
                    description
                      "Match packets with CS5 (Precedence 5) (DSCP 101000)";
                  }
                  enum cs6 {
                    value 48;
                    description
                      "Match packets with CS6 (Precedence 6) (DSCP 110000)";
                  }
                  enum cs7 {
                    value 56;
                    description
                      "Match packets with CS7 (Precedence 7) (DSCP 111000)";
                  }
                  enum default {
                    value 0;
                    description
                      "Match packets with default (DSCP 000000)";
                  }
                  enum ef {
                    value 46;
                    description
                      "Match packets with EF dscp (101110)";
                  }
                }
              }
              description
                "Set IP DSCP (DiffServ CodePoint)";
            }
          }
        }
        case PRECEDENCE {
          container precedence {
            must 'precedence-value';
            presence "Set precedence";
            description
              "Set precedence";
            leaf precedence-value {
              type union {
                type uint32 {
                  range "0..7" {
                    description
                      "Precedence value";
                  }
                }
                type enumeration {
                  enum critical {
                    value 5;
                    description
                      "Match packets with critical precedence (5)";
                  }
                  enum flash {
                    value 3;
                    description
                      "Match packets with flash precedence (3)";
                  }
                  enum flash-override {
                    value 4;
                    description
                      "Match packets with flash override precedence (4)";
                  }
                  enum immediate {
                    value 2;
                    description
                      "Match packets with immediate precedence (2)";
                  }
                  enum internet {
                    value 6;
                    description
                      "Match packets with internetwork control precedence (6)";
                  }
                  enum network {
                    value 7;
                    description
                      "Match packets with network control precedence (7)";
                  }
                  enum priority {
                    value 1;
                    description
                      "Match packets with priority precedence (1)";
                  }
                  enum routine {
                    value 0;
                    description
                      "Match packets with routine precedence (0)";
                  }
                }
              }
              description
                "Set precedence";
            }
          }
        }
      }
    }
    container ipv4 {
      description
        "Mark the dscp/precedence bit for ipv4 packets";
      choice IPV4 {
        description
          "Mark the dscp/precedence bit for ipv4 packets";
        case DSCP {
          container dscp {
            must 'dscp-value';
            presence "Set IP DSCP (DiffServ CodePoint)";
            description
              "Set IP DSCP (DiffServ CodePoint)";
            leaf dscp-value {
              type union {
                type uint32 {
                  range "0..63" {
                    description
                      "Differentiated services codepoint value";
                  }
                }
                type enumeration {
                  enum af11 {
                    value 10;
                    description
                      "Match packets with AF11 (DSCP 001010)";
                  }
                  enum af12 {
                    value 12;
                    description
                      "Match packets with AF12 (DSCP 001100)";
                  }
                  enum af13 {
                    value 14;
                    description
                      "Match packets with AF13 (DSCP 001110)";
                  }
                  enum af21 {
                    value 18;
                    description
                      "Match packets with AF21 (DSCP 010010)";
                  }
                  enum af22 {
                    value 20;
                    description
                      "Match packets with AF22 (DSCP 010100)";
                  }
                  enum af23 {
                    value 22;
                    description
                      "Match packets with AF23 (DSCP 010110)";
                  }
                  enum af31 {
                    value 26;
                    description
                      "Match packets with AF31 (DSCP 011010)";
                  }
                  enum af32 {
                    value 28;
                    description
                      "Match packets with AF32 (DSCP 011100)";
                  }
                  enum af33 {
                    value 30;
                    description
                      "Match packets with AF33 (DSCP 011110)";
                  }
                  enum af41 {
                    value 34;
                    description
                      "Match packets with AF41 (DSCP 100010)";
                  }
                  enum af42 {
                    value 36;
                    description
                      "Match packets with AF42 (DSCP 100100)";
                  }
                  enum af43 {
                    value 38;
                    description
                      "Match packets with AF43 (DSCP 100110)";
                  }
                  enum cs1 {
                    value 8;
                    description
                      "Match packets with CS1 (Precedence 1) (DSCP 001000)";
                  }
                  enum cs2 {
                    value 16;
                    description
                      "Match packets with CS2 (Precedence 2) (DSCP 010000)";
                  }
                  enum cs3 {
                    value 24;
                    description
                      "Match packets with CS3 (Precedence 3) (DSCP 011000)";
                  }
                  enum cs4 {
                    value 32;
                    description
                      "Match packets with CS4 (Precedence 4) (DSCP 100000)";
                  }
                  enum cs5 {
                    value 40;
                    description
                      "Match packets with CS5 (Precedence 5) (DSCP 101000)";
                  }
                  enum cs6 {
                    value 48;
                    description
                      "Match packets with CS6 (Precedence 6) (DSCP 110000)";
                  }
                  enum cs7 {
                    value 56;
                    description
                      "Match packets with CS7 (Precedence 7) (DSCP 111000)";
                  }
                  enum default {
                    value 0;
                    description
                      "Match packets with default (DSCP 000000)";
                  }
                  enum ef {
                    value 46;
                    description
                      "Match packets with EF dscp (101110)";
                  }
                }
              }
              description
                "Set IP DSCP (DiffServ CodePoint)";
            }
          }
        }
        case PRECEDENCE {
          container precedence {
            must 'precedence-value';
            presence "Set precedence";
            description
              "Set precedence";
            leaf precedence-value {
              type union {
                type uint32 {
                  range "0..7" {
                    description
                      "Precedence value";
                  }
                }
                type enumeration {
                  enum critical {
                    value 5;
                    description
                      "Match packets with critical precedence (5)";
                  }
                  enum flash {
                    value 3;
                    description
                      "Match packets with flash precedence (3)";
                  }
                  enum flash-override {
                    value 4;
                    description
                      "Match packets with flash override precedence (4)";
                  }
                  enum immediate {
                    value 2;
                    description
                      "Match packets with immediate precedence (2)";
                  }
                  enum internet {
                    value 6;
                    description
                      "Match packets with internetwork control precedence (6)";
                  }
                  enum network {
                    value 7;
                    description
                      "Match packets with network control precedence (7)";
                  }
                  enum priority {
                    value 1;
                    description
                      "Match packets with priority precedence (1)";
                  }
                  enum routine {
                    value 0;
                    description
                      "Match packets with routine precedence (0)";
                  }
                }
              }
              description
                "Set precedence";
            }
          }
        }
      }
    }
    leaf yang {
      type enumeration {
        enum alerts {
          value 1;
          description
            "Immediate action needed";
        }
        enum critical {
          value 2;
          description
            "Critical conditions";
        }
        enum debugging {
          value 7;
          description
            "Debugging messages";
        }
        enum emergencies {
          value 0;
          description
            "System is unusable";
        }
        enum errors {
          value 3;
          description
            "Error conditions";
        }
        enum informational {
          value 6;
          description
            "Informational messages";
        }
        enum notifications {
          value 5;
          description
            "Normal but significant conditions";
        }
        enum warnings {
          value 4;
          description
            "Warning conditions";
        }
        enum disable {
          value 15;
          description
            "Disable yang logging parameters";
        }
      }
      description
        "Set yang logging parameters";
    }
    container buffered {
      description
        "Set buffered logging parameters";
      leaf entries-count {
        type uint32 {
          range "2545..151699" {
            description
              "Number of syslog entries in buffer";
          }
        }
        description
          "Syslog in buffer";
      }
      container discriminator {
        description
          "Set logging buffer discriminator";
        leaf match1 {
          type string {
            length "1..32" {
              description
                "match discriminator 1";
            }
          }
          description
            "Set match discriminator 1";
        }
        leaf match2 {
          type string {
            length "1..32" {
              description
                "match discriminator 2";
            }
          }
          description
            "Set match discriminator 2";
        }
        leaf match3 {
          type string {
            length "1..32" {
              description
                "match discriminator 3";
            }
          }
          description
            "Set match discriminator 3";
        }
        leaf nomatch1 {
          type string {
            length "1..32" {
              description
                "no-match discriminator 1";
            }
          }
          description
            "Set no-match discriminator 1";
        }
        leaf nomatch2 {
          type string {
            length "1..32" {
              description
                "no-match discriminator 2";
            }
          }
          description
            "Set no-match discriminator 2";
        }
        leaf nomatch3 {
          type string {
            length "1..32" {
              description
                "no-match discriminator 3";
            }
          }
          description
            "Set no-match discriminator 3";
        }
      }
      leaf buffered-level {
        type enumeration {
          enum alerts {
            value 1;
            description
              "Immediate action needed";
          }
          enum critical {
            value 2;
            description
              "Critical conditions";
          }
          enum debugging {
            value 7;
            description
              "Debugging messages";
          }
          enum emergencies {
            value 0;
            description
              "System is unusable";
          }
          enum errors {
            value 3;
            description
              "Error conditions";
          }
          enum informational {
            value 6;
            description
              "Informational messages";
          }
          enum notifications {
            value 5;
            description
              "Normal but significant conditions";
          }
          enum warnings {
            value 4;
            description
              "Warning conditions";
          }
        }
        description
          "buffered level";
      }
      leaf log-buffer-size {
        type uint32 {
          range "2097152..125000000" {
            description
              "Logging buffer size";
          }
        }
        description
          "Logging buffer size";
      }
    }
    leaf hostnameprefix {
      type string {
        length "1..1024" {
          description
            "hostname prefix string";
        }
      }
      description
        "Hostname prefix to add on msgs to servers";
    }
    container source-interfaces {
      description
        "Specify interface for source address in logging transactions";
      list source-interface {
        key "interface-name vrf-name";
        description
          "Specify interface for source address in logging transactions";
        leaf interface-name {
          type xr:Interface-name;
          description
            "Specify interface for source address in logging transactions";
        }
        leaf vrf-name {
          type xr:Cisco-ios-xr-string {
            length "1..1024" {
              description
                "specify the vrf name";
            }
          }
          description
            "Set VRF option";
        }
      }
    }
    leaf format {
      type enumeration {
        enum rfc5424 {
          value 1;
          description
            "Enable to send the syslog message rfc5424 format";
        }
        enum bsd {
          value 2;
          description
            "Enable to send the syslog message as BSD format";
        }
      }
      description
        "Specify syslog message format send to the server";
    }
    container suppress {
      description
        "Suppress logging behaviour";
      leaf duplicates {
        type empty;
        description
          "Suppress consecutive duplicate messages";
      }
    }
    container history {
      description
        "Set history logging";
      leaf size {
        type uint32 {
          range "1..500" {
            description
              "Logging history size";
          }
        }
        description
          "Logging history size";
      }
      leaf level {
        type enumeration {
          enum alerts {
            value 1;
            description
              "Immediate action needed";
          }
          enum critical {
            value 2;
            description
              "Critical conditions";
          }
          enum debugging {
            value 7;
            description
              "Debugging messages";
          }
          enum emergencies {
            value 0;
            description
              "System is unusable";
          }
          enum errors {
            value 3;
            description
              "Error conditions";
          }
          enum informational {
            value 6;
            description
              "Informational messages";
          }
          enum notifications {
            value 5;
            description
              "Normal but significant conditions";
          }
          enum warnings {
            value 4;
            description
              "Warning conditions";
          }
          enum disable {
            value 15;
            description
              "Disable logging";
          }
        }
        description
          "history level";
      }
    }
    leaf localfilesize {
      type uint32 {
        range "1..125000000" {
          description
            "Size of the local log file";
        }
      }
      description
        "Set size of the local log file";
    }
    leaf facility {
      type enumeration {
        enum kern {
          value 0;
          description
            "Kernel";
        }
        enum user {
          value 8;
          description
            "User process";
        }
        enum mail {
          value 16;
          description
            "Mail system";
        }
        enum daemon {
          value 24;
          description
            "System daemons";
        }
        enum auth {
          value 32;
          description
            "Authorization system";
        }
        enum syslog {
          value 40;
          description
            "Syslog itself";
        }
        enum authpriv {
          value 80;
          description
            "Privileged authorization messages";
        }
        enum ntp {
          value 96;
          description
            "NTP subsystem";
        }
        enum audit {
          value 104;
          description
            "log audit";
        }
        enum console {
          value 112;
          description
            "log alert messages";
        }
        enum local0 {
          value 128;
          description
            "Local use";
        }
        enum local1 {
          value 136;
          description
            "Local use";
        }
        enum local2 {
          value 144;
          description
            "Local use";
        }
        enum local3 {
          value 152;
          description
            "Local use";
        }
        enum local4 {
          value 160;
          description
            "Local use";
        }
        enum local5 {
          value 168;
          description
            "Local use";
        }
        enum local6 {
          value 176;
          description
            "Local use";
        }
        enum local7 {
          value 184;
          description
            "Local use";
        }
        enum all {
          value 192;
          description
            "All supported facilities";
        }
      }
      description
        "Modify message logging facilities";
    }
    container container {
      description
        "Enable to include containers application logs";
      leaf fetch-timestamp {
        type empty;
        description
          "Fetch logs with container timestamp for all containers";
      }
      leaf all {
        type empty;
        description
          "Enables log collection from all containers";
      }
    }
    container files {
      description
        "Set file logging";
      list file {
        must 'discriminator or path';
        key "file-name";
        description
          "Set file logging";
        leaf file-name {
          type string {
            length "1..256" {
              description
                "File name";
            }
          }
          description
            "File name";
        }
        container discriminator {
          description
            "Set file logging discriminator";
          leaf match1 {
            type string {
              length "1..32" {
                description
                  "match discriminator 1";
              }
            }
            description
              "Set match discriminator 1";
          }
          leaf match2 {
            type string {
              length "1..32" {
                description
                  "match discriminator 2";
              }
            }
            description
              "Set match discriminator 2";
          }
          leaf match3 {
            type string {
              length "1..32" {
                description
                  "match discriminator 3";
              }
            }
            description
              "Set match discriminator 3";
          }
          leaf nomatch1 {
            type string {
              length "1..32" {
                description
                  "no-match discriminator 1";
              }
            }
            description
              "Set no-match discriminator 1";
          }
          leaf nomatch2 {
            type string {
              length "1..32" {
                description
                  "no-match discriminator 2";
              }
            }
            description
              "Set no-match discriminator 2";
          }
          leaf nomatch3 {
            type string {
              length "1..32" {
                description
                  "no-match discriminator 3";
              }
            }
            description
              "Set no-match discriminator 3";
          }
        }
        container path {
          presence "Set file path";
          description
            "Set file path";
          leaf path-name {
            type string {
              length "1..256" {
                description
                  "File path (e.g. /disk0: )";
              }
            }
            mandatory true;
            description
              "File path (e.g. /disk0: )";
          }
          leaf maxfilesize {
            type uint32 {
              range "1..2097152" {
                description
                  "Max file size (in KB)";
              }
            }
            mandatory true;
            description
              "Set max file size";
          }
          leaf severity {
            type enumeration {
              enum alerts {
                value 1;
                description
                  "Immediate action needed           (severity=1)";
              }
              enum critical {
                value 2;
                description
                  "Critical conditions               (severity=2)";
              }
              enum debugging {
                value 7;
                description
                  "Debugging messages                (severity=7)";
              }
              enum emergencies {
                value 0;
                description
                  "System is unusable                (severity=0)";
              }
              enum errors {
                value 3;
                description
                  "Error conditions                  (severity=3)";
              }
              enum informational {
                value 6;
                description
                  "Informational messages            (severity=6)";
              }
              enum notifications {
                value 5;
                description
                  "Normal but significant conditions (severity=5)";
              }
              enum warning {
                value 4;
                description
                  "Warning conditions                (severity=4)";
              }
              enum disable {
                value 15;
                description
                  "Disable logging";
              }
            }
            mandatory true;
            description
              "severity";
          }
          container local-accounting {
            presence "Store only the command accounting logs";
            description
              "Store only the command accounting logs";
            container send-to-remote {
              presence "Send the command accounting logs to syslog server";
              description
                "Send the command accounting logs to syslog server";
              leaf facility {
                type enumeration {
                  enum auth {
                    value 32;
                    description
                      "Authorization system";
                  }
                  enum cron {
                    value 72;
                    description
                      "Cron/at facility";
                  }
                  enum daemon {
                    value 24;
                    description
                      "System daemons";
                  }
                  enum kern {
                    value 0;
                    description
                      "Kernel";
                  }
                  enum local0 {
                    value 128;
                    description
                      "Local use";
                  }
                  enum local1 {
                    value 136;
                    description
                      "Local use";
                  }
                  enum local2 {
                    value 144;
                    description
                      "Local use";
                  }
                  enum local3 {
                    value 152;
                    description
                      "Local use";
                  }
                  enum local4 {
                    value 160;
                    description
                      "Local use";
                  }
                  enum local5 {
                    value 168;
                    description
                      "Local use";
                  }
                  enum local6 {
                    value 176;
                    description
                      "Local use";
                  }
                  enum local7 {
                    value 184;
                    description
                      "Local use";
                  }
                  enum lpr {
                    value 48;
                    description
                      "Line printer system";
                  }
                  enum mail {
                    value 16;
                    description
                      "Mail system";
                  }
                  enum news {
                    value 56;
                    description
                      "USENET news";
                  }
                  enum syslog {
                    value 40;
                    description
                      "Syslog itself";
                  }
                  enum user {
                    value 8;
                    description
                      "User process";
                  }
                  enum uucp {
                    value 64;
                    description
                      "Unix-to-Unix copy system";
                  }
                }
                description
                  "Modify message logging facilities";
              }
            }
          }
        }
      }
    }
    container tls-servers {
      description
        "Secure server over tls";
      list tls-server {
        key "tls-server-name";
        description
          "Secure server over tls";
        leaf tls-server-name {
          type string {
            length "1..1024" {
              description
                "Name for the tls peer configuration";
            }
          }
          description
            "Name for the tls peer configuration";
        }
        leaf vrf {
          type string {
            length "1..32" {
              description
                "VPN Routing/Forwarding instance name";
            }
          }
          description
            "Set VRF option";
        }
        container address {
          description
            "Specify a TLS server address";
          leaf ipv6 {
            type inet:ipv6-address-no-zone;
            description
              "IPv6 Address";
          }
          leaf ipv4 {
            type inet:ipv4-address-no-zone;
            description
              "IPv4 Address";
          }
        }
        leaf tls-hostname {
          type string {
            length "1..1024" {
              description
                "Name of the logging host";
            }
          }
          description
            "Hostname or FQDN of Secure Log server";
        }
        leaf trustpoint {
          type string {
            length "1..32" {
              description
                "Name of the trustpoint configured";
            }
          }
          description
            "Trustpoint";
        }
        leaf severity {
          type enumeration {
            enum alerts {
              value 1;
              description
                "Immediate action needed           (severity=1)";
            }
            enum critical {
              value 2;
              description
                "Critical conditions               (severity=2)";
            }
            enum debugging {
              value 7;
              description
                "Debugging messages                (severity=7)";
            }
            enum emergencies {
              value 0;
              description
                "System is unusable                (severity=0)";
            }
            enum errors {
              value 3;
              description
                "Error conditions                  (severity=3)";
            }
            enum informational {
              value 6;
              description
                "Informational messages            (severity=6)";
            }
            enum notifications {
              value 5;
              description
                "Normal but significant conditions (severity=5)";
            }
            enum warning {
              value 4;
              description
                "Warning conditions                (severity=4)";
            }
          }
          description
            "severity of remote host";
        }
        leaf source-interface {
          type xr:Interface-name;
          description
            "Specify Source interface";
        }
        container version {
          description
            "TLS version";
          leaf min-version {
            type enumeration {
              enum tls1.0 {
                value 100;
                status deprecated;
                description
                  "Set TLSv1.0 to be used as min version for syslog, TLSv1.0 is deprecated from 25.3.1";
              }
              enum tls1.1 {
                value 101;
                status deprecated;
                description
                  "Set TLSv1.1 to be used as min version for syslog, TLSv1.1 is deprecated from 25.3.1";
              }
              enum tls1.2 {
                value 102;
                description
                  "Set TLSv1.2 to be used as min version for syslog";
              }
              enum tls1.3 {
                value 103;
                description
                  "Set TLSv1.3 to be used as min version for syslog";
              }
            }
            description
              "Min TLS version";
          }
          leaf max-version {
            type enumeration {
              enum tls1.0 {
                value 100;
                status deprecated;
                description
                  "Set TLSv1.0 to be used as max version for syslog, TLSv1.0 is deprecated from 25.3.1";
              }
              enum tls1.1 {
                value 101;
                status deprecated;
                description
                  "Set TLSv1.1 to be used as max version for syslog, TLSv1.1 is deprecated from 25.3.1";
              }
              enum tls1.2 {
                value 102;
                description
                  "Set TLSv1.2 to be used as max version for syslog";
              }
              enum tls1.3 {
                value 103;
                description
                  "Set TLSv1.3 to be used as max version for syslog";
              }
            }
            description
              "Max TLS version";
          }
        }
      }
    }
    container archive {
      description
        "logging to a persistent device(disk/harddisk)";
      container device {
        description
          "Configure the archive device";
        choice DEVICE {
          description
            "Configure the archive device";
          case DISK0 {
            leaf disk0 {
              type empty;
              description
                "Use disk0 as the archive device";
            }
          }
          case DISK1 {
            leaf disk1 {
              type empty;
              description
                "Use disk1 as the archive device";
            }
          }
          case HARDDISK {
            leaf harddisk {
              type empty;
              description
                "Use harddisk as the archive device";
            }
          }
        }
      }
      leaf frequency {
        type enumeration {
          enum daily {
            value 2;
            description
              "Collect log in files on a daily basis";
          }
          enum weekly {
            value 1;
            description
              "Collect log in files on a weekly basis";
          }
        }
        description
          "The collection interval for logs";
      }
      leaf file-size {
        type uint32 {
          range "1..2047" {
            description
              "Size in MB";
          }
        }
        description
          "The maximum file size for a single log file.";
      }
      leaf archive-size {
        type uint32 {
          range "1..2047" {
            description
              "Size in MB";
          }
        }
        description
          "The total size of the archive";
      }
      leaf archive-length {
        type uint32 {
          range "1..256" {
            description
              "Number of weeks";
          }
        }
        description
          "The maximum no of weeks of log to maintain";
      }
      leaf severity {
        type enumeration {
          enum alerts {
            value 1;
            description
              "Immediate action needed           (severity=1)";
          }
          enum critical {
            value 2;
            description
              "Critical conditions               (severity=2)";
          }
          enum debugging {
            value 7;
            description
              "Debugging messages                (severity=7)";
          }
          enum emergencies {
            value 0;
            description
              "System is unusable                (severity=0)";
          }
          enum errors {
            value 3;
            description
              "Error conditions                  (severity=3)";
          }
          enum informational {
            value 6;
            description
              "Informational messages            (severity=6)";
          }
          enum notifications {
            value 5;
            description
              "Normal but significant conditions (severity=5)";
          }
          enum warning {
            value 4;
            description
              "Warning conditions                (severity=4)";
          }
        }
        description
          "severity of remote host";
      }
      leaf threshold {
        type uint32 {
          range "1..99" {
            description
              "Threshold percent";
          }
        }
        description
          "The size threshold at which a syslog is generated";
      }
    }
    container vrfs {
      description
        "VPN Routing/Forwarding instance name";
      list vrf {
        must 'ipv4-hostnames or ipv6-hostnames or hostnames';
        key "vrf-name";
        description
          "VPN Routing/Forwarding instance name";
        leaf vrf-name {
          type xr:Cisco-ios-xr-string {
            length "1..32" {
              description
                "VPN Routing/Forwarding instance name";
            }
          }
          description
            "VPN Routing/Forwarding instance name";
        }
        container ipv4-hostnames {
          description
            "IPv4 of the logging host";
          list ipv4-hostname {
            must 'severity or port or operator or facility or source-address';
            key "ipv4-address";
            description
              "IPv4 of the logging host";
            leaf ipv4-address {
              type inet:ipv4-address-no-zone;
              description
                "IP v4/v6 address of the logging host";
            }
            uses HOSTNAME-OPTIONS;
          }
        }
        container ipv6-hostnames {
          description
            "IPv6 of the logging host";
          list ipv6-hostname {
            must 'severity or port or operator or facility or source-address';
            key "ipv6-address";
            description
              "IPv6 of the logging host";
            leaf ipv6-address {
              type inet:ipv6-address-no-zone;
              description
                "IP v4/v6 address of the logging host";
            }
            uses HOSTNAME-OPTIONS;
          }
        }
        container hostnames {
          description
            "Name of the logging host";
          list hostname {
            must 'severity or port or operator or facility or source-address';
            key "host";
            description
              "Name of the logging host";
            leaf host {
              type string {
                length "1..32" {
                  description
                    "Name of the logging host";
                }
                pattern '[a-zA-Z0-9._-]+';
              }
              description
                "Name of the logging host";
            }
            uses HOSTNAME-OPTIONS;
          }
        }
      }
    }
  }
}
