module srl_nokia-load-balancing {
  yang-version 1.1;
  namespace "urn:nokia.com:srlinux:linux:load-balancing";
  prefix srl_nokia-lb;

  import srl_nokia-extensions {
    prefix srl_nokia-ext;
  }
  import srl_nokia-system {
    prefix srl-system;
  }
  import srl_nokia-features {
    prefix srl_nokia-feat;
  }
  import srl_nokia-common {
    prefix srl_nokia-comm;
  }

  organization
    "Nokia";
  contact
    "Nokia SR Linux Support
     Web: <http://www.nokia.com>";
  description
    "This module defines configuration and operational state data related to ECMP and other load-balancing options.";

  revision 2025-03-31 {
    description
      "SRLinux 2025.3.1";
  }
  revision 2024-10-31 {
    description
      "SRLinux 24.10.1";
  }
  revision 2024-07-31 {
    description
      "SRLinux 24.7.1";
  }
  revision 2023-10-31 {
    description
      "SRLinux 23.10.1";
  }
  revision 2023-07-31 {
    description
      "SRLinux 23.7.1";
  }
  revision 2022-11-30 {
    description
      "SRLinux 22.11.1";
  }
  revision 2022-03-31 {
    description
      "SRLinux 22.3.1";
  }
  revision 2021-11-30 {
    description
      "SRLinux 21.11.1";
  }
  revision 2021-06-30 {
    description
      "SRLinux 21.6.1";
  }
  revision 2019-11-30 {
    description
      "SRLinux 19.11.1";
  }

  grouping generic-load-balancing {
    container load-balancing {
      if-feature "srl_nokia-feat:load-balancing";
      description
        "Adjust system-wide ECMP load balancing options.";
      container hash-options {
        if-feature "not srl_nokia-feat:fpcx";
        must 'destination-address = source-address' {
          error-message "Destination address and source address hashing cannot be set differently on this platform";
          srl_nokia-ext:if-feature "srl_nokia-features:ixr-dnx";
        }
        must 'destination-port = source-port' {
          error-message "Destination address and source port hashing cannot be set differently on this platform";
          srl_nokia-ext:if-feature "srl_nokia-features:ixr-dnx";
        }
        description
          "Container for packet header fields and other inputs used in hashing calculations";
        leaf hash-seed {
          type union {
            type uint16;
            type enumeration {
              enum generate-from-mac;
            }
          }
          default "generate-from-mac";
          description
            "The hash seed to use for random selection of ECMP/LAG members

             To avoid polarization effects, directly-connected nodes should have unique hash-seeds. This can be achieved through explicit configuration of the hash-seed, or using the generate-from-mac option (which is the default), and checking that the auto-generated hash-seed is in fact unique (by reading the state value of this leaf).";
        }
        leaf destination-address {
          description
            "Include the destination IP address in the hash calculation";
          type boolean;
          default "true";
        }
        leaf destination-port {
          description
            "Include the destination TCP/UDP port number in the hash calculation if the packet is an unfragmented IP packet carrying a TCP/UDP payload";
          type boolean;
          default "true";
        }
        leaf ipv6-flow-label {
          description
            "Include the IPv6 flow label in the hash calculation if the packet is an IPv6 packet

             It is expected that the IPv6 flow label value is written by the server or other host originating the flow and not changed by any intermediate switch or router.";
          type boolean;
          default "false";
        }
        leaf protocol {
          description
            "Include the IP protocol number in the hash calculation. For an IPv6 packet this is protocol value in the next-header field of the last extension header.";
          type boolean;
          default "true";
        }
        leaf source-address {
          description
            "Include the source IP address in the hash calculation";
          type boolean;
          default "true";
        }
        leaf source-port {
          description
            "Include the source TCP/UDP port number in the hash calculation if the packet is an unfragmented IP packet carrying a TCP/UDP payload";
          type boolean;
          default "true";
        }
        leaf vlan {
          if-feature "srl_nokia-feat:trident3 or srl_nokia-feat:trident4 or srl_nokia-feat:tomahawk3 or srl_nokia-feat:tomahawk4";
          description
            "Include the received VLAN ID in the hash calculation";
          type boolean;
          default "true";
        }
        leaf mpls-label-stack {
          description
            "Include the received labels (terminated and non-terminated) in the hash calculation";
          type boolean;
          default "false";
        }
      }
      list hash-profile {
        if-feature "srl_nokia-feat:system-hash-profile";
        key "name";
        description
          "List of user configured hash profiles";
        leaf name {
          description
            "The name of the user-configured hash profile";
          type srl_nokia-comm:name;
        }
        leaf hash-seed {
          type uint16;
          description
            "The hash seed to use for random selection of ECMP/LAG members

             To avoid polarization effects, directly-connected nodes should have unique hash-seeds.";
          mandatory true;
        }
      }
      leaf lsr-profile {
        description
          "Adjust system-wide LSR ECMP load balancing options.";
        if-feature "srl_nokia-feat:fpcx";
        type enumeration {
          enum label-stack {
            description
              "LSR load balancing based on only the label stack.

               The datapath searches for BoS=1 or up until hash label search depth is reached";
          }
          enum label-eth-or-ip-l4-teid {
            description
              "LSR load balancing based on the label stack and Eth or IP headers

               The datapath performs Eth speculation after BoS=1 or once max label stack depth is reached.
               Irrespective of the outcome of the Eth speculation further attempts IPv4/6 speculation based on first nibble, includes source and destination IP address, followed by UDP/TCP check
               for inclusion of soruce and destination ports and includes GTP/TEID when UDP or TCP port is 2123 or 2152.
               When Ethernet header speculation yields a positive outcome, source and destination MAC together with up to two VLANs are included in the hash";
          }
        }
        default "label-stack";
      }
    }
  }

  augment "/srl-system:system" {
    uses generic-load-balancing;
  }
}
