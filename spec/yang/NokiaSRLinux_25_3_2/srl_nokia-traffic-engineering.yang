module srl_nokia-traffic-engineering {
  yang-version 1.1;
  namespace "urn:nokia.com:srlinux:te:traffic-engineering";
  prefix srl_nokia-te;

  import srl_nokia-common {
    prefix srl_nokia-comm;
  }
  import srl_nokia-network-instance {
    prefix srl_nokia-netinst;
  }
  import srl_nokia-features {
    prefix srl-feat;
  }
  import srl_nokia-interfaces {
    prefix srl_nokia-if;
  }

  organization
    "Nokia";
  contact
    "Nokia SR Linux Support
     Web: <http://www.nokia.com>";
  description
    "Configuration and state related to the use and propagation of TE information.";

  revision 2025-03-31 {
    description
      "SRLinux 2025.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2021-11-30 {
    description
      "SRLinux 21.11.1";
  }
  revision 2021-06-30 {
    description
      "SRLinux 21.6.1";
  }
  revision 2021-03-31 {
    description
      "SRLinux 21.3.1";
  }

  grouping igp-instance-te-advertisement {
    description
      "Container with options for controlling the link-state advertisement of the TE properties of this network instance's TE interfaces";
    leaf advertisement {
      description
        "A setting of false means that no TE-related TLVs and subTLVs should be added to LSAs or LSPs originated by this IGP instance.
         A setting of true means that TE-related TLVs and subTLVs should be added to LSAs or LSPs originated by this IGP instance.";
      type boolean;
      default "false";
      must "(../../../../../srl_nokia-netinst:type = 'srl_nokia-netinst:default') or (../advertisement = false())" {
        error-message "traffic-engineering is only allowed on network-instance of type default";
      }
    }
  }

  grouping tedb-bgp-ls {
    container bgp-ls {
      presence "Install topology and TE information related to this protocol instance into the TE database in a format that supports export as BGP-LS routes.";
      description
        "When present, topology and TE information related to this protocol instance is installed into the TE database in a format that supports export as BGP-LS routes";
      leaf igp-identifier {
        description
          "Unique identifier of the IGP instance that is sent in the BGP-LS NLRI";
        type uint64 {
          range "0..18446744073709551615";
        }
      }
    }
  }

  grouping direct-tedb {
    container te-database-install {
      presence "Install local topology and TE information into the TE database.";
      description
        "When present, local topology and TE information is installed into the TE database";
      must "(../../../srl_nokia-netinst:type = 'srl_nokia-netinst:default')" {
        error-message "traffic-engineering is only allowed on network-instance of type default";
      }
      uses tedb-bgp-ls;
    }
  }

  grouping protocol-instance-tedb {
    container te-database-install {
      presence "Install topology and TE information related to this protocol instance into the TE database.";
      description
        "When present, topology and TE information related to this protocol instance is installed into the TE database";
      must "(../../../../srl_nokia-netinst:type = 'srl_nokia-netinst:default')" {
        error-message "traffic-engineering is only allowed on network-instance of type default";
      }
      uses tedb-bgp-ls {
        if-feature "srl-feat:traffic-engineering-bgpls";
      }
    }
  }

  grouping igp-area-level-tedb {
    leaf bgp-ls-exclude {
      description
        "When set to true, topology and TE information related to this area or level should nkot be imported into the TE database in a format that supports export as BGP-LS routes";
      type boolean;
      must '. = false() or (. = true() and ../../te-database-install/bgp-ls)';
      default "false";
    }
  }

  grouping net-instance-te {
    container traffic-engineering {
      presence "Enable traffic engineering in the network instance.";
      must "../srl_nokia-netinst:type = 'srl_nokia-netinst:default'";
      description
        "Container with traffic engineering options for the network-instance";
      leaf autonomous-system {
        description
          "The autonomous system number of the network-instance, for protocols and pseudo-protocols that do not have their own configuration of AS number.";
        type srl_nokia-comm:as-number;
      }
      leaf ipv4-te-router-id {
        description
          "A routable IPv4 address to identify the router uniquely in a TE domain.";
        type srl_nokia-comm:ipv4-address-unicast;
      }
      leaf ipv6-te-router-id {
        description
          "A routable IPv6 address to identify the router uniquely in a TE domain.";
        type srl_nokia-comm:ipv6-address-unicast-without-local;
      }
      container admin-groups {
        description
          "Container for configuring admin groups";
        list group {
          description
            "List of admin groups defined for this network instance.";
          key "name";
          leaf name {
            description
              "The name of the admin group";
            type srl_nokia-comm:name;
          }
          leaf bit-position {
            mandatory true;
            type uint32 {
              range "0..31";
            }
            description
              "The bit-position value for the admin-group.

               The value for the admin group is an integer that represents one of the bit positions in the admin-group bitmask.";
          }
        }
      }
      container shared-risk-link-groups {
        description
          "Container for configuring SRLGs";
        list group {
          description
            "List of shared risk link groups defined for this network instance.";
          key "name";
          leaf name {
            description
              "The name of the shared risk link group";
            type srl_nokia-comm:name;
          }
          leaf value {
            mandatory true;
            type uint32;
            description
              "Group ID for the SRLG";
          }
        }
      }
      list interface {
        description
          "List of routed subinterfaces that have associated TE information";
        key "interface-name";
        leaf interface-name {
          type srl_nokia-netinst:network-instance-subintf-name;
          description
            "Name of a subinterface";
          must "../interface-ref/interface or not((. = 'system0.0') or (starts-with(., 'lo')))" {
            error-message "Traffic-Engineering config is not allowed on the system0 or a loopback interface";
          }
        }
        container interface-ref {
          description
            "Reference to a subinterface";
          leaf interface {
            type leafref {
              path "/srl_nokia-if:interface/srl_nokia-if:name";
            }
            description
              "Reference to a base interface, for example a port or LAG";
            must '../subinterface >= 0' {
              error-message "subinterface must be configured when interface is set";
            }
            must "not((. = 'system0') or (starts-with(., 'lo')))" {
              error-message "Traffic-Engineering config is not allowed on the system0 or a loopback interface";
            }
          }
          leaf subinterface {
            type leafref {
              path "/srl_nokia-if:interface[srl_nokia-if:name=current()/../interface]/srl_nokia-if:subinterface/srl_nokia-if:index";
            }
            description
              "Reference to a subinterface

               This requires the base interface to be specified using the interface leaf in this container.";
            must '../interface' {
              error-message "interface must be configured when subinterface is set";
            }
          }
        }
        leaf-list admin-group {
          description
            "The list of admin-groups generically associated with the interface (not application specific)";
          type leafref {
            path "../../admin-groups/group/name";
          }
        }
        leaf-list srlg-membership {
          description
            "The list of srlgs generically associated with the interface (not application specific)";
          type leafref {
            path "../../shared-risk-link-groups/group/name";
          }
        }
        leaf te-metric {
          description
            "The TE metric associated with the interface (not application specific)";
          type uint32 {
            range "1..16777215";
          }
        }
      }
      container bgp-ls {
        if-feature "srl-feat:traffic-engineering-bgpls";
        container export {
          leaf reachable-ls-only {
            description
              "Export only link state information from a node that is reachable";
            type boolean;
            default "true";
          }
        }
      }
    }
  }

  augment "/srl_nokia-netinst:network-instance" {
    if-feature "srl-feat:traffic-engineering";
    uses net-instance-te;
  }

  augment "/srl_nokia-netinst:network-instance/srl_nokia-netinst:protocols/srl_nokia-netinst:directly-connected" {
    if-feature "srl-feat:traffic-engineering-bgpls-directly-connected";
    uses direct-tedb;
  }
}
