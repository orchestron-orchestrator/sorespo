module srl_nokia-interfaces {
  yang-version 1.1;
  namespace "urn:nokia.com:srlinux:chassis:interfaces";
  prefix srl_nokia-if;

  import srl_nokia-common {
    prefix srl_nokia-comm;
  }
  import srl_nokia-features {
    prefix srl_nokia-feat;
  }
  import srl_nokia-if-ip {
    prefix srl_nokia-if-ip;
  }
  import srl_nokia-extensions {
    prefix srl_nokia-ext;
  }
  import srl_nokia-interfaces-bridge-table {
    prefix srl_nokia-if-bt;
  }
  import srl_nokia-platform-lc {
    prefix srl_nokia-lc;
  }
  import srl_nokia-platform {
    prefix srl_nokia-plat;
  }
  import srl_nokia-system {
    prefix srl_nokia-sys;
  }
  import srl_nokia-load-balancing {
    prefix srl_nokia-lb;
  }

  organization
    "Nokia";
  contact
    "Nokia SR Linux Support
     Web: <http://www.nokia.com>";
  description
    "Model for managing network interfaces and subinterfaces.

     This model reuses data items defined in the IETF YANG model for
     interfaces described by RFC 7223";

  revision 2025-03-31 {
    description
      "SRLinux 2025.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  identity si-type {
    description
      "Base type for subinterface types";
  }

  identity routed {
    base si-type;
    description
      "Indicates subinterface is used in a routed context";
  }

  identity bridged {
    if-feature "srl_nokia-feat:bridged";
    base si-type;
    description
      "Indicates subinterface is used in a bridged context";
  }

  identity local-mirror-dest {
    if-feature "srl_nokia-feat:mirroring";
    base si-type;
    description
      "Indicates subinterface is used in a mirroring destination SPAN context";
  }

  identity transceiver-functional-type {
    description
      "Base type for transceiver functional types";
  }

  identity standard {
    base transceiver-functional-type;
    description
      "indicates transceiver supports standard optics";
  }

  identity digital-coherent-optics {
    if-feature "srl_nokia-feat:digital-coherent-optics";
    base transceiver-functional-type;
    description
      "Indicates transceiver supports digital coherent optics";
  }

  identity optical-line-system {
    if-feature "srl_nokia-feat:optical-line-system";
    base transceiver-functional-type;
    description
      "Indicates transceiver is a QSFP-DD-LS Amplifier

       These are used to multiplex and amplify coherent optical signals and do not themselves support Ethernet interfaces.";
  }

  typedef port-oper-down-reason {
    type enumeration {
      enum port-admin-disabled;
      enum mda-admin-disabled;
      enum transceiver-oper-down;
      enum port-not-present;
      enum mda-not-present;
      enum phy-initializing;
      enum lower-layer-down;
      enum auto-negotiation-mismatch;
      enum port-mtu-resource-exceeded;
      enum unsupported-speed;
      enum unsupported-fec;
      enum other;
      enum fabric-availability;
      enum no-active-links;
      enum min-link-threshold;
      enum port-9-12-speed-mismatch;
      enum lag-resource-exceeded;
      enum lag-member-resource-exceeded;
      enum standby-signaling;
      enum interface-hold-time-up-active;
      enum interface-reload-timer-active;
      enum connector-down;
      enum event-handler;
      enum unsupported-breakout-port;
      enum cfm-ccm-defect;
      enum crc-monitor-fail-threshold;
      enum symbol-monitor-fail-threshold;
      enum link-loss-forwarding;
      enum storm-control-action;
      enum unsupported-num-channels-for-speed;
    }
  }

  typedef subif-oper-down-reason {
    type enumeration {
      enum admin-disabled;
      enum port-down;
      enum ip-mtu-resource-exceeded;
      enum mpls-mtu-resource-exceeded;
      enum ip-mtu-too-large;
      enum mpls-mtu-too-large;
      enum l2-mtu-too-large;
      enum no-ip-config;
      enum ip-mtu-larger-than-oper-mac-vrf-mtu;
      enum irb-mac-address-not-programmed;
      enum missing-xdp-state;
      enum no-underlay-egress-next-hop-resources;
      enum cfm-ccm-defect;
      enum no-irb-hardware-resources;
      enum other;
    }
  }

  typedef transceiver-oper-state {
    type enumeration {
      enum up;
      enum down;
    }
  }

  typedef transceiver-oper-down-reason {
    type enumeration {
      enum not-present;
      enum read-failure;
      enum checksum-failure;
      enum unknown-transceiver;
      enum tx-laser-disabled;
      enum unsupported-breakout;
      enum port-disabled;
      enum connector-transceiver-down;
      enum unsupported-operational-mode;
      enum no-tunable-config;
      enum ols-link-not-established;
      enum functional-type-mismatch;
    }
  }

  typedef oper-fec-type {
    type enumeration {
      enum disabled {
        description
          "No FEC is active on the host interface";
      }
      enum cl74-baser {
        description
          "An early form of FEC used with 25G interfaces

           Not very strong performance - cl108-rs528 is preferred.  cl74-baser should only be used if the far end doesn't support cl108-rs528";
      }
      enum cl108-rs528 {
        description
          "IEEE 802.3 Clause 108 using RS(528,514)

           IEEE defines this as mandatory for 25G interfaces";
      }
      enum cl91-rs528 {
        description
          "IEEE 802.3 Clause 91 using RS(528,514)

           IEEE defines this as an option for 100G interfaces using NRZ";
      }
      enum cl91-rs544 {
        description
          "IEEE 802.3 Clause 91 using RS(544,514)

           IEEE defines this as mandatory for 100G interfaces using PAM4";
      }
      enum cl119-rs544 {
        description
          "IEEE 802.3 Clause 119 using RS(544,514)

           IEEE defines this as mandatory for 200G and 400G interfaces";
      }
      enum cl134-rs544 {
        description
          "IEEE 802.3 Clause 134 using RS(544,514)

           IEEE defines this as mandatory for 50G interfaces";
      }
    }
    description
      "Enumerations of fec options for a STANDARD Ethernet interface

       Only a subset of these are configurable.";
  }

  typedef interface-id {
    type string;
    description
      "User-defined identifier for an interface

       This is generally used to name a interface reference. The id can be arbitrary but a useful convention is to use a combination of base interface name and subinterface index.";
  }

  typedef loopback-mode-type {
    type enumeration {
      enum none {
        description
          "No loopback is applied";
      }
      enum facility {
        if-feature "srl_nokia-feat:loopback-mode-facility";
        description
          "A loopback which directs traffic received from an external source on the port back out the transmit side of the same port.";
      }
      enum terminal {
        if-feature "srl_nokia-feat:loopback-mode-terminal";
        description
          "A loopback which directs traffic normally transmitted on the port back into the switch as if received on the same
           port from an external source

           On some systems this is also called local loopback.";
      }
    }
    description
      "Loopback modes for physical ports";
  }

  typedef ethernet-monitor-report-status {
    type enumeration {
      enum none {
        value 0;
      }
      enum sd-threshold-exceeded {
        value 1;
      }
      enum sf-threshold-exceeded {
        value 2;
      }
    }
  }

  grouping subinterface-delay {
    container unidirectional-link-delay {
      if-feature "srl_nokia-feat:traffic-engineering or srl_nokia-feat:link-measurement";
      description
        "Unidirectional link delay configuration and state related to subinterface";
      leaf static-delay {
        if-feature "srl_nokia-feat:traffic-engineering";
        type union {
          type int32 {
            range "1..16777215";
          }
          type enumeration {
            enum none {
              value -1;
            }
          }
        }
        units "microseconds";
        default "none";
        description
          "A statically configured unidirectional delay value that can be advertised as an interface attribute by an IGP";
        must "(string(.) = 'none') or (starts-with(../../../srl_nokia-if:name, 'ethernet') or starts-with(../../../srl_nokia-if:name, 'lag'))" {
          error-message "static-delay is supported for ethernet and lag interfaces only";
        }
      }
      leaf last-reported-dynamic-delay {
        if-feature "srl_nokia-feat:link-measurement";
        config false;
        type union {
          type int32 {
            range "0..2147483647";
          }
          type enumeration {
            enum none {
              value -1;
            }
          }
        }
        units "microseconds";
        description
          "Indicates the last delay measurement reported to the routing engine";
      }
    }
  }

  grouping interface-common-config {
    description
      "Configuration data nodes common to physical interfaces and subinterfaces";
    leaf description {
      type srl_nokia-comm:description;
      description
        "A user-configured description of the interface";
      reference
        "RFC 2863: The Interfaces Group MIB - ifAlias";
    }
  }

  grouping interface-phys-config {
    description
      "Configuration data for physical interfaces";
    uses interface-common-config;
    leaf admin-state {
      srl_nokia-ext:show-importance "high";
      type srl_nokia-comm:admin-state;
      default "enable";
      description
        "The configured, desired state of the interface";
      reference
        "RFC 2863: The Interfaces Group MIB - ifAdminStatus";
      must "((. = 'enable') and starts-with(../srl_nokia-if:name, 'system0')) or not(starts-with(../srl_nokia-if:name, 'system0'))" {
        error-message "admin-state must be enable";
      }
    }
    leaf num-physical-channels {
      if-feature "srl_nokia-feat:num-physical-channels";
      type uint8 {
        range "1..8";
      }
      description
        "Sets the number of lanes or physical channels assigned to this interface or to the set of interfaces within this breakout group

         This leaf can be used to distinguish between transceivers that provide the same port-speed or breakout-configuration but using different PMAs.
         For example, if a port supports two transceivers providing 100G optical signal but one uses CAUI4 and the other uses 100GAUI-2, then this leaf
         can be set to 4 for the CAUI4 transceiver and 2 for the 100GAUI-2 transceiver.
         Similarly, a transceiver that provides a breakout of 4 ports of 100G using 4 x 100GAUI2 would set this leaf to 8 but a transceiver using 4 x 100GAUI-1 would have this leaf set to 4.

         If not set, then the default shall be as follows:
            1 is used for 10G, 25G
            2 is used for 50G
            4 is used for 40G, 100G, 2x50G, 1x100G, 4x10G, 4x25G
            6 is used for 3x100G (digital coherent optics)
            8 is used for 200G, 400G, 800G, 2x100G, 4x100G, 8x50G
        ";
    }
    container breakout-mode {
      if-feature "srl_nokia-feat:port-breakout";
      presence "Configures the connector for breakout mode";
      must 'starts-with(../srl_nokia-if:name, "ethernet")' {
        error-message "Breakout not supported for this port type";
      }
      description
        "Configuration of breakout options.

         7220 D3 ports 3-33: 4x10G and 4x25G
         7220 D3L ports 1-31: 2x50G, 4x10G and 4x25G
         7220 H3 ports 3-34: 4x10G, 2x100G/4x100G, and 2x200G
         7220 H4 ports 1-64: 4x100G and 2x200G
         7220 H4-32D ports 1-32: 2x100G/4x100G and 2x200G
         7220 H5-64D ports 1-32: 2x50G, 8x50G, 2x100G/4x100G/8x100G and 2x400G
         7220 H5-64D ports 33-64: 2x50G, 2x100G and 2x400G
         7220 D4 ports 29-32: 4x100G, 4x25G, and 4x10G
         7220 D4 ports 9, 23-27: 4x25G and 4x10G
         7220 D5 ports 1-32: 4x10G, 4x25G, 2x100G/4x100G, and 2x200G
         7730 SXR-1d-32D QSFP28 ports 1-16, 21-32: 4x10G and 4x25G (Note 3)
         7730 SXR-1d-32D QSFPDD ports 17-20: 4x100G, 3x100G (Note 1), 4x25G, and 4x10G
         7730 SXR-1x-44S SFPDD ports 1-20, 23-42: No breakouts
         7730 SXR-1x-44S QSFPDD ports 21,22,43,44: 4x100G, 3x100G (Note 1), 4x25G, and 4x10G
         7250 IXR-6e/10e 60p QSFP28 IMM ports: 9,12,15,18,21,24,26,27,29,30,32,33,35,36,38,39,41,42,45,48: 4x25G and 4x10G (Note 2)
         7250 IXR-6e/10e 36p QSFPDD IMM all ports: 4x100G, 2x100G, 4x25G, and 4x10G
         7250 IXR-6e/10e/18e 36p QSFP112-DD IMM all ports: 2x400G, 4x100G, 3x100G (Note 1), 2x100G, 4x25G
         7250 IXR-X1b QSFP28 ports 1-24: 4x25G, and 4x10G (Note 4)
         7250 IXR-X1b QSFPDD ports 25-36: 4x100G, 3x100G (Note 1), 2x100G (Note 1), 1x100G (Note 1), 4x25G, and 4x10G
         7250 IXR-X3b QSFPDD all ports: 4x100G, 3x100G (Note 1), 2x100G (Note 1), 1x100G (Note 1), 4x25G, and 4x10G
         Note 1: 3x100G, 2x100G, 1x100G is only supported for Digital Coherent Optic transceivers

         Note 2: For the following port groupings only the higher numbered port supports breakout-mode.
                 If the higher numbered port is to be configured for breakout-mode, then the lower numbered port should not be configured.
                 If both ports are configured, then the lower numbered port takes precedence and the higher numbered port shall be operationally down with reason unsupported-breakout-port.
                 Groupings are (8,9), (11,12), (14,15), (17,18), (20,21), (23,24), (44, 45), (47,48).

         Note 3: Breakout and 40G is only supported on odd numbered ports.
                 For the QSFP28 four port groupings [1-4], [5-8], [9-12], [13-16], [21-24], [25-28], and [29-32] if either of the odd numbered ports within a group is configured for 40G, 4x10G, or 4x25G,
                 then the other odd numbered port in the same group may only be configured if it is configured for one of 40G, 4x10G, or 4x25G (can differ between the odd ports) and neither of
                 the two even numbered ports within the same group can be configured.

         Note 4: For the QSFP28 ports, the following port groups exist [n, n+1, n+2, n+3] for n = 1, 5, 9, 13, 17, 21.  Breakout for 4x25G or 4x10G is only supported on ports n+1 and n+3.
                 When initially configuring a port with a breakout configuration or port speed that does not already exist on another configured port within the same group, then a link flap and traffic hit may occur on other ports within the same group.
                 When the breakout configuration or port speed is changed for a port in a group, then a link flap and traffic hit may occur on other ports within the same group.
                 If port n+1 within the group is configured for breakout, then port n cannot be configured.
                 In addition if port n+1 is configured for breakout and port n+3 is configured without breakout, then port n+2 may only be configured with the same speed as port n+3.
                 If port n+3 within the group is configured for breakout, then port n+2 cannot be configured.
                 In addition if port n+3 is configured for breakout and port n+1 is configured without breakout, then port n may only be configured with the same speed as port n+1.

         Port Groups and auto-configuration of port speed:
          Manually configured breakout-mode takes precedence over the auto-configured port-speed.  This means that configuring a port within a port-group can have a side effect to take down an operational port that had its speed set based on the auto configuration feature.  If there is risk of mixing transceiver types within a port group, then it is recommended to always manually configure the ports";
      leaf num-breakout-ports {
        description
          "The number of breakout ports supported by this connector";
        type enumeration {
          enum 1 {
            if-feature "srl_nokia-feat:breakout-ports-1";
          }
          enum 2 {
            if-feature "srl_nokia-feat:breakout-ports-2";
          }
          enum 3 {
            if-feature "srl_nokia-feat:breakout-ports-3";
          }
          enum 4 {
            if-feature "srl_nokia-feat:breakout-ports-4";
          }
          enum 8 {
            if-feature "srl_nokia-feat:breakout-ports-8";
          }
        }
        must "not((. = '1') and ../breakout-port-speed != '100G')" {
          error-message "breakout-port-speed must be 100G when num-breakout-ports is 1";
        }
        must "not((. = '3') and ../breakout-port-speed != '100G')" {
          error-message "breakout-port-speed must be 100G when num-breakout-ports is 3";
        }
        must "not((. = '1') and ../../transceiver/functional-type != 'digital-coherent-optics')" {
          error-message "transceiver functional-type must be digital-coherent-optics when breakout-port-speed is 100G and num-breakout-ports is 1";
        }
        must "not((. = '3') and ../../transceiver/functional-type != 'digital-coherent-optics')" {
          error-message "transceiver functional-type must be digital-coherent-optics when breakout-port-speed is 100G and num-breakout-ports is 3";
        }
        must "not((. = '8') and ../../transceiver/functional-type = 'digital-coherent-optics')" {
          error-message "transceiver functional-type must not be digital-coherent-optics when num-breakout-ports is 8";
        }
        mandatory true;
      }
      leaf breakout-port-speed {
        description
          "The speed of each breakout port";
        type enumeration {
          enum 1G {
            if-feature "srl_nokia-feat:breakout-speed-1G";
          }
          enum 10G {
            if-feature "srl_nokia-feat:breakout-speed-10G";
          }
          enum 25G {
            if-feature "srl_nokia-feat:breakout-speed-25G";
          }
          enum 50G {
            if-feature "srl_nokia-feat:breakout-speed-50G";
          }
          enum 100G {
            if-feature "srl_nokia-feat:breakout-speed-100G";
          }
          enum 200G {
            if-feature "srl_nokia-feat:breakout-speed-200G";
          }
          enum 400G {
            if-feature "srl_nokia-feat:breakout-speed-400G";
          }
        }
        must "not((. = '10G') and ../../transceiver/functional-type = 'digital-coherent-optics')" {
          error-message "digital-coherent-optics do not support 10G breakout-port-speed";
        }
        must "not((. = '25G') and ../../transceiver/functional-type = 'digital-coherent-optics')" {
          error-message "digital-coherent-optics do not support 25G breakout-port-speed";
        }
        must "not((. = '50G') and ../../transceiver/functional-type = 'digital-coherent-optics')" {
          error-message "digital-coherent-optics do not support 50G breakout-port-speed";
        }
        must "not((. = '200G') and ../../transceiver/functional-type = 'digital-coherent-optics')" {
          error-message "digital-coherent-optics do not support 200G breakout-port-speed";
        }
        must "not((. = '400G') and ../../transceiver/functional-type = 'digital-coherent-optics')" {
          error-message "digital-coherent-optics do not support 400G breakout-port-speed";
        }
        mandatory true;
      }
    }
    leaf mtu {
      type uint16 {
        range "1450..9500";
      }
      units "bytes";
      description
        "Port MTU in bytes including ethernet overhead but excluding 4-bytes FCS

         If a transmitted packet exceeds this size it is dropped.
         The default value for ethernet-x interfaces is taken from /system/mtu/default-port-mtu. For the mgmt0 and mgmt0-standby interfaces the default is 1514 bytes, but the value can be changed for each interface individually.
         Port MTU is not configurable for loopback interfaces or irb interfaces. For irb interfaces, if the size of the ip packets to be routed to a mac-vrf has to be restricted, the subinterface.ip-mtu should be configured instead.
         The max mtu for the mgmt0 and mgmt0-standby interfaces is 9216.
         The 7220 IXR-D1, 7220 IXR-D2, 7220 IXR-D3, 7220 IXR-D4, 7220 IXR-D5, 7220 IXR-H2, 7220 IXR-H3, and 7220 IXR-H4 systems support a maximum port MTU of 9412 bytes and minimum of 1500 bytes.
         The VSRL system supports a maximum port MTU of 9500 and minimum of 1450 bytes.
         The 7730 SXR systems support a maximum port MTU of 9408 bytes and minimum of 1500 bytes.
         All other systems support a maximum port MTU of 9500 and minimum of 1500 bytes.
         Each 7250 IXR IMM supports a maximum of 8 different port MTU values. 7220 IXR systems do not have any limit on the maximum number of different port MTU values.";
      must 'not(../breakout-mode)' {
        error-message "mtu not configurable when breakout-mode is enabled";
      }
      must 'starts-with(../srl_nokia-if:name, "lif") or starts-with(../srl_nokia-if:name, "vhn") or (. >= 1500)' {
        error-message "minimum mtu is 1500 for this interface type";
      }
      must "(not (starts-with(../srl_nokia-if:name, 'mgmt'))) or (. <= 9216)" {
        error-message "mtu max is 9216 for mgmt interface";
      }
    }
    leaf loopback-mode {
      if-feature "not srl_nokia-feat:platform-vsrl";
      description
        "Loopback mode of the port";
      type loopback-mode-type;
      must "(starts-with(../srl_nokia-if:name, 'ethernet'))" {
        error-message "physical loopback not supported on this interface";
      }
      must 'not(../breakout-mode)' {
        error-message "loopback-mode not configurable when breakout-mode is enabled";
      }
    }
    leaf swap-src-dst-mac {
      if-feature "srl_nokia-feat:loopback-mode-facility";
      type boolean;
      default "false";
      description
        "Enable swapping source and destination MAC addresses";
      must ". = false() or ../loopback-mode = 'facility'" {
        error-message "MAC SWAP is only supported when interface loopback mode is facility";
      }
      must "not(../loopback-mode = 'facility') or . = true()" {
        srl_nokia-ext:if-feature "not srl_nokia-features:fpcx";
        error-message "MAC SWAP must be true when interface loopback mode is facility";
      }
    }
  }

  grouping sflow-sampling-rate-config {
    leaf ingress-sampling-rate {
      if-feature "srl_nokia-feat:sflow-interface-sampling";
      type uint32 {
        range "0..2000000";
      }
      must 'starts-with(../../srl_nokia-if:name, "ethernet")' {
        error-message "sFlow Ingress packet sampling is supported only on ethernet interfaces.";
      }
      must 'not(../../breakout-mode)' {
        error-message "sFlow Ingress packet sampling is not supported when breakout-mode is enabled.";
      }
      description
        "Specify sFlow Ingress packet sample rate.
         This value is the rate at which traffic will be sampled at a rate of 1:N received packets.";
    }
    leaf egress-sampling-rate {
      if-feature "srl_nokia-feat:sflow-interface-sampling";
      type uint32 {
        range "0..2000000";
      }
      must 'starts-with(../../srl_nokia-if:name, "ethernet")' {
        error-message "sFlow Egress packet sampling is supported only on ethernet interfaces.";
      }
      must 'not(../../breakout-mode)' {
        error-message "sFlow Egress packet sampling is not supported when breakout-mode is enabled.";
      }
      description
        "Specify sFlow Egress packet sample rate.
         This value is the rate at which traffic will be sampled at a rate of 1:N received packets.";
    }
  }

  grouping interface-sflow-config {
    description
      "Container for sFlow configuration applied at the interface level";
    container sflow {
      if-feature "srl_nokia-feat:sflow";
      presence "Configures the Sflow parameters at interface level";
      description
        "Context to configure sFlow parameters";
      leaf admin-state {
        type srl_nokia-comm:admin-state;
        must 'starts-with(../../srl_nokia-if:name, "ethernet") or starts-with(../../srl_nokia-if:name, "lag") or (../admin-state = "disable")' {
          srl_nokia-ext:if-feature "srl_nokia-features:sflow-lag";
          error-message "sFlow collector is supported only on ethernet or LAG interfaces.";
        }
        must 'starts-with(../../srl_nokia-if:name, "ethernet") or (../admin-state = "disable")' {
          srl_nokia-ext:if-feature "not srl_nokia-features:sflow-lag";
          error-message "sFlow collector is supported only on ethernet interfaces.";
        }
        must 'not(../../breakout-mode) or (../admin-state = "disable")' {
          error-message "sFlow collector is not supported when breakout-mode is enabled.";
        }
        description
          "Administratively enable or disable sFlow on this interface";
      }
      uses sflow-sampling-rate-config;
    }
  }

  grouping power-levels {
    container input-power {
      if-feature "not srl_nokia-feat:platform-vsrl";
      config false;
      leaf latest-value {
        type decimal64 {
          fraction-digits 2;
        }
        description
          "The current value of the optical Rx power in dBm";
      }
      leaf high-alarm-condition {
        type boolean;
        description
          "High alarm threshold condition.

           Set to true whenever the Rx power is above the high-alarm-threshold and set to false whenever the Rx power is below the high-alarm-threshold";
      }
      leaf high-alarm-threshold {
        type decimal64 {
          fraction-digits 2;
        }
        description
          "High alarm threshold.

           Read from the installed transceiver";
      }
      leaf low-alarm-condition {
        type boolean;
        description
          "Low alarm threshold condition.

           Set to true whenever the Rx power is below the low-alarm-threshold and set to false whenever the Rx power is above the low-alarm-threshold";
      }
      leaf low-alarm-threshold {
        type decimal64 {
          fraction-digits 2;
        }
        description
          "Low alarm threshold condition.

           Read from the installed transceiver";
      }
      leaf high-warning-condition {
        type boolean;
        description
          "High warning threshold condition.

           Set to true whenever the Rx power is above the high-warning-threshold and set to false whenever the Rx power is below the high-warning-threshold";
      }
      leaf high-warning-threshold {
        type decimal64 {
          fraction-digits 2;
        }
        description
          "High warning threshold.

           Read from the installed transceiver";
      }
      leaf low-warning-condition {
        type boolean;
        description
          "Low warning threshold condition.

           Set to true whenever the Rx power is below the low-warning-threshold and set to false whenever the Rx power is above the low-warning-threshold";
      }
      leaf low-warning-threshold {
        type decimal64 {
          fraction-digits 2;
        }
        description
          "Low warning threshold.

           Read from the installed transceiver";
      }
    }
    container output-power {
      config false;
      if-feature "not srl_nokia-feat:platform-vsrl";
      leaf latest-value {
        type decimal64 {
          fraction-digits 2;
        }
        description
          "The current value of the optical Tx power in dBm";
      }
      leaf high-alarm-condition {
        type boolean;
        description
          "High alarm threshold condition.

           Set to true whenever the Tx power is above the high-alarm-threshold and set to false whenever the Tx power is below the high-alarm-threshold";
      }
      leaf high-alarm-threshold {
        type decimal64 {
          fraction-digits 2;
        }
        description
          "High alarm threshold.

           Read from the installed transceiver";
      }
      leaf low-alarm-condition {
        type boolean;
        description
          "Low alarm threshold condition.

           Set to true whenever the Tx power is below the low-alarm-threshold and set to false whenever the Tx power is above the low-alarm-threshold";
      }
      leaf low-alarm-threshold {
        type decimal64 {
          fraction-digits 2;
        }
        description
          "Low alarm threshold.

           Read from the installed transceiver";
      }
      leaf high-warning-condition {
        type boolean;
        description
          "High warning threshold condition.

           Set to true whenever the Tx power is above the high-warning-threshold and set to false whenever the Tx power is below the high-warning-threshold";
      }
      leaf high-warning-threshold {
        type decimal64 {
          fraction-digits 2;
        }
        description
          "High warning threshold.

           Read from the installed transceiver";
      }
      leaf low-warning-condition {
        type boolean;
        description
          "Low warning threshold condition.

           Set to true whenever the Tx power is below the low-warning-threshold and set to false whenever the Tx power is above the low-warning-threshold";
      }
      leaf low-warning-threshold {
        type decimal64 {
          fraction-digits 2;
        }
        description
          "Low warning threshold.

           Read from the installed transceiver";
      }
    }
    container laser-bias-current {
      if-feature "not srl_nokia-feat:platform-vsrl";
      config false;
      leaf latest-value {
        type decimal64 {
          fraction-digits 3;
        }
        description
          "The current value of the laser bias current in mA";
      }
      leaf high-alarm-condition {
        type boolean;
        description
          "High alarm threshold condition.

           Set to true whenever the laser bias current is above the high-alarm-threshold and set to false whenever the laser bias current is below the high-alarm-threshold";
      }
      leaf high-alarm-threshold {
        type decimal64 {
          fraction-digits 3;
        }
        description
          "High alarm threshold.

           Read from the installed transceiver";
      }
      leaf low-alarm-condition {
        type boolean;
        description
          "Low alarm threshold condition.

           Set to true whenever the laser bias current is below the low-alarm-threshold and set to false whenever the laser bias current is above the low-alarm-threshold";
      }
      leaf low-alarm-threshold {
        type decimal64 {
          fraction-digits 3;
        }
        description
          "Low alarm threshold.

           Read from the installed transceiver";
      }
      leaf high-warning-condition {
        type boolean;
        description
          "High warning threshold condition.

           Set to true whenever the laser bias current is above the high-warning-threshold and set to false whenever the laser bias current is below the high-warning-threshold";
      }
      leaf high-warning-threshold {
        type decimal64 {
          fraction-digits 3;
        }
        description
          "High warning threshold.

           Read from the installed transceiver";
      }
      leaf low-warning-condition {
        type boolean;
        description
          "Low warning threshold condition.

           Set to true whenever the laser bias current is below the low-warning-threshold and set to false whenever the laser bias current is above the low-warning-threshold";
      }
      leaf low-warning-threshold {
        type decimal64 {
          fraction-digits 3;
        }
        description
          "Low warning threshold.

           Read from the installed transceiver";
      }
    }
  }

  grouping subinterface-config {
    description
      "Configuration data for subinterfaces";
    uses interface-common-config;
    leaf admin-state {
      srl_nokia-ext:show-importance "high";
      type srl_nokia-comm:admin-state;
      default "enable";
      description
        "The configured, desired state of the subinterface";
      reference
        "RFC 2863: The Interfaces Group MIB - ifAdminStatus";
      must "((. = 'enable') and starts-with(../../srl_nokia-if:name, 'system0')) or not(starts-with(../../srl_nokia-if:name, 'system0'))" {
        error-message "admin-state must be enable";
      }
    }
    leaf ip-mtu {
      type uint16 {
        range "1280..9486";
      }
      units "bytes";
      description
        "IP MTU of the subinterface in bytes.

         Includes the IP header but excludes Ethernet encapsulation.

         IP MTU specifies the maximum sized IPv4 or IPv6 packet that can be transmitted on the subinterface. If an IPv4 or IPv6 packet exceeds this size it is dropped and this may result in the generation of an ICMP error message back to the source.

         The default IP MTU for a subinterface is taken from /system/mtu/default-ip-mtu.  For the mgmt0 and mgmt0-standby subinterfaces the default is the associated interface MTU minus the Ethernet encapsulation overhead.

         The IP MTU is not configurable for subinterfaces of loopback interfaces.

         The 7220 IXR-D1, 7220 IXR-D2, 7220 IXR-D3, 7220 IXR-D4, 7220 IXR-D5, 7220 IXR-H2, 7220 IXR-H3, and 7220 IXR-H4 systems support a maximum IP MTU of 9398 bytes.

         The 7730 SXR systems support a maximum IP MTU of 9394 bytes.

         Each 7250 IXR IMM supports a maximum of 4 different IP MTU values. 7220 IXR systems do not have any limit on the maximum number of different IP MTU values.";
      must "not (starts-with(../../srl_nokia-if:name, 'system') or starts-with(../../srl_nokia-if:name, 'lo'))" {
        error-message "ip-mtu not supported on this interface";
      }
      must "(../type != 'srl_nokia-if:bridged') and (../type != 'srl_nokia-if:local-mirror-dest')" {
        error-message "ip-mtu not allowed with type bridged or type local-mirror-dest";
      }
    }
    leaf l2-mtu {
      if-feature "srl_nokia-feat:config-sub-if-l2-mtu";
      type uint16 {
        range "1450..9500";
      }
      units "bytes";
      description
        "Layer-2 MTU of the subinterface in bytes.

         Includes the Ethernet header and VLAN tags, and excludes 4-bytes FCS.

         L2 MTU specifies the maximum sized Ethernet frame that can be transmitted on the subinterface. If a frame exceeds this size it is discarded. If the l2-mtu of the subinterface exceeds the port-mtu of the associated
         interface, the subinterface will remain operationally down.

         The default value for a subinterface is taken from /system/mtu/default-l2-mtu. The L2 MTU is only configurable for bridged subinterfaces.

         The 7220 IXR-D1, 7220 IXR-D2, 7220 IXR-D3, 7220 IXR-D4, 7220 IXR-D5, 7220 IXR-H2, 7220 IXR-H3, and 7220 IXR-H4 systems support a maximum L2 MTU of 9412 bytes and minimum of 1500 bytes.

         The 7730 SXR systems support a maximum L2 MTU of 9408 bytes.

         The VSRL system supports a maximum L2 MTU of 9500 and minimum of 1450 bytes.

         All other systems support a maximum L2 MTU of 9500 and minimum of 1500 bytes.";
      must "../type = 'srl_nokia-if:bridged'" {
        error-message "l2-mtu only allowed with type bridged";
      }
      must 'starts-with(../../srl_nokia-if:name, "lif") or starts-with(../../srl_nokia-if:name, "vhn") or (. >= 1500)' {
        error-message "minimum l2-mtu is 1500 for this interface type";
      }
    }
    leaf mpls-mtu {
      if-feature "srl_nokia-feat:mpls";
      type uint16 {
        range "1284..9496";
      }
      units "bytes";
      description
        "MPLS MTU of the subinterface in bytes, including the transmitted label stack.

         MPLS MTU specifies the maximum sized MPLS packet that can be transmitted on the subinterface. If an MPLS packet containing any payload exceeds this size then it is dropped. If the payload of the dropped packet is IPv4 or IPv6 then this may also result in the generation of an ICMP error message that is either tunneled or sent back to the source.

         The default MPLS MTU for a subinterface is taken from /system/mtu/default-mpls-mtu.

         The MPLS MTU is not configurable for subinterfaces of loopback interfaces.

         The 7730 SXR systems support a maximum MPLS MTU of 9404 bytes.

         Each 7250 IXR IMM supports a maximum of 4 different MPLS MTU values.";
      must "not (starts-with(../../srl_nokia-if:name, 'system') or starts-with(../../srl_nokia-if:name, 'lo') or starts-with(../../srl_nokia-if:name, 'mgmt'))" {
        error-message "mpls-mtu not supported on this interface";
      }
      must "(../type != 'srl_nokia-if:bridged') and (../type != 'srl_nokia-if:local-mirror-dest')" {
        error-message "mpls-mtu not allowed with type bridged or type local-mirror-dest";
      }
    }
  }

  grouping subinterface-top {
    description
      "Subinterface data for logical interfaces associated with a given interface";
    list subinterface {
      max-elements 4095;
      key "index";
      description
        "The list of subinterfaces (logical interfaces) associated with a physical interface";
      leaf index {
        type uint32 {
          range "0..9999";
        }
        description
          "The index of the subinterface, or logical interface number";
        must "((. = 0) and starts-with(../../srl_nokia-if:name, 'system0')) or not(starts-with(../../srl_nokia-if:name, 'system0'))" {
          error-message "subinterface index must be 0 for system0 interface";
        }
        must "not(starts-with(../../srl_nokia-if:name, 'sync0'))" {
          error-message "subinterfaces not supported on sync0 port";
        }
      }
      leaf type {
        type identityref {
          base si-type;
        }
        description
          "Indicates the context in which the ethernet subinterface will be used";
        must "(starts-with(../../srl_nokia-if:name, 'ethernet') or starts-with(../../srl_nokia-if:name, 'lag') or starts-with(../../srl_nokia-if:name, 'lif') or starts-with(../../srl_nokia-if:name, 'enp') or starts-with(../../srl_nokia-if:name, 'vhn'))" {
          error-message "type not supported on this interface";
        }
        must "(. != 'srl_nokia-if:local-mirror-dest') or (starts-with(../../srl_nokia-if:name, 'ethernet') or starts-with(../../srl_nokia-if:name, 'lag'))" {
          error-message "local-mirror-dest is not supported on this interface";
        }
      }
      uses subinterface-config;
      uses subinterface-delay;
      leaf name {
        config false;
        type string;
        description
          "The system assigned name of the subinterface.

           It is formed by taking the base interface name and appending a dot (.) and the subinterface index number. For example, ethernet-2/1.0";
      }
      leaf ifindex {
        config false;
        type uint32;
        description
          "System-wide persistent unique ifIndex assigned to the subinterface";
      }
      leaf oper-state {
        srl_nokia-ext:show-importance "high";
        config false;
        type enumeration {
          enum up;
          enum down;
        }
        description
          "The operational state of the subinterface";
      }
      leaf oper-down-reason {
        config false;
        srl_nokia-ext:show-importance "high";
        type subif-oper-down-reason;
        description
          "The first (and possibly only) reason for the subinterface being operationally down";
      }
      leaf last-change {
        config false;
        type srl_nokia-comm:date-and-time-delta;
        description
          "The date and time of the most recent change to the subinterface state";
      }
      leaf collect-irb-stats {
        if-feature "srl_nokia-feat:subif-detailed-stats-config";
        type boolean;
        description
          "Set to false to disable statistics collection on the IRB subinterface

           By default basic statistics are collected for each IRB subinterface";
        must "starts-with(../../name,'irb')" {
          error-message "Only supported on IRB subinterfaces";
        }
      }
      leaf collect-detailed-stats {
        if-feature "srl_nokia-feat:subif-detailed-stats-config";
        type boolean;
        description
          "Set to false to disable detailed statistics collection on the routed (non IRB) subinterface

           By default detailed statistics are collected for each routed (non IRB) subinterface";
        must "starts-with(../../name,'ethernet') or starts-with(../../name,'lag') and ((../type = 'routed') or not (../type))" {
          error-message "Only supported on routed, non-IRB subinterfaces";
        }
      }
      uses srl_nokia-if-ip:ipv4-top;
      uses srl_nokia-if-ip:ipv6-top;
      uses srl_nokia-if-ip:anycast-gw-top;
      uses srl_nokia-if-ip:subinterface-statistics;
      uses srl_nokia-if-bt:bridge-table-top;
    }
  }

  grouping interface-top {
    description
      "Top-level grouping for interface configuration and operational state data";
    list interface {
      key "name";
      description
        "The list of named interfaces on the device";
      leaf name {
        type srl_nokia-comm:interface-all;
        description
          "The name of the interface

           Valid options are:
           irb<N>, N=0..255
           lif-<lif_name>
           enp<bus>s<dev>f<fn>, bus=0..255, dev=0..31, fn=0..7
           vhn-<vhn_name>
           lag<N>, N=1..1000 [note1]
           lo<N>, N=0..255
           mgmt0
           mgmt0-standby
           ethernet-<slot>/<port>
           ethernet-<slot>/<connector>/<port>
           ethernet-<slot>/m<mda>/<port>
           ethernet-<slot>/m<mda>/<connector>/<port>
           system0
           sync0

           <lif_name>=Linux interface name
           <vhn_name>=vhost interface name
           <slot>=slot number {1,2,3,..}
           <mda>=mda id {1,2,3,..}
           <connector>=connector id {1,2,3,..}
           <port>=port id {1,2,3,..}

           [note1] The maximum number of LAGs per platform is as follows:
            D1: 32 (N must be 1..32)
            D2-D3: 128 (N must be 1..1000)
            D4-D5: 64 (N must be 1..64)
            H2-H3: 127 (N must be 1..127)
            H4-32D: 127 (N must be 1..127)
            H4: 255 (N must be 1..255)
            IXR: 128 (N must be 1..128)
            SXR-1d-32D: 128 (N must be 1..128)
            SXR-1x-44S: 128 (N must be 1..128)
            vSRL: 8 (N must be 1..8)
            A1: 10 (N must be 1..10)
            IXR-X1b: 512 (N must be 1..512)
            IXR-X3b: 512 (N must be 1..512)";
      }
      uses interface-phys-config;
      leaf ifindex {
        config false;
        type uint32;
        description
          "System-wide persistent unique ifIndex assigned to the interface";
      }
      leaf oper-state {
        srl_nokia-ext:show-importance "high";
        config false;
        type enumeration {
          enum up;
          enum down;
          enum testing;
        }
        description
          "The operational state of the interface";
      }
      leaf oper-down-reason {
        config false;
        srl_nokia-ext:show-importance "high";
        type port-oper-down-reason;
        description
          "The first (and possibly only) reason for the port being operationally down";
      }
      leaf last-change {
        config false;
        type srl_nokia-comm:date-and-time-delta;
        description
          "The date and time of the most recent change to the interface state";
      }
      leaf linecard {
        config false;
        type leafref {
          path "/srl_nokia-plat:platform/srl_nokia-lc:linecard/srl_nokia-lc:slot";
        }
        description
          "The linecard on which this interface resides

           This field is not populated for non-forwarding-complex-attached interfaces, for example mgmt0.";
      }
      leaf forwarding-complex {
        config false;
        type leafref {
          path "/srl_nokia-plat:platform/srl_nokia-lc:linecard/srl_nokia-lc:forwarding-complex/srl_nokia-lc:name";
        }
        description
          "The forwarding-complex on which this interface resides

           This field is not populated for non-forwarding-complex-attached interfaces, for example mgmt0.";
      }
      leaf-list phy-group-members {
        if-feature "srl_nokia-feat:platform-7220-d2 or srl_nokia-feat:platform-7730-sxr-1d-32d or srl_nokia-feat:platform-7250-ixr-x1b";
        config false;
        type string;
        description
          "The group of interfaces sharing a phy with this interface

           On the 7220 IXR-D2 and 7220 IXR-D2L platforms this group of interfaces must be set to the same speed, either 1/10G or 25G.";
      }
      leaf-list physical-channel {
        config false;
        description
          "The list of transceiver channels associated with this port";
        type leafref {
          path "/srl_nokia-if:interface/srl_nokia-if:transceiver/srl_nokia-if:channel/srl_nokia-if:index";
        }
      }
      leaf forwarding-mode {
        if-feature "srl_nokia-feat:system-forwarding-mode";
        config false;
        type enumeration {
          enum store-and-forward;
          enum cut-through;
        }
        description
          "The forwarding mode for Ethernet frames received on this interface";
      }
      container statistics {
        srl_nokia-ext:delivery-node-override "true";
        srl_nokia-ext:stream-mode "sample=5";
        config false;
        leaf in-packets {
          type srl_nokia-comm:zero-based-counter64;
          description
            "Sum of all received packets, independent of protocol and forwarding type and before discards and errors";
        }
        leaf in-octets {
          type srl_nokia-comm:zero-based-counter64;
          description
            "Corresponds to ifHCInOctets from the IFMIB";
        }
        leaf in-unicast-packets {
          type srl_nokia-comm:zero-based-counter64;
          description
            "Corresponds to ifHCInUcastPkts from the IF-MIB";
        }
        leaf in-broadcast-packets {
          type srl_nokia-comm:zero-based-counter64;
          description
            "Corresponds to ifHCInBroadcastPkts from the IF-MIB";
        }
        leaf in-multicast-packets {
          type srl_nokia-comm:zero-based-counter64;
          description
            "Corresponds to ifHCInMulticastPkts from the IF-MIB";
        }
        leaf in-discarded-packets {
          type srl_nokia-comm:zero-based-counter64;
          description
            "Corresponds to ifInDiscards from the IFMIB.

             This counts the number of IP packets discarded due to VLAN mismatch, unknown dest MAC or drop by system-filter drop action. On 7250 IXR/IXRe systems this counter is not expected to increment above zero.";
        }
        leaf in-error-packets {
          type srl_nokia-comm:zero-based-counter64;
          description
            "Corresponds to ifInErrors from the IF-MIB";
        }
        leaf in-fcs-error-packets {
          type srl_nokia-comm:zero-based-counter64;
          description
            "Ingress FCS errors";
        }
        leaf out-packets {
          type srl_nokia-comm:zero-based-counter64;
          description
            "Sum of all transmitted packets, independent of protocol and forwarding type and before discards and errors";
        }
        leaf out-octets {
          type srl_nokia-comm:zero-based-counter64;
          description
            "Corresponds to ifHCOutOctets from the IF-MIB";
        }
        leaf out-mirror-octets {
          if-feature "srl_nokia-feat:mirroring-intf-stats";
          type srl_nokia-comm:zero-based-counter64;
          description
            "This counts the number of outgoing mirrored octets";
        }
        leaf out-unicast-packets {
          type srl_nokia-comm:zero-based-counter64;
          description
            "Corresponds to ifHCOutUcastPkts from the IF-MIB";
        }
        leaf out-broadcast-packets {
          type srl_nokia-comm:zero-based-counter64;
          description
            "Corresponds to ifHCOutBroadcastPkts from the IF-MIB";
        }
        leaf out-multicast-packets {
          type srl_nokia-comm:zero-based-counter64;
          description
            "Corresponds to ifHCOutMulticastPkts from the IF-MIB";
        }
        leaf out-discarded-packets {
          type srl_nokia-comm:zero-based-counter64;
          description
            "Corresponds to ifOutDiscards from the IF-MIB.

             On Jericho2 systems this counts packets dropped by an egress IP ACL of any of the port's subinterfaces.";
        }
        leaf out-error-packets {
          type srl_nokia-comm:zero-based-counter64;
          description
            "Corresponds to ifOutErrors from the IF-MIB";
        }
        leaf out-mirror-packets {
          if-feature "srl_nokia-feat:mirroring-intf-stats";
          type srl_nokia-comm:zero-based-counter64;
          description
            "This counts the number of outgoing mirrored packets";
        }
        leaf carrier-transitions {
          type srl_nokia-comm:zero-based-counter64;
          description
            "Number of times the interface state has transitioned from down to up.

             This is reset to zero when the device is started or reset or the counters are cleared.";
        }
        leaf last-clear {
          type srl_nokia-comm:date-and-time-delta;
          description
            "Timestamp of the last time the interface counters were cleared";
        }
      }
      container traffic-rate {
        srl_nokia-ext:delivery-node-override "true";
        config false;
        description
          "Container for traffic rate statistics";
        leaf in-bps {
          type uint64;
          description
            "The ingress bandwidth utilization of the port";
        }
        leaf out-bps {
          type uint64;
          description
            "The egress bandwidth utilization of the port";
        }
      }
      container adapter {
        config false;
        description
          "State for adapters";
        leaf model-number {
          type string;
          description
            "Model information for the adapter

             This is the information as read from the EEPROM of the part.  The string is expected to contain printable ASCII characters, but unprintable ASCII characters read from the EEPROM are not filtered out.";
        }
        leaf type {
          type enumeration {
            enum unknown {
              value 0;
            }
            enum qsfp28-to-sfp+/sfp28 {
              value 1;
            }
            enum cfp-to-qsfp28 {
              value 2;
            }
          }
          description
            "Type of adapter for the port";
        }
        leaf vendor-manufacture-date {
          type string;
          description
            "Vendor's date code.

             This is the information as read from the EEPROM of the part.  ";
        }
        leaf vendor-oui {
          type string;
          description
            "Vendor's OUI which contains the IEEE company identifier for the vendor

             This is the information as read from the EEPROM of the part.  A value of all zero indicates that the vendor OUI is unspecified.";
        }
        leaf vendor-part-number {
          type string;
          description
            "Vendor's part number or product name of the adapter

             This is the information as read from the EEPROM of the part.  An empty string indicates the vendor part number is unspecified. The string is expected to contain printable ASCII characters, but unprintable ASCII characters read from the EEPROM are not filtered out.";
        }
        leaf vendor-serial-number {
          type string;
          description
            "Vendor's serial number of the adapter

             This is the information as read from the EEPROM of the part.  An empty string indicates the vendor serial number is unspecified. The string is expected to contain printable ASCII characters, but unprintable ASCII characters read from the EEPROM are not filtered out.";
        }
      }
      container transceiver {
        leaf functional-type {
          if-feature "srl_nokia-feat:digital-coherent-optics or srl_nokia-feat:optical-line-system";
          type identityref {
            base transceiver-functional-type;
          }
          description
            "Indicates the module functional type which will be deployed for this interface

             This refines the set of leaves available within the transceiver configuration.";
          must "starts-with(../../srl_nokia-if:name, 'ethernet')" {
            error-message "functional-type not supported on this interface";
          }
        }
        leaf tx-laser {
          type boolean;
          description
            "Enable (true) or disable (false) the transmit laser of the transceiver

             When read from state this leaf always returns false (even if the configured value is true) when the Ethernet port is a copper/RJ45 port.

             Default is true (for interfaces that support transceivers).";
          must "starts-with(../../srl_nokia-if:name, 'ethernet')" {
            error-message "tx-laser not supported on this interface";
          }
          must 'not(../../breakout-mode)' {
            error-message "tx-laser not configurable when breakout-mode is enabled";
          }
        }
        leaf oper-state {
          config false;
          type transceiver-oper-state;
          description
            "The operational state of the transceiver

             The oper-state is always down when the Ethernet port is a copper/RJ45 port.";
        }
        leaf oper-down-reason {
          config false;
          type transceiver-oper-down-reason;
          description
            "The reason for the transceiver being operationally down";
        }
        leaf ddm-events {
          type boolean;
          description
            "Controls the reporting of DDM events

             When set to true, log events related to the Digital Diagnostic Monitoring (DDM) capabilities of the transceiver are generated.

             When set to false, no DDM-related log events are generated for this port/transceiver.

             When read from state this leaf always returns false (even if the configured value is true) when the Ethernet port is a copper/RJ45 port.";
          must "starts-with(../../srl_nokia-if:name, 'ethernet')" {
            error-message "ddm-events not supported on this interface";
          }
          must 'not(../../breakout-mode)' {
            error-message "ddm-events not configurable when breakout-mode is enabled";
          }
        }
        leaf forward-error-correction {
          if-feature "not srl_nokia-feat:forward-error-correction-ethernet and not srl_nokia-feat:platform-7215-a1";
          type enumeration {
            enum disabled;
            enum rs-528;
            enum rs-544;
            enum base-r {
              if-feature "srl_nokia-feat:port-fec-clause74";
              description
                "BASE-R FEC algorithm for 25GbE interfaces (also known as fire-code)";
            }
            enum rs-108 {
              description
                "Reed Solomon FEC algorithm for 25GbE interfaces";
            }
          }
          description
            "The forward error correction algorithm to use on the optical channel

             The same FEC algorithm must be used at both ends of a link.

             25G interfaces support disabled, base-r, rs-108 and rs-528; configuring other (incompatible) options will bring the port down. The FEC requirement for a 25G interface depends on the cable type. A CA-N DAC cable has a loss specification that requires no FEC. A CA-S DAC cable requires base-r FEC at a minimum. A CA-L DAC cable requires the stronger rs-108 Reed Solomon FEC.

             100G interfaces support disabled and rs-528; configuring other (incompatible) options will bring the port down.

             400G interfaces require rs-544; configuring other (unsupported) options will bring the port down.";
          must "starts-with(../../srl_nokia-if:name, 'ethernet')" {
            error-message "forward-error-correction not supported on this interface";
          }
          must 'not(../../breakout-mode)' {
            error-message "forward-error-correction not configurable when breakout-mode is enabled";
          }
        }
        leaf form-factor {
          config false;
          type enumeration {
            enum CFP2 {
              value 1;
            }
            enum CFP2-ACO {
              value 2;
            }
            enum CFP4 {
              value 3;
            }
            enum QSFP {
              value 4;
            }
            enum QSFPplus {
              value 5;
            }
            enum QSFP28 {
              value 6;
            }
            enum QSFPDD {
              value 7;
            }
            enum SFP {
              value 8;
            }
            enum SFPplus {
              value 9;
            }
            enum Non-pluggable {
              value 10;
            }
            enum Other {
              value 11;
            }
            enum SFP28 {
              value 12;
            }
            enum SFPDD {
              value 13;
            }
            enum QSFP56 {
              value 14;
            }
            enum SFP56 {
              value 15;
            }
            enum CSFP {
              value 16;
            }
            enum OSFP {
              value 17;
            }
          }
          description
            "Specifies the transceiver form factor associated with the port";
        }
        leaf ethernet-pmd {
          config false;
          type string;
          description
            "Specifies the Ethernet compliance code of the transceiver associated with the port";
        }
        leaf connector-type {
          config false;
          type enumeration {
            enum SC {
              value 1;
            }
            enum FC-STYLE1-COPPER {
              value 2;
            }
            enum FC-STYLE2-COPPER {
              value 3;
            }
            enum BNC-OR-TNC {
              value 4;
            }
            enum FC-COAX {
              value 5;
            }
            enum FIBER-JACK {
              value 6;
            }
            enum LC {
              value 7;
            }
            enum MT-RJ {
              value 8;
            }
            enum MU {
              value 9;
            }
            enum SG {
              value 10;
            }
            enum OPTICAL-PIGTAIL {
              value 11;
            }
            enum MPO-1x12 {
              value 12;
            }
            enum MPO-2x16 {
              value 13;
            }
            enum HSSDC {
              value 14;
            }
            enum COPPER-PIGTAIL {
              value 15;
            }
            enum RJ45 {
              value 16;
            }
            enum no-separable-connector {
              value 17;
            }
            enum MXC-2x16 {
              value 18;
            }
            enum CS-OPTICAL-CONNECTOR {
              value 19;
            }
            enum SN-OPTICAL-CONNECTOR {
              value 20;
            }
            enum MPO-2x12 {
              value 21;
            }
            enum MPO-1x16 {
              value 22;
            }
            enum unknown {
              value 23;
            }
          }
          description
            "Specifies the fiber connector type of the transceiver associated with the port";
        }
        leaf vendor {
          config false;
          type string;
          description
            "Name of the transceiver vendor

             This is the information as read from the EEPROM of the part.";
        }
        leaf vendor-part-number {
          config false;
          type string;
          description
            "Vendor's part number for the transceiver

             This is the information as read from the EEPROM of the part.";
        }
        leaf vendor-revision {
          config false;
          type string;
          description
            "Vendor's revision number for the transceiver

             This is the information as read from the EEPROM of the part.";
        }
        leaf vendor-lot-number {
          config false;
          type string;
          description
            "Vendor's lot number for the transceiver

             This is the information as read from the EEPROM of the part.";
        }
        leaf serial-number {
          config false;
          type string;
          description
            "Transceiver serial number

             This is the information as read from the EEPROM of the part.";
        }
        leaf date-code {
          config false;
          type srl_nokia-comm:date-and-time-delta;
          description
            "Transceiver date code.";
        }
        leaf firmware-version {
          if-feature "srl_nokia-feat:transceiver-firmware-version";
          config false;
          type string;
          description
            "Active firmware version

             This is the information as read from the EEPROM of the part.  For transceivers with both major and minor revision, the string uses the format major#.minor#
             This is only available for digital coherent optic transceivers.";
        }
        leaf fault-condition {
          config false;
          type boolean;
          description
            "Indicates if a fault condition exists in the transceiver.";
        }
        leaf wavelength {
          config false;
          type decimal64 {
            fraction-digits 2;
          }
          description
            "Wavelength of the transmitting laser in nanometers";
        }
        leaf link-length-information {
          if-feature "srl_nokia-feat:transceiver-link-length-info";
          config false;
          type string;
          description
            "Indicates the link length information stored in transceiver EEPROMs

              This leaf is applicable only when the transceiver is equipped.  The information is presented as a string interpretation of the 6 octets from the EEPROM.";
        }
        container temperature {
          config false;
          leaf latest-value {
            type srl_nokia-comm:temperature;
            description
              "The current temperature of the transceiver module in degrees Celsius";
          }
          leaf maximum {
            type srl_nokia-comm:temperature;
            description
              "Represents the highest temperature the transceiver has reached since it booted";
          }
          leaf maximum-time {
            type srl_nokia-comm:date-and-time-delta;
            description
              "Indicates the time this transceiver reached the temperature referenced in maximum";
          }
          leaf high-alarm-condition {
            type boolean;
            description
              "High alarm threshold condition

               Set to true whenever the temperature is above the high-alarm-threshold and set to false whenever the temperature is below the high-alarm-threshold";
          }
          leaf high-alarm-threshold {
            type srl_nokia-comm:temperature;
            description
              "High alarm threshold

               Read from the installed transceiver";
          }
          leaf low-alarm-condition {
            type boolean;
            description
              "Low alarm threshold condition.

               Set to true whenever the temperature is below the low-alarm-threshold and set to false whenever the temperature is above the low-alarm-threshold";
          }
          leaf low-alarm-threshold {
            type srl_nokia-comm:temperature;
            description
              "Low alarm threshold.

               Read from the installed transceiver";
          }
          leaf high-warning-condition {
            type boolean;
            description
              "High warning threshold condition.

               Set to true whenever the temperature is above the high-warning-threshold and set to false whenever the temperature is below the high-warning-threshold";
          }
          leaf high-warning-threshold {
            type srl_nokia-comm:temperature;
            description
              "High warning threshold.

               Read from the installed transceiver";
          }
          leaf low-warning-condition {
            type boolean;
            description
              "Low warning threshold condition.

               Set to true whenever the temperature is below the low-warning-threshold and set to false whenever the temperature is above the low-warning-threshold";
          }
          leaf low-warning-threshold {
            type srl_nokia-comm:temperature;
            description
              "Low warning threshold.

               Read from the installed transceiver";
          }
        }
        container voltage {
          config false;
          leaf latest-value {
            type decimal64 {
              fraction-digits 4;
            }
            description
              "The current voltage reading of the transceiver module (in Volts)";
          }
          leaf high-alarm-condition {
            type boolean;
            description
              "High alarm threshold condition.

               Set to true whenever the module voltage is above the high-alarm-threshold and set to false whenever the module voltage is below the high-alarm-threshold";
          }
          leaf high-alarm-threshold {
            type decimal64 {
              fraction-digits 4;
            }
            description
              "High alarm threshold.

               Read from the installed transceiver";
          }
          leaf low-alarm-condition {
            type boolean;
            description
              "Low alarm threshold condition.

               Set to true whenever the module voltage is below the low-alarm-threshold and set to false whenever the module voltage is above the low-alarm-threshold";
          }
          leaf low-alarm-threshold {
            type decimal64 {
              fraction-digits 4;
            }
            description
              "Low alarm threshold.

               Read from the installed transceiver";
          }
          leaf high-warning-condition {
            type boolean;
            description
              "High warning threshold condition.

               Set to true whenever the module voltage is above the high-warning-threshold and set to false whenever the module voltage is below the high-warning-threshold";
          }
          leaf high-warning-threshold {
            type decimal64 {
              fraction-digits 4;
            }
            description
              "High warning threshold.

               Read from the installed transceiver";
          }
          leaf low-warning-condition {
            type boolean;
            description
              "Low warning threshold condition.

               Set to true whenever the module voltage is below the low-warning-threshold and set to false whenever the module voltage is above the low-warning-threshold";
          }
          leaf low-warning-threshold {
            type decimal64 {
              fraction-digits 4;
            }
            description
              "Low warning threshold.

               Read from the installed transceiver";
          }
        }
        uses power-levels;
        list channel {
          config false;
          description
            "List of physical channels supported by the transceiver associated with this port.

             Availability of these leaves is dependent on the transceiver-functional-type; not all leaves are available for all types";
          key "index";
          leaf index {
            type uint8 {
              range "1..10";
            }
            description
              "Index of the physical channel or lane";
          }
          leaf wavelength {
            config false;
            type decimal64 {
              fraction-digits 2;
            }
            description
              "Wavelength of the transmitting laser in nanometers";
          }
          uses power-levels;
        }
      }
      container ethernet {
        leaf aggregate-id {
          if-feature "srl_nokia-feat:lag";
          description
            "lag interface with which this interface is associated";
          type leafref {
            path "/srl_nokia-if:interface/srl_nokia-if:name";
          }
          must 'not(../../qos)' {
            error-message "qos configuration is not supported on LAG member ports";
          }
          must 'not(../../mtu >= 0)' {
            error-message "mtu and aggregate-id can not be configured together";
          }
          must 'not(true() = ../../vlan-tagging or false() = ../../vlan-tagging)' {
            error-message "vlan-tagging and aggregate-id can not be configured together";
          }
          must 'not(../../tpid)' {
            error-message "tpid and aggregate-id can not be configured together";
          }
          must 'not(../../ethernet/duplex-mode)' {
            error-message "duplex-mode and aggregate-id can not be configured together";
          }
          must 'not(true() = ../../ethernet/flow-control/receive or false() = ../../ethernet/flow-control/receive)' {
            error-message "flow-control receive and aggregate-id can not be configured together";
          }
          must 'not(true() = ../../ethernet/flow-control/transmit or false() = ../../ethernet/flow-control/transmit)' {
            error-message "flow-control transmit and aggregate-id can not be configured together";
          }
          must 'not(../../breakout-mode)' {
            error-message "aggregate-id not configurable when breakout-mode is enabled";
          }
          must 'not(../../ethernet/standby-signaling)' {
            error-message "standby-signaling and aggregate-id cannot be configured together";
          }
          must 'not(../../ethernet/link-loss-forwarding)' {
            error-message "link-loss-forwarding and aggregate-id cannot be configured together";
          }
          must 'not(../../load-balancing/hash-profile)' {
            error-message "hash-profile and aggregate-id can not be configured together";
          }
        }
        leaf forwarding-viable {
          if-feature "srl_nokia-feat:lag-forwarding-viable";
          type boolean;
          must '(../aggregate-id)' {
            error-message "aggregate-id must be configured";
          }
          description
            "If true:
             this LAG member link should be used for the transmission of traffic if all other LAG/port attributes allow it.

             If false:
             this LAG member link should not be used for the transmission of traffic.

             In all cases:
             This LAG member link should process any received frames when it is an active member link.  L2 protocols such as LLDP, LACP and micro-BFD should continue to be sent and processed.";
        }
        leaf auto-negotiate {
          if-feature "srl_nokia-feat:platform-7220-d1 or srl_nokia-feat:platform-7215-a1";
          type boolean;
          must "re-match(../../srl_nokia-if:name, 'ethernet-1/[1-9]') or re-match(../../srl_nokia-if:name, 'ethernet-1/[1-3][0-9]') or re-match(../../srl_nokia-if:name, 'ethernet-1/4[0-8]')" {
            error-message "auto-negotiation not supported on this interface";
          }
          description
            "When set to true the interface uses auto-negotiation for speed, duplex and flow-control settings.

             When set to false, the transmission parameters are specified manually.";
          must 'not(../../breakout-mode)' {
            error-message "auto-negotiate not configurable when breakout-mode is enabled";
          }
        }
        leaf duplex-mode {
          if-feature "srl_nokia-feat:platform-7220-d1 or srl_nokia-feat:platform-7215-a1";
          type enumeration {
            enum full;
            enum half;
          }
          must "re-match(../../srl_nokia-if:name, 'ethernet-1/[1-9]') or re-match(../../srl_nokia-if:name, 'ethernet-1/[1-3][0-9]') or re-match(../../srl_nokia-if:name, 'ethernet-1/4[0-8]')" {
            error-message "duplex-mode not supported on this interface";
          }
          must 'not(../../breakout-mode)' {
            error-message "duplex-mode not configurable when breakout-mode is enabled";
          }
          description
            "When auto-negotiate is true, this sets the duplex mode that will be advertised to the peer.  When auto-negotiate is false, this directly sets the duplex mode of the interface.";
        }
        leaf dac-link-training {
          if-feature "srl_nokia-feat:dac-link-training";
          type boolean;
          must "starts-with(../../srl_nokia-if:name, 'ethernet')" {
            error-message "dac-link-training not supported on this interface";
          }
          must 'not(../../breakout-mode)' {
            error-message "dac-link-training not configurable when breakout-mode is enabled";
          }
          description
            "If the system detects that the transceiver is connected to a DAC cable then a true setting enables link training for better link stability. The link training setting must be the same at both ends of the DAC cable or else the link may not come up.";
        }
        container flow-control {
          leaf receive {
            type boolean;
            must "starts-with(../../../srl_nokia-if:name, 'mgmt') or starts-with(../../../srl_nokia-if:name, 'ethernet') or starts-with(../../../srl_nokia-if:name, 'lag')" {
              error-message "flow-control receive not supported on this interface";
            }
            must 'not(../../../breakout-mode)' {
              error-message "flow-control receive not configurable when breakout-mode is enabled";
            }
            description
              "When this is true PAUSE frames received on this interface are accepted and processed, and, if auto-negotiation is enabled it also causes the capability to receive PAUSE frames to be signaled to the peer (applicable only to ports 1-48 of the 7220 IXR-D1 and to mgmt0 and mgmt0-standby ports).

               When this is false PAUSE frames received on this interface are ignored, and, if auto-negotiation is enabled it causes the capability to receive PAUSE frames to be signaled to the peer as non-support (applicable only to ports 1-48 of the 7220 IXR-D1 and to mgmt0 and mgmt0-standby ports)";
          }
          leaf transmit {
            if-feature "srl_nokia-feat:tx-flow-control";
            type boolean;
            must "starts-with(../../../srl_nokia-if:name, 'ethernet') or starts-with(../../../srl_nokia-if:name, 'lag')" {
              error-message "flow-control transmit not supported on this interface";
            }
            must 'not(../../../breakout-mode)' {
              error-message "flow-control transmit not configurable when breakout-mode is enabled";
            }
            description
              "Enables/disables the sending of PAUSE frames.

               If auto-negotiation is enabled (applicable only to ports 1-48 of the 7220 IXR-D1 and to mgmt0 and mgmt0-standby ports) PAUSE frames are sent to the peer only if the peer advertised support for PAUSE frames.";
          }
        }
        leaf lacp-port-priority {
          if-feature "srl_nokia-feat:lacp-fallback";
          type uint16;
          must "starts-with(../../srl_nokia-if:name, 'ethernet')" {
            error-message "lacp-port-priority not supported on this interface";
          }
          must 'not(../../breakout-mode)' {
            error-message "lacp-port-priority not configurable when breakout-mode is enabled";
          }
          description
            "Configure the port priority for LACP.  This value is used to  determine which port should be activated with LACP fallback mode. Lower values are more preferred.";
        }
        leaf port-speed {
          srl_nokia-ext:show-importance "high";
          type enumeration {
            enum 10M {
              if-feature "srl_nokia-feat:port-speed-10M";
            }
            enum 100M {
              if-feature "srl_nokia-feat:port-speed-100M";
            }
            enum 1G {
              if-feature "srl_nokia-feat:port-speed-1G";
            }
            enum 10G {
              if-feature "srl_nokia-feat:port-speed-10G or srl_nokia-feat:breakout-speed-10G";
            }
            enum 25G {
              if-feature "srl_nokia-feat:port-speed-25G or srl_nokia-feat:breakout-speed-25G";
            }
            enum 40G {
              if-feature "srl_nokia-feat:port-speed-40G";
            }
            enum 50G {
              if-feature "srl_nokia-feat:port-speed-50G or srl_nokia-feat:breakout-speed-50G";
            }
            enum 100G {
              if-feature "srl_nokia-feat:port-speed-100G or srl_nokia-feat:breakout-speed-100G";
            }
            enum 200G {
              if-feature "srl_nokia-feat:port-speed-200G";
            }
            enum 400G {
              if-feature "srl_nokia-feat:port-speed-400G or srl_nokia-feat:breakout-speed-400G";
            }
            enum 800G {
              if-feature "srl_nokia-feat:port-speed-800G";
            }
            enum 1T {
              if-feature "srl_nokia-feat:port-speed-1T";
            }
          }
          must "(starts-with(../../srl_nokia-if:name, 'ethernet') or starts-with(../../srl_nokia-if:name, 'lif') or starts-with(../../srl_nokia-if:name, 'enp') or starts-with(../../srl_nokia-if:name, 'vhn'))" {
            error-message "port speed not configurable on this interface";
          }
          must 'not(../../breakout-mode)' {
            error-message "port-speed not configurable when breakout-mode is enabled";
          }
          description
            "The speed of the port or channel

             If this parameter is configured, then the configured value will be applied.  If it is not configured, then there are two mechanisms that will set a speed for the port.

             Some platforms support a mechanism to automatically set the port-speed based on the form factor of the inserted transceiver.
                form-factor    speed
                QSFP28         100G
                SFP112         100G
                SFP56-DD       100G
                SFP            1G
                SFP+           10G
                QSFP56-DD      400G
                QSFP56         200G
                QSFP28-DD      200G
                SFP28          25G
                QSFP112        400G
                QSFP+          40G
                QSFP28-50G     50G
                SFP56          50G
                QSFP112-DD     800G
                CFP2-DCO       400G

             When the auto-configuration of speed based on form factor is not supported and the speed is not configured, then the default speed of a port (when auto-negotiation is disabled or unsupported) depends on the platform and port/connector number as follows:

             mgmt0 and mgmt0-standby ports: 1G
             7250 IXR-6/10 IMM ports 1-32:  100G
             7250 IXR-6/10 IMM ports 33-36: 100G
             7215 IXS-A1 ports 1-48: 1G
             7215 IXS-A1 ports 49-52: 10G
             7220-D1 ports 1-48: 1G
             7220-D1 ports 49-52: 10G
             7220-D2/D2L ports 1-48: 25G
             7220-D2/D2L ports 49-56: 100G
             7220-D2L ports 57-58: 10G
             7220-D3 ports 1-2: 10G
             7220-D3 ports 3-34: 100G
             7220-D3L ports 1-32: 100G
             7220-D3L ports 33-34: 10G
             7220-D4 ports 1-28: 100G
             7220-D4 ports 29-36: 400G
             7220-D5 ports 1-32: 400G
             7220-D5 ports 33-38: 10G
             7220-H2 ports 1-128: 100G
             7220-H3 ports 1-2: 10G
             7220-H3 ports 3-34: 400G
             7220-H4 ports 1-64: 400G
             7220-H4 ports 65-66: 10G
             7220-H4-32D ports 1-32: 400G
             7220-H4-32D ports 33: 10G
             7220-H5-64D ports 1-64: 800G
             7220-H5-64D ports 65-66: 10G
             7250 IXR-6e/10e 60p QSFP28 IMM all ports:  100G
             7250 IXR-6e/10e 36p QSFPDD-400 IMM all ports:  400G
             7250 IXR-6e/10e/18e 36p QSFP112-DD IMM all ports:  800G
             7250 IXR-X1b QSFP28 ports 1-24: 100G
             7250 IXR-X1b QSFPDD ports 25-36: 400G
             7250 IXR-X3b QSFPDD all ports: 400G
             7730 SXR-1d-32D QSFP28 ports 1-16,21-32: 100G
             7730 SXR-1d-32D QSFPDD ports 17-20: 400G
             7730 SXR-1x-44S SFPDD ports 1-20, 23-42: 100G
             7730 SXR-1x-44S QSFPDD ports 21,22,43,44: 400G

             Supported speeds:
             mgmt0 and mgmt0-standby ports: 1G
             7250 IXR-6/10 IMM ports 1-8,13-32: 40G, 100G
             7250 IXR-6/10 IMM ports 9-12: 100G
             7250 IXR-6/10 IMM ports 33-36: 40G, 100G, 400G
             7215 IXS-A1 ports 1-48: 10M, 100M, 1G
             7215 IXS-A1 ports 49-52: 1G, 10G
             7220-D1 ports 1-48: 10M, 100M, 1G
             7220-D1 ports 49-52: 10G
             7220-D2/D2L ports 1-48: 1G, 10G, 25G (Note 2)
             7220-D2 ports 49-56: 10G, 25G, 40G, 100G
             7220-D2L ports 49-56: 10G, 25G, 40G, 100G
             7220-D2L ports 57-58: 10G
             7220-D3 ports 1-2: 10G
             7220-D3 ports 3-34: 10G, 25G, 40G, 50G, 100G
             7220-D3L ports 1-32: 10G, 25G, 40G, 50G, 100G
             7220-D3L ports 33-34: 10G
             7220-D4 ports 1-8: 40G, 100G
             7220-D4 ports 9-28: 10G, 25G, 40G, 100G
             7220-D4 ports 29-36: 10G, 25G, 40G, 100G, 400G
             7220-D5 ports 1-32: 40G, 100G, 400G
             7220-D5 ports 33-38: 10G
             7220-H2 ports 1-128: 100G
             7220-H3 ports 1-2: 10G
             7220-H3 ports 3-34: 40G, 100G, 200G, 400G
             7220-H4 ports 1-64: 40G, 100G, 200G, 400G
             7220-H4 ports 65-66: 10G
             7220-H4-32D ports 1-32: 40G, 100G, 400G
             7220-H4-32D ports 33: 10G
             7220-H5-64D ports 1-64: 50G, 100G, 200G, 400G, 800G
             7220-H5-64D ports 65-66: 10G
             7250 IXR-6e/10e 60p QSFP28 IMM all ports:  100G
             7250 IXR-6e/10e 36p QSFPDD-400 IMM all ports:  40G, 100G, 400G
             7250 IXR-6e/10e/18e 36p QSFP112-DD IMM all ports:  100G, 400G, 800G
             7250 IXR-X1b QSFP28 ports 1-24: 40G, 100G (Note 4)
             7250 IXR-X1b QSFPDD ports 25-36: 40G, 100G, 400G
             7250 IXR-X3b QSFPDD all ports: 40G, 50G, 100G, 400G
             7730 SXR-1d-32D QSFP28 ports 1-16,21-32: 40G, 100G (Note 3)
             7730 SXR-1d-32D QSFPDD ports 17-20: 40G, 100G, 400G
             7730 SXR-1x-44S SFPDD ports 1-20,23-42: 10G, 25G, 100G
             7730 SXR-1x-44S QSFPDD ports 21,22,43,44: 40G, 100G, 400G

             Note 1:
              Note reserved for future use.

             Note 2:
              On 7220-D2: if one port in each consecutive group of 4 ports (1-4, 5-8, .. , 45-48) is enabled and has a configured speed of 25G then the other 3 ports may only be enabled if they also have a configured speed of 25G or no speed configured; if one port in each consecutive group of 4 ports (1-4, 5-8, .. , 45-48) is enabled and has a configured speed of 1G or 10G the other 3 ports may only be enabled if they also have a configured speed of 1G or 10G or no speed configured.
              On 7220-D2L: if one port in each port group of 4 ports ({1, 2, 3, 6}, {4, 5, 7, 9}, {8, 10, 11, 12}, {13, 14, 15, 18}, {16, 17, 19, 21}, {20, 22, 23, 24}, {25, 26, 27, 30}, {28, 29, 31, 33}, {32, 34, 35, 36}, {37, 38, 39, 42}, {40, 41, 43, 45}, {44, 46, 47, 48}) is enabled and has a configured speed of 25G the other 3 ports may only be enabled if they also have a configured speed of 25G or no speed configured; if one port in each port group of 4 ports is enabled and has a configured speed of 1G or 10G the other 3 ports may only be enabled if they also have a configured speed of 1G or 10G or no speed configured.

             Note 3: Breakout and 40G is only supported on odd numbered ports.
              For the QSFP28 four port groupings [1-4], [5-8], [9-12], [13-16], [21-24], [25-28], and [29-32] if either of the odd numbered ports within a group is configured for 40G, 4x10G, or 4x25G,
              then the other odd numbered port in the same group may only be configured if it is configured for one of 40G, 4x10G, or 4x25G (can differ between the odd ports) and neither of
              the two even numbered ports within the same group can be configured.

             Note 4: For the QSFP28 ports, the following port groups exist [n, n+1, n+2, n+3] for n = 1, 5, 9, 13, 17, 21.  Breakout for 4x25G or 4x10G is only supported on ports n+1 and n+3.
              When initially configuring a port with a breakout configuration or port speed that does not already exist on another configured port within the same group, then a link flap and traffic hit may occur on other ports within the same group.
              When the breakout configuration or port speed is changed for a port in a group, then a link flap and traffic hit may occur on other ports within the same group.
              If port n+1 within the group is configured for breakout, then port n cannot be configured.
              In addition if port n+1 is configured for breakout and port n+3 is configured without breakout, then port n+2 may only be configured with the same speed as port n+3.
              If port n+3 within the group is configured for breakout, then port n+2 cannot be configured.
              In addition if port n+3 is configured for breakout and port n+1 is configured without breakout, then port n may only be configured with the same speed as port n+1.

             7250 IXR details:
              If the interface corresponds to a connector that has no installed transceiver then the value is accepted without any checking or restriction, and info from state will display the configured value.  Otherwise if the configured port-speed is NOT supported by the installed transceiver the port is forced operationally down.

             Port Groups and auto-configuration:
              Manually configured and enabled port-speed (and breakout-modes) take precedence over the auto-configured port-speed.  This means that configuring and enabling a port within a port-group can have a side effect to take down an operational port that had its speed set based on the auto-configuration feature.  If there is risk of mixing transceiver types within a port group, then it is recommended to always manually configure the speed for enabled ports";
        }
        leaf hw-mac-address {
          config false;
          type srl_nokia-comm:mac-address;
          description
            "The MAC address associated with the port";
        }
        leaf mac-address {
          if-feature "srl_nokia-feat:configurable-intf-mac-addr";
          type srl_nokia-comm:mac-address;
          must "not (starts-with(../../srl_nokia-if:name, 'lo') or starts-with(../../srl_nokia-if:name, 'system'))" {
            error-message "mac-address not configurable on this interface";
          }
          must 'not(../../breakout-mode)' {
            error-message "mac-address not configurable when breakout-mode is enabled";
          }
          description
            "MAC address of the interface

             If not configured, this is set to the hw-mac-address, which is populated depending on interface type:

             - For interfaces with a discoverable MAC address (either populated by an external system or present in hardware) the discovered value is populated.
             - For interfaces without a discoverable MAC address, the address is generated from a hash of the interface name and the chassis MAC address.

             When deleted, will revert back to the value of hw-mac-address.";
        }
        container forward-error-correction {
          if-feature "srl_nokia-feat:forward-error-correction-ethernet";
          leaf fec-option {
            type enumeration {
              enum disabled;
              enum base-r {
                if-feature "srl_nokia-feat:port-fec-clause74";
                description
                  "An early form of FEC used with 25G interfaces

                   Defined in clause 74 of IEEE 802.3.  This FEC has poor performance compared to clause 108 (rs-528).  base-r should only be used if the far end doesn't support rs-528

                   This type of FEC is only supported for 25G interfaces.";
              }
              enum rs-528 {
                description
                  "Reed-Solomon RS(528,514) code FEC

                   For 25G interfaces, this is IEEE 802.3 Clause 108 using RS(528,514)
                   For 100G interfaces, this is IEEE 802.3 Clause 91 using RS(528,514)";
              }
            }
            description
              "The forward error correction algorithm requested for the interface

               The same FEC algorithm must be used at both ends of a link.  This leaf should be only be configured for 25G and 100G interfaces; it can cause the port to remain operationally down for other interface speeds.
               1G, 10G, and 40G interfaces do not use FEC
               50G and interfaces with speeds higher than 100G have well defined FEC settings in IEEE 802.3 that must be used and so configuration is not needed.

               For 100G interfaces, if the specific transceiver inserted uses PAM4 encoding, then the system shall always enable clause 91 RS(544,514) FEC and so this leaf should be left unconfigured.
               For 100G interfaces, if the specific transceiver inserted uses NRZ encoding, then it may require rs-528 to be enabled.  This is dependent on the specific PMD and also whether the installed transceiver includes the FEC functionality inside the transceiver.
               Refer to Nokia support for the correct setting for the specific transceiver.

               If this leaf is configured and the setting is incompatible with the installed transceiver, the interface shall be kept down with a reason of unsupported-fec.

               25G interfaces support disabled, base-r, and rs-528.
               The FEC requirement for a 25G interface depends on the cable type. A CA-N DAC cable has a loss specification that requires no FEC. A CA-S DAC cable requires FEC, rs-528 recommended.  A CA-L DAC cable requires the stronger rs-528 FEC.";
            must "starts-with(../../../srl_nokia-if:name, 'ethernet')" {
              error-message "forward-error-correction not supported on this interface";
            }
            must 'not(../../../breakout-mode)' {
              error-message "forward-error-correction not configurable on interfaces with breakout-mode is enabled";
            }
          }
          leaf operational-host-if-fec {
            config false;
            type oper-fec-type;
            description
              "The forward error correction algorithm in use to use at the host interface and potentially the media interface

               The same FEC algorithm must be used at both ends of a link.";
          }
          container statistics {
            config false;
            description
              "Container for the fec statistics";
            container host-if-fec-router {
              if-feature "srl_nokia-feat:port-host-if-fec-stats-router";
              description
                "Statistics for fec as reported at the router for the host interface; received from the transceiver";
              leaf status {
                type enumeration {
                  enum locked;
                  enum unlocked;
                }
                description
                  "Operational status of FEC";
              }
              leaf frame-error-count {
                type srl_nokia-comm:zero-based-counter64;
                description
                  "The number of uncorrectable FEC blocks/frames";
              }
              container pre-fec-ber {
                description
                  "Bit error rate before forward error correction";
                leaf instant {
                  type decimal64 {
                    fraction-digits 18;
                  }
                  units "bit-errors-per-second";
                  description
                    "The instantaneous value of the ber";
                }
              }
            }
            container host-if-fec-transceiver {
              if-feature "srl_nokia-feat:port-host-if-fec-stats-transceiver";
              description
                "Statistics for fec as reported at the transceiver for the host interface; received from the router

                 Not all configurations have FEC enabled in the transceiver for the host interface so this set of statistics will not always be available.";
              container frame-error-count {
                description
                  "The number of uncorrectable FEC blocks/frames";
                leaf instant {
                  type srl_nokia-comm:zero-based-counter64;
                  description
                    "The instantaneous value of the ferc";
                }
                leaf avg {
                  type srl_nokia-comm:zero-based-counter64;
                  description
                    "The arithmetic mean value of the ferc";
                }
                leaf min {
                  type srl_nokia-comm:zero-based-counter64;
                  description
                    "The minimum value of the ferc";
                }
                leaf max {
                  type srl_nokia-comm:zero-based-counter64;
                  description
                    "The maximum value of the ferc";
                }
              }
              container pre-fec-ber {
                description
                  "Bit error rate before forward error correction";
                leaf instant {
                  type decimal64 {
                    fraction-digits 18;
                  }
                  units "bit-errors-per-second";
                  description
                    "The instantaneous value of the ber";
                }
                leaf avg {
                  type decimal64 {
                    fraction-digits 18;
                  }
                  units "bit-errors-per-second";
                  description
                    "The arithmetic mean value of the ber";
                }
                leaf min {
                  type decimal64 {
                    fraction-digits 18;
                  }
                  units "bit-errors-per-second";
                  description
                    "The minimum value of the ber";
                }
                leaf max {
                  type decimal64 {
                    fraction-digits 18;
                  }
                  units "bit-errors-per-second";
                  description
                    "The maximum value of the ber";
                }
              }
            }
          }
        }
        leaf physical-medium {
          config false;
          type enumeration {
            enum 1000BASE-T;
          }
          description
            "Indicates the PHY supported by the RJ45 port.

             If the port is supported by a SFP, QSFP+, QSFP28 or QSFP-DD transceiver no value is populated in this leaf.";
        }
        leaf ptp-asymmetry {
          if-feature "srl_nokia-feat:sync";
          type int32;
          units "nanoseconds";
          default "0";
          must '(. = 0) or (starts-with(../../srl_nokia-if:name, "ethernet"))' {
            error-message "ptp-asymmetry is supported only on ethernet interfaces";
          }
          must '(. = 0) or not(../../breakout-mode)' {
            error-message "ptp-asymmetry is not supported on interfaces with breakout mode enabled";
          }
          description
            "This command configures the PTP asymmetry delay on the Ethernet port

             This command is used to correct known asymmetry as part of time of day or phase
             recovery using PTP packets on both local and downstream PTP clocks.";
        }
        container ptp-timestamping {
          if-feature "srl_nokia-feat:sync-ptp-ip-peers and srl_nokia-feat:special-ptp-ip-timestamping";
          presence "Configures the ptp timestamping parameters";
          must '(starts-with(../../srl_nokia-if:name, "ethernet"))' {
            error-message "ptp-timestamping is supported only on ethernet interfaces";
          }
          must 'not(../../breakout-mode)' {
            error-message "ptp-timestamping is not supported on interfaces with breakout mode enabled";
          }
          leaf disable-ip-timestamping {
            type boolean;
            description
              "Disables timestamping of PTP over IP messages on this port

               For platforms supporting PTP functionality, any transiting PTP over IP packets are timestamped in hardware by default, regardless of whether PTP is enabled on the system. To avoid unwanted correction-field updates of PTP transit packets on ports (ports involved in PTP packet transit only), this command can be used to disabled the timestamping.";
          }
        }
        leaf standby-signaling {
          type enumeration {
            enum power-off;
            enum lacp;
          }
          must "starts-with(../../srl_nokia-if:name, 'ethernet') or starts-with(../../srl_nokia-if:name, 'lag')" {
            error-message "standby-signaling not supported on this interface";
          }
          must "((. = 'lacp') and (../../lag/lag-type = 'lacp')) or (. != 'lacp')" {
            error-message "lacp-based standby-signaling supported only on lacp enabled lag interfaces";
          }
          must 'not(../../breakout-mode)' {
            error-message "standby-signaling not configurable when breakout-mode is enabled";
          }
          description
            "Indicates the standby-signaling used in the interface.

             An application using a port-based redundancy mechanism will trigger the standby signaling on the ethernet
             interface if the interface is selected as standby.";
        }
        leaf link-loss-forwarding {
          if-feature "srl_nokia-feat:link-loss-forwarding";
          type boolean;
          must "starts-with(../../srl_nokia-if:name, 'ethernet') or starts-with(../../srl_nokia-if:name, 'lag')" {
            error-message "link-loss-forwarding not supported on this interface";
          }
          must 'not(../../breakout-mode)' {
            error-message "link-loss-forwarding not configurable when breakout-mode is enabled";
          }
          must 'not(true() = ../../vlan-tagging)' {
            error-message "vlan-tagging true and link-loss-forwarding can not be configured together";
          }
          must '../standby-signaling' {
            error-message "link-loss-forwarding requires the configuration of standby-signaling";
          }
          description
            "Indicates whether link-loss-forwarding is enabled in the interface

             When enabled, faults can be propagated to the devices connected to this interface. It is supported on interfaces
             with a single non-tagged subinterface that is associated to a network-instance of type vpws. On VPWS services,
             the propagation of faults from a connection-point to the opposite connection-point is known as Link Loss
             Forwarding and requires setting this command to true and the standby-signaling command to the type of propagation
             signaling to be used with the connected Customer Equipment.";
        }
        leaf reload-delay {
          if-feature "srl_nokia-feat:reload-delay";
          type uint32 {
            range "1..86400";
          }
          units "seconds";
          description
            "Configure reload-delay timer for Ethernet interfaces.

             The reload-delay timer starts when the associated XDP interface state is learned. While the timer is
             running, the interface transceiver laser is disabled to avoid attracting traffic from the connected
             device at the other end of the interface. The reload-delay timer should be used in multi-homing
             interfaces and be set to a value long enough to allow the system to recover all the network protocols
             upon reboot, before start attracting traffic from the multi-homed device.";
          must "starts-with(../../srl_nokia-if:name, 'ethernet')" {
            error-message "reload-delay not supported on this interface";
          }
          must 'not(../../breakout-mode)' {
            error-message "reload-delay not configurable when breakout-mode is enabled";
          }
        }
        leaf reload-delay-expires {
          if-feature "srl_nokia-feat:reload-delay";
          config false;
          type srl_nokia-comm:date-and-time-delta;
          description
            "The remaining time until the reload-delay expires and the interface can go operationally up.";
        }
        container hold-time {
          if-feature "(not srl_nokia-feat:fpcx) or srl_nokia-feat:hold-time-fpcx";
          description
            "Configure interface hold timers for Ethernet interfaces";
          leaf up {
            type uint32 {
              range "0 | 100..86400000";
            }
            units "milliseconds";
            default "0";
            must "starts-with(../../../srl_nokia-if:name, 'ethernet') or (. = 0)" {
              error-message "hold-time up not supported on this interface";
            }
            must 'not(../../../breakout-mode) or (. = 0)' {
              error-message "hold-time up not configurable when breakout-mode is enabled";
            }
            must '. mod 50 = 0' {
              error-message "hold-time up must be a multiple of 50";
            }
            description
              "Holds link up events for the configured time

               The hold-time up behavior is triggered with any event that tries to bring up the ethernet interface
               (interface admin-state enable, a reboot, etc). While the hold-time up is running, the transceiver
               laser will be enabled, however the higher layers will not be notified that the interface is
               operationally up until the timer expires.";
          }
          leaf up-expires {
            config false;
            type srl_nokia-comm:date-and-time-delta;
            description
              "The remaining time until the hold-time up expires and the interface comes up.";
          }
          leaf down {
            type uint32 {
              range "0 | 100..86400000";
            }
            units "milliseconds";
            default "0";
            must "starts-with(../../../srl_nokia-if:name, 'ethernet') or (. = 0)" {
              error-message "hold-time down not supported on this interface";
            }
            must 'not(../../../breakout-mode) or (. = 0)' {
              error-message "hold-time down not configurable when breakout-mode is enabled";
            }
            must '. mod 50 = 0' {
              error-message "hold-time down must be a multiple of 50";
            }
            description
              "Holds link down events for the configured time

               The hold-time down behavior is triggered with events that try to bring the ethernet interface
               down and can change quickly. It is not triggered with an admin-state disable event or interface
               disable due to other internal reasons (such as fabric unavailability). When running, the
               interface will not be brought down till the timer expires. The typical use of the hold-time down
               is to provide stability and avoid the protocols to advertise/withdraw messages if there are
               flapping optics. The hold-time down is aborted if the user does admin-state disable or if the
               interface is disabled due to other internal reasons that prevent the traffic to be forwarded
               on the interface.";
          }
          leaf down-expires {
            config false;
            type srl_nokia-comm:date-and-time-delta;
            description
              "The remaining time until the hold-time down expires and the interface goes operationally down.";
          }
        }
        container crc-monitor {
          if-feature "srl_nokia-feat:crc-symbol-monitoring";
          must '( (./signal-failure/exponent < ./signal-degrade/exponent) or ((./signal-failure/exponent = ./signal-degrade/exponent) and (./signal-failure/multiplier >= ./signal-degrade/multiplier)))' {
            error-message "Signal-failure threshold must be equal to or larger than signal-degrade threshold";
          }
          description
            "Parameters for crc frame error monitoring

             Both a signal degrade and signal error threshold can be defined.
             Crossing of the signal degrade threshold triggers a notification
             Crossing of the signal failure threshold changes the interface operational state to down.
             Each threshold is defined using an exponent (N) and a multiplier (M) using the formula M*10E-N.";
          leaf admin-state {
            type srl_nokia-comm:admin-state;
            default "disable";
            must "(. = 'disable') or starts-with(../../../srl_nokia-if:name, 'ethernet')" {
              error-message "crc-monitor not supported on this interface";
            }
            must "(. = 'disable') or not(../../../breakout-mode)" {
              error-message "crc-monitor not configurable when breakout-mode is enabled";
            }
            description
              "Administrative state of crc monitoring on the port";
          }
          leaf window-size {
            type uint32 {
              range "5..60";
            }
            units "seconds";
            default "10";
            description
              "Sliding window size over which errors are measured";
          }
          container signal-degrade {
            description
              "Signal-degrade parameters to calculate threshold M*10E-N where M is the configured multiplier and N the configured exponent";
            leaf exponent {
              type uint32 {
                range "1..9";
              }
              default "5";
              description
                "Signal-degrade exponent";
            }
            leaf multiplier {
              type uint32 {
                range "1..9";
              }
              default "1";
              description
                "Signal-degrade multiplier";
            }
          }
          container signal-failure {
            description
              "Signal-failure parameters to calculate threshold M*10E-N where M is the configured multiplier and N the configured exponent";
            leaf exponent {
              type uint32 {
                range "1..9";
              }
              default "5";
              description
                "Signal-failure exponent";
            }
            leaf multiplier {
              type uint32 {
                range "1..9";
              }
              default "1";
              description
                "Signal-failure multiplier";
            }
          }
          leaf-list current-alarms {
            config false;
            type ethernet-monitor-report-status;
            description
              "Current alarms of the Ethernet CRC monitoring, raised when corresponding threshold is exceeded";
          }
        }
        container symbol-monitor {
          if-feature "srl_nokia-feat:crc-symbol-monitoring";
          must '( (./signal-failure/exponent < ./signal-degrade/exponent) or ((./signal-failure/exponent = ./signal-degrade/exponent) and (./signal-failure/multiplier >= ./signal-degrade/multiplier)))' {
            error-message "Signal-failure threshold must be equal to or larger than signal-degrade threshold";
          }
          description
            "Parameters for ethernet symbol monitoring

             Both a signal degrade and signal error threshold can be defined.
             Crossing of the signal degrade threshold triggers a notification
             Crossing of the signal failure threshold changes the interface operational state to down.
             Each threshold is defined using an exponent (N) and a multiplier (M) using the formula M*10E-N.";
          leaf admin-state {
            type srl_nokia-comm:admin-state;
            default "disable";
            must "(. = 'disable') or starts-with(../../../srl_nokia-if:name, 'ethernet')" {
              error-message "symbol-monitor not supported on this interface";
            }
            must "(. = 'disable') or not(../../../breakout-mode)" {
              error-message "symbol-monitor not configurable when breakout-mode is enabled";
            }
            description
              "Administrative state of symbol monitoring on the port";
          }
          leaf window-size {
            type uint32 {
              range "5..60";
            }
            units "seconds";
            default "10";
            description
              "Sliding window size over which errors are measured";
          }
          container signal-degrade {
            description
              "Signal-degrade parameters to calculate threshold M*10E-N where M is the configured multiplier and N the configured exponent";
            leaf exponent {
              type uint32 {
                range "1..9";
              }
              default "5";
              description
                "Signal-degrade exponent";
            }
            leaf multiplier {
              type uint32 {
                range "1..9";
              }
              default "1";
              description
                "Signal-degrade multiplier";
            }
          }
          container signal-failure {
            description
              "Signal-failure parameters to calculate threshold M*10E-N where M is the configured multiplier and N the configured exponent";
            leaf exponent {
              type uint32 {
                range "1..9";
              }
              default "5";
              description
                "Signal-failure exponent";
            }
            leaf multiplier {
              type uint32 {
                range "1..9";
              }
              default "1";
              description
                "Signal-failure multiplier";
            }
          }
          leaf-list current-alarms {
            config false;
            type ethernet-monitor-report-status;
            description
              "Current alarms of the Ethernet symbol monitoring, raised when corresponding threshold is exceeded";
          }
        }
        container exponential-port-dampening {
          if-feature "srl_nokia-feat:exponential-port-dampening";
          description
            "Exponential port dampening parameters";
          leaf admin-state {
            type srl_nokia-comm:admin-state;
            default "disable";
            description
              "Administrative state of exponential port dampening";
          }
          leaf half-life {
            type uint32 {
              range "1..2000";
            }
            units "seconds";
            default "5";
            description
              "Half-life decay time";
          }
          leaf max-suppress-time {
            type uint32 {
              range "1..43200";
            }
            units "seconds";
            default "20";
            description
              "Maximum suppression time";
          }
          leaf reuse-threshold {
            type uint32 {
              range "1..20000";
            }
            units "penalties";
            default "1000";
            description
              "Threshold which port-up state is no longer suppressed";
          }
          leaf suppress-threshold {
            type uint32 {
              range "1..20000";
            }
            units "penalties";
            default "2000";
            description
              "Threshold at which the port-up state is suppressed";
          }
          leaf current-penalties {
            config false;
            type srl_nokia-comm:zero-based-counter64;
            description
              "Indicates the accumulated penalties applied to the port

               Penalties are accumulated on every port down event except a system restart.";
          }
          leaf max-penalties {
            config false;
            type srl_nokia-comm:zero-based-counter64;
            description
              "Indicates the maximum possible value of the accumulated penalties against the port";
          }
          leaf oper-state {
            config false;
            type enumeration {
              enum active {
                value 1;
              }
              enum idle {
                value 2;
              }
            }
            description
              "Indicates if the port up state of the port is suppressed or not

               The port up state is 'idle' if the value of current-penalties
               exceeds the value of suppress-threshold. The port up state will
               be 'active' when current-penalties falls below the value of
               reuse-threshold.";
          }
        }
        container storm-control {
          if-feature "srl_nokia-feat:storm-control";
          presence "Configures the storm-control parameters";
          must "starts-with(../../srl_nokia-if:name, 'ethernet')" {
            error-message "storm-control not supported on this interface";
          }
          must 'not(../../breakout-mode)' {
            error-message "storm-control not configurable when breakout-mode is enabled";
          }
          leaf units {
            type enumeration {
              enum kbps;
              enum percentage;
            }
            default "percentage";
            description
              "Units of storm-control policer in kbps or percentage of the interface bandwidth";
          }
          leaf broadcast-rate {
            must "not(../units = 'percentage' and (. >100))" {
              error-message "The valid percentage range is between 0% and 100%";
            }
            type uint32 {
              range "0..132000000";
            }
            description
              "The maximum rate allowed for ingress broadcast frames on the interface

               The rate can be set in multiple of 64kbps. If the rate is configured to any value
               in the 1-127 kbps range, the effective rate will be 64kbps and shown in the
               operational rate. If any value in the 128-191 range, the effective rate will be
               128kbps and shown in the operational rate, and so on for higher rates. When the
               rate is set to zero, all the broadcast traffic in the interface is discarded.

               The maximum rate that can be effectively configured in 7220 D4/D5 platforms is
               132000000. When a configured percentage exceeds that value, the maximum supported
               rate is set and shown in the operational-broadcast-rate.";
          }
          leaf multicast-rate {
            must "not(../units = 'percentage' and (. >100))" {
              error-message "The valid percentage range is between 0% and 100%";
            }
            type uint32 {
              range "0..132000000";
            }
            description
              "The maximum rate allowed for ingress multicast frames on the interface

               The rate can be set in multiple of 64kbps. If the rate is configured to any value
               in the 1-127 kbps range, the effective rate will be 64kbps and shown in the
               operational rate. If any value in the 128-191 range, the effective rate will be
               128kbps and shown in the operational rate, and so on for higher rates. When the
               rate is set to zero, all the multicast traffic in the interface is discarded.

               The maximum rate that can be effectively configured in 7220 D4/D5 platforms is
               132000000. When a configured percentage exceeds that value, the maximum supported
               rate is set and shown in the operational-multicast-rate.";
          }
          leaf unknown-unicast-rate {
            must "not(../units = 'percentage' and (. >100))" {
              error-message "The valid percentage range is between 0% and 100%";
            }
            type uint32 {
              range "0..132000000";
            }
            description
              "The maximum rate allowed for ingress unknown unicast frames on the interface

               The rate can be set in multiple of 64kbps. If the rate is configured to any value
               in the 1-127 kbps range, the effective rate will be 64kbps and shown in the
               operational rate. If any value in the 128-191 range, the effective rate will be
               128kbps and shown in the operational rate, and so on for higher rates. When the
               rate is set to zero, all the unknown unicast traffic in the interface is discarded.

               The maximum rate that can be effectively configured in 7220 D4/D5 platforms is
               132000000. When a configured percentage exceeds that value, the maximum supported
               rate is set and shown in the operational-multicast-rate.";
          }
          leaf operational-broadcast-rate {
            config false;
            type uint32;
            units "kbps";
            description
              "The operational maximum rate for ingress broadcast frames programmed on the interface";
          }
          leaf operational-multicast-rate {
            config false;
            type uint32;
            units "kbps";
            description
              "The operational maximum rate for ingress multicast frames programmed on the interface";
          }
          leaf operational-unknown-unicast-rate {
            config false;
            type uint32;
            units "kbps";
            description
              "The operational maximum rate for ingress unknown unicast frames programmed on the interface";
          }
          leaf rising-threshold-action {
            if-feature "srl_nokia-feat:storm-control-action";
            type enumeration {
              enum none {
                description
                  "No action is triggered upon exceeding any of the storm-control configured rates";
              }
              enum trigger-event {
                description
                  "An event is triggered upon exceeding any of the storm-control configured rates";
              }
              enum disable-interface {
                description
                  "the interface is disabled upon exceeding any of the storm-control configured rates";
              }
            }
            default "none";
            description
              "Configures the action triggered when traffic exceeds the configured storm-control rates";
          }
        }
        container synce {
          if-feature "srl_nokia-feat:sync";
          presence "Configures the synce parameters";
          must "(starts-with(../../srl_nokia-if:name, 'ethernet') or starts-with(../../srl_nokia-if:name, 'sync'))" {
            error-message "synce not supported on this interface";
          }
          must 'not(../../breakout-mode)' {
            error-message "synce not configurable when breakout-mode is enabled";
          }
          description
            "This struct containing all attributes for SyncE in line/client ports.";
          container ssm {
            description
              "This struct containing all attributes for QL/SSM with SyncE in these ports.";
            leaf admin-state {
              type srl_nokia-comm:admin-state;
              default "disable";
              description
                "Configure the administrative state for SyncE in line/client ports.
                 When enabled, the associated transmit and receiver ports are set to
                 synchronous mode and ESMC/SSM processing is enabled.
                 Otherwise, all syncE functions are disabled in the port.";
            }
          }
        }
        container statistics {
          config false;
          leaf in-mac-pause-frames {
            type srl_nokia-comm:zero-based-counter64;
            description
              "Number of MAC layer PAUSE frames received on the interface.";
          }
          leaf in-oversize-frames {
            type srl_nokia-comm:zero-based-counter64;
            description
              "Number of oversize frames received on the interface (i.e. frames that exceed the operational port MTU)";
          }
          leaf in-jabber-frames {
            type srl_nokia-comm:zero-based-counter64;
            description
              "Number of jabber frames received on the interface. Jabber frames are typically defined as oversize frames which also have a bad CRC";
          }
          leaf in-fragment-frames {
            type srl_nokia-comm:zero-based-counter64;
            description
              "Number of fragment frames received on the interface";
          }
          leaf in-crc-error-frames {
            type srl_nokia-comm:zero-based-counter64;
            description
              "Number of receive error events due to FCS/CRC check failure";
          }
          leaf out-mac-pause-frames {
            type srl_nokia-comm:zero-based-counter64;
            description
              "Number of MAC layer PAUSE frames sent on the interface";
          }
          leaf in-64b-frames {
            type srl_nokia-comm:zero-based-counter64;
            description
              "Number of received Ethernet frames that are exactly 64 bytes in length";
          }
          leaf in-65b-to-127b-frames {
            type srl_nokia-comm:zero-based-counter64;
            description
              "Number of received Ethernet frames that are 65-127 bytes in length";
          }
          leaf in-128b-to-255b-frames {
            type srl_nokia-comm:zero-based-counter64;
            description
              "Number of received Ethernet frames that are 128-255 bytes in length";
          }
          leaf in-256b-to-511b-frames {
            type srl_nokia-comm:zero-based-counter64;
            description
              "Number of received Ethernet frames that are 256-511 bytes in length";
          }
          leaf in-512b-to-1023b-frames {
            type srl_nokia-comm:zero-based-counter64;
            description
              "Number of received Ethernet frames that are 512-1023 bytes in length";
          }
          leaf in-1024b-to-1518b-frames {
            type srl_nokia-comm:zero-based-counter64;
            description
              "Number of received Ethernet frames that are 1024-1518 bytes in length";
          }
          leaf in-1519b-or-longer-frames {
            type srl_nokia-comm:zero-based-counter64;
            description
              "Number of received Ethernet frames that are 1519 bytes or longer";
          }
          leaf out-64b-frames {
            type srl_nokia-comm:zero-based-counter64;
            description
              "Number of transmitted Ethernet frames that are exactly 64 bytes in length";
          }
          leaf out-65b-to-127b-frames {
            type srl_nokia-comm:zero-based-counter64;
            description
              "Number of transmitted Ethernet frames that are 65-127 bytes in length";
          }
          leaf out-128b-to-255b-frames {
            type srl_nokia-comm:zero-based-counter64;
            description
              "Number of transmitted Ethernet frames that are 128-255 bytes in length";
          }
          leaf out-256b-to-511b-frames {
            type srl_nokia-comm:zero-based-counter64;
            description
              "Number of transmitted Ethernet frames that are 256-511 bytes in length";
          }
          leaf out-512b-to-1023b-frames {
            type srl_nokia-comm:zero-based-counter64;
            description
              "Number of transmitted Ethernet frames that are 512-1023 bytes in length";
          }
          leaf out-1024b-to-1518b-frames {
            type srl_nokia-comm:zero-based-counter64;
            description
              "Number of transmitted Ethernet frames that are 1024-1518 bytes in length";
          }
          leaf out-1519b-or-longer-frames {
            type srl_nokia-comm:zero-based-counter64;
            description
              "Number of transmitted Ethernet frames that are 1519 bytes or longer";
          }
          leaf last-clear {
            type srl_nokia-comm:date-and-time-delta;
            description
              "Timestamp of the last time the MAC counters were cleared";
          }
        }
      }
      container load-balancing {
        if-feature "srl_nokia-feat:per-port-hash-seed and srl_nokia-feat:load-balancing";
        description
          "Configure load-balancing options specific to the interface";
        leaf hash-profile {
          if-feature "srl_nokia-feat:system-hash-profile";
          description
            "Reference to a configured hash-profile

             If an Ethernet port associated with a J3 ASIC does not specify a hash-profile then a per-port hash-seed is randomly generated.";
          type leafref {
            path "/srl_nokia-sys:system/srl_nokia-lb:load-balancing/srl_nokia-lb:hash-profile/srl_nokia-lb:name";
          }
          must "(starts-with(../../srl_nokia-if:name, 'ethernet') or starts-with(../../srl_nokia-if:name, 'lag'))" {
            error-message "hash-profile is supported for ethernet and lag interfaces only";
          }
          must 'not(../../breakout-mode)' {
            error-message "hash-profile not configurable when breakout-mode is enabled";
          }
        }
        leaf hash-seed {
          config false;
          description
            "Load-balancing hash seed used for incoming traffic on the port";
          type uint16;
        }
      }
      uses subinterface-top;
      uses interface-sflow-config;
    }
  }

  uses interface-top;
}
