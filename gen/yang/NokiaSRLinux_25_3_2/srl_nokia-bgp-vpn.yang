module srl_nokia-bgp-vpn {
  yang-version 1.1;
  namespace "urn:nokia.com:srlinux:bgp:bgp-vpn";
  prefix srl_nokia-bgp-vpn;

  import srl_nokia-common {
    prefix srl_nokia-comm;
  }
  import srl_nokia-features {
    prefix srl_nokia-feat;
  }
  import srl_nokia-network-instance {
    prefix srl_nokia-netinst;
  }
  import srl_nokia-extensions {
    prefix srl_nokia-ext;
  }
  import srl_nokia-policy-types {
    prefix srl_nokia-pol-types;
  }

  organization
    "Nokia";
  contact
    "Nokia SR Linux Support
     Web: <http://www.nokia.com>";
  description
    "This yang file models configuration and state of the bgp-vpn protocols (EVPN and IPVPN).";

  revision 2025-03-31 {
    description
      "SRLinux 2025.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2022-06-30 {
    description
      "SRLinux 22.6.1";
  }
  revision 2021-03-31 {
    description
      "SRLinux 21.3.1";
  }

  grouping bgp-vpn-top {
    description
      "Top-level grouping containing a list of bgp-vpn instances.";
    container bgp-vpn {
      description
        "Top-level configuration and operational state for common bgp-ipvpn and bgp-evpn parameters";
      presence "Configuration and state of bgp-vpn.";
      must '(/srl_nokia-netinst:network-instance[srl_nokia-netinst:name = current()/../../srl_nokia-netinst:name]/srl_nokia-netinst:type != "srl_nokia-netinst:default")' {
        error-message "The bgp-vpn configuration is not possible on network-instance of type default.";
      }
      must '(/srl_nokia-netinst:network-instance[srl_nokia-netinst:name = current()/../../srl_nokia-netinst:name]/srl_nokia-netinst:type != "srl_nokia-netinst:host")' {
        error-message "The bgp-vpn configuration is not possible on network-instance of type host.";
      }
      list bgp-instance {
        key "id";
        max-elements 2;
        description
          "List of bgp-vpn instances configured in the network-instance. Only one instance allowed in the current release.";
        leaf id {
          type uint8 {
            range "1..2";
          }
          description
            "The index of the bgp-vpn instance";
        }
        container route-distinguisher {
          description
            "Route Distinguisher (RD) of the bgp-vpn instance.";
          leaf rd {
            srl_nokia-ext:show-importance "high";
            type srl_nokia-comm:route-distinguisher;
            description
              "Route Distinguisher (RD) in the bgp-vpn instance. When used for evpn and if not configured, the RD is auto-derived
               as <ip-address>:<evi> where 'ip-address' is the ipv4 address associated to the subinterface lo0.1.";
            must 'not(starts-with(string(.), "0:"))' {
              error-message "invalid value 0:*";
            }
            must 'not(starts-with(string(.), "0.0:"))' {
              error-message "invalid value 0.0:*";
            }
            must 'not(starts-with(string(.), "0.0.0.0:") and (number(substring-after(string(.), ":")) < 513))' {
              error-message "route-distinguisher value reserved";
            }
          }
          leaf route-distinguisher-origin {
            config false;
            srl_nokia-ext:show-importance "high";
            type enumeration {
              enum auto-derived-from-evi;
              enum auto-derived-from-system-ip:0;
              enum manual;
              enum none;
            }
            description
              "Origin of the operational Route Distinguisher (RD) of the bgp-vpn instance.

                'Auto-derived-from-evi' refers to an RD that is automatically allocated with the format <ip-address>:<evi>
                where 'ip-address' is the ipv4 address associated to the subinterface lo0.1.
                'Auto-derived-from-system-ip:0' refers to the RD for the EVPN Ethernet Segment routes that is automatically allocated with the format <ip-address>:0
                where 'ip-address' is the ipv4 address associated to the subinterface lo0.1.
                'Manual' refers to an RD that is configured.
                'None' indicates that the RD is neither configured nor auto-derived.";
          }
        }
        container route-target {
          description
            "Route Target (RT) of the bgp-vpn instance.";
          leaf export-rt {
            srl_nokia-ext:show-importance "high";
            type srl_nokia-pol-types:bgp-ext-community-type;
            must "starts-with(.,'target')";
            description
              "Export Route Target (RT) in the bgp-vpn instance. When used for evpn and if not configured, the RT is auto-derived
               with the format <asn>:<evi> where 'asn' is the autonomous-system configured in the network-instance default.";
          }
          leaf import-rt {
            srl_nokia-ext:show-importance "high";
            type srl_nokia-pol-types:bgp-ext-community-type;
            must "starts-with(.,'target')";
            description
              "Import Route Target (RT) in the bgp-vpn instance. When used for evpn and if not configured, the RT is
               auto-derived with the format <asn>:<evi> where 'asn' is the autonomous-system configured in the network-instance default.";
          }
        }
      }
    }
  }

  augment "/srl_nokia-netinst:network-instance/srl_nokia-netinst:protocols" {
    uses bgp-vpn-top;
  }
}
