module srl_nokia-bgp-evpn {
  yang-version 1.1;
  namespace "urn:nokia.com:srlinux:net-inst:bgp-evpn";
  prefix srl_nokia-bgp-evpn;

  import srl_nokia-common {
    prefix srl_nokia-comm;
  }
  import srl_nokia-network-instance {
    prefix srl_nokia-netinst;
  }
  import srl_nokia-extensions {
    prefix srl_nokia-ext;
  }
  import srl_nokia-bgp-vpn {
    prefix srl_bgp-vpn;
  }
  import srl_nokia-bgp {
    prefix srl-bgp;
  }
  import srl_nokia-routing-policy {
    prefix srl_nokia-routing-pol;
  }
  import srl_nokia-features {
    prefix srl_nokia-feat;
  }

  organization
    "Nokia";
  contact
    "Nokia SR Linux Support
     Web: <http://www.nokia.com>";
  description
    "This yang file models configuration and state of the bgp-evpn protocol";

  revision 2024-10-31 {
    description
      "SRLinux 24.10.1";
  }
  revision 2024-07-31 {
    description
      "SRLinux 24.7.1";
  }
  revision 2024-03-31 {
    description
      "SRLinux 24.3.1";
  }
  revision 2023-07-31 {
    description
      "SRLinux 23.7.1";
  }
  revision 2023-03-31 {
    description
      "SRLinux 23.3.1";
  }
  revision 2022-06-30 {
    description
      "SRLinux 22.6.1";
  }
  revision 2022-03-31 {
    description
      "SRLinux 22.3.1";
  }
  revision 2021-11-30 {
    description
      "SRLinux 21.11.1";
  }
  revision 2021-03-31 {
    description
      "SRLinux 21.3.1";
  }

  grouping bgp-evpn-top {
    description
      "Top-level grouping containing the bgp-evpn configuration and state.";
    list bgp-instance {
      key "id";
      max-elements 1;
      description
        "bgp evpn instances configured in net-instance";
      leaf id {
        type uint8 {
          range "1..2";
        }
        description
          "The index of the bgp-vpn instance";
      }
      leaf admin-state {
        type srl_nokia-comm:admin-state;
        default "enable";
        description
          "Configurable state of the bgp evpn instance.";
      }
      leaf vxlan-interface {
        if-feature "srl_nokia-feat:vxlan";
        must "../encapsulation-type = 'vxlan'" {
          error-message "supported only when encapsulation is vxlan";
        }
        type leafref {
          path "../../../../srl_nokia-netinst:vxlan-interface/srl_nokia-netinst:name";
        }
        description
          "Identifier of vxlan-interface used in this bgp-instance.";
      }
      leaf evi {
        type srl_nokia-comm:evi;
        description
          "EVPN Instance identifier associated to the bgp-evpn instance.

           Used for auto-derivation of:
           - the bgp-instance route distinguisher in the format <ip-address>:evi (where 'ip-address' is the ipv4 address
             associated to the subinterface lo0.1.
           - the bgp-instance route target in the format <asn>:<evi>, where 'asn' is the autonomous-system configured in
             the network-instance default (under /protocols/bgp/autonomous-system).

           In addition, the evi value is used for the EVPN Multi-Homing Designated Forwarder (DF) Election.";
        mandatory true;
      }
    }
  }

  augment "/srl_nokia-netinst:network-instance/srl_nokia-netinst:protocols/srl_nokia-netinst:bgp-evpn" {
    uses bgp-evpn-top;
  }
}
