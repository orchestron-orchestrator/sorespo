module srl_nokia-network-instance {
  yang-version 1.1;
  namespace "urn:nokia.com:srlinux:net-inst:network-instance";
  prefix srl_nokia-netinst;

  import srl_nokia-common {
    prefix srl_nokia-comm;
  }
  import srl_nokia-interfaces {
    prefix srl_nokia-if;
  }
  import srl_nokia-extensions {
    prefix srl_nokia-ext;
  }
  import srl_nokia-features {
    prefix srl-feat;
  }

  organization
    "Nokia";
  contact
    "Nokia SR Linux Support
     Web: <http://www.nokia.com>";
  description
    "This yang file gives a description of a network-instance. This may be a Layer 3 forwarding construct such as a virtual routing and forwarding (VRF) instance, or a Layer 2 instance such as a virtual switch instance (VSI). Mixed Layer 2 and Layer 3 instances are also supported.";

  revision 2025-03-31 {
    description
      "SRLinux 2025.3.1";
  }
  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef network-instance-subintf-name {
    type string {
      length "1..255";
    }
    description
      "User defined name or reference type to a specific subinterface of the form <interface-name>.<subinterface-index>";
  }

  typedef network-instance-vxlan-if-ref {
    type string {
      length "8..17";
      pattern '(vxlan(0|1[0-9][0-9]|2([0-4][0-9]|5[0-5])|[1-9][0-9]|[1-9])\.(0|[1-9](\d){0,8}))';
    }
    description
      "Reference type to a specific vxlan-interface of the form <tunnel-interface-name>.<vxlan-interface-index>";
  }

  identity ni-type {
    description
      "Base type for network instance types.";
  }

  identity host {
    base ni-type;
    if-feature "srl-feat:host-network-instance";
    description
      "A special routing instances that refers to the hosts network instance (i.e. the network namespace of PID 1)";
  }

  identity default {
    base ni-type;
    description
      "A special routing instance which acts as the 'default' routing instance for a network device.";
  }

  identity ip-vrf {
    base ni-type;
    description
      "A private Layer 3 only routing instance.";
  }

  identity mac-vrf {
    if-feature "srl-feat:bridged";
    base ni-type;
    description
      "A private Layer 2 only switching instance.";
  }

  identity vpws {
    if-feature "srl-feat:vpws";
    base ni-type;
    description
      "A private Layer 2 point-to-point instance.";
  }

  grouping network-instance-top {
    description
      "Top-level grouping containing a list of network instances.";
    list network-instance {
      key "name";
      description
        "Network instances configured on the local system";
      leaf name {
        type srl_nokia-comm:restricted-name;
        description
          "A unique name identifying the network instance";
      }
      leaf type {
        type identityref {
          base ni-type;
        }
        default "default";
        description
          "The type of network instance. The value of this leaf
           indicates the type of forwarding entries that should be
           supported by this network instance";
      }
      leaf admin-state {
        type srl_nokia-comm:admin-state;
        default "enable";
        description
          "This leaf contains the configured, desired state of the
           network instance.";
      }
      leaf description {
        type srl_nokia-comm:description;
        description
          "A user-entered description of this network instance.";
      }
      leaf router-id {
        type srl_nokia-comm:dotted-quad;
        must "(../type = 'srl_nokia-netinst:ip-vrf' or ../type = 'srl_nokia-netinst:default')" {
          error-message "Router-id configuration is not possible on network-instance of types other than ip-vrf or default";
        }
        description
          "A identifier for the local network instance - typically
           used within associated routing protocols or signalling
           routing information in another network instance";
      }

      list interface {
        key "name";
        description
          "List of subinterfaces used by this network-instance";
        must "../type != 'srl_nokia-netinst:host'" {
          error-message "Interfaces cannot be added to a network instance of type host";
        }
        leaf name {
          type srl_nokia-netinst:network-instance-subintf-name;
          description
            "Name of the subinterface bound to this network-instance";
          must "../interface-ref/interface or not(starts-with(.,'lo') and ../../type = 'srl_nokia-netinst:mac-vrf')" {
            error-message "Loopback interfaces cannot be configured on network-instance of type mac-vrf";
          }
          must "../interface-ref/interface or not(starts-with(.,'system') and ../../type != 'srl_nokia-netinst:default')" {
            error-message "System interfaces can only be configured on network-instance of type default";
          }
          must "../interface-ref/interface or /srl_nokia-if:interface[srl_nokia-if:name=substring-before(current(), '.')]/srl_nokia-if:subinterface[srl_nokia-if:index=substring-after(current(), '.')]/srl_nokia-if:type != 'local-mirror-dest'" {
            error-message "subinterface with type local-mirror-dest cannot be configured on network-instance";
          }
          must "../interface-ref/interface or not(starts-with(.,'irb') and ../../bridge-table/proxy-arp)" {
            error-message "IRB interfaces cannot be configured with proxy-arp";
          }
          must "../interface-ref/interface or not(starts-with(.,'irb') and ../../bridge-table/proxy-nd)" {
            error-message "IRB interfaces cannot be configured with proxy-nd";
          }
        }
        container interface-ref {
          if-feature "srl-feat:interface-references";
          description
            "Reference to a subinterface";
          leaf interface {
            type leafref {
              path "/srl_nokia-if:interface/srl_nokia-if:name";
            }
            description
              "Reference to a base interface, for example a port or LAG";
            must '../subinterface >= 0' {
              error-message "subinterface must be configured when interface is set";
            }
            must "not(starts-with(.,'lo') and ../../../type = 'srl_nokia-netinst:mac-vrf')" {
              error-message "Loopback interfaces cannot be configured on network-instance of type mac-vrf";
            }
            must "not(starts-with(.,'system') and ../../../type != 'srl_nokia-netinst:default')" {
              error-message "System interfaces can only be configured on network-instance of type default";
            }
            must "/srl_nokia-if:interface[srl_nokia-if:name=current()]/srl_nokia-if:subinterface[srl_nokia-if:index=current()/../subinterface]/srl_nokia-if:type != 'local-mirror-dest'" {
              error-message "subinterface with type local-mirror-dest cannot be configured on network-instance";
            }
            must "not(starts-with(.,'irb') and ../../../bridge-table/proxy-arp)" {
              error-message "IRB interfaces cannot be configured with proxy-arp";
            }
            must "not(starts-with(.,'irb') and ../../../bridge-table/proxy-nd)" {
              error-message "IRB interfaces cannot be configured with proxy-nd";
            }
          }
          leaf subinterface {
            type leafref {
              path "/srl_nokia-if:interface[srl_nokia-if:name=current()/../interface]/srl_nokia-if:subinterface/srl_nokia-if:index";
            }
            description
              "Reference to a subinterface
               This requires the base interface to be specified using the interface leaf in this container.";
            must '../interface' {
              error-message "interface must be configured when subinterface is set";
            }
          }
        }
      }
      list vxlan-interface {
        if-feature "srl-feat:vxlan";
        key "name";
        max-elements 1;
        must '(/srl_nokia-netinst:network-instance[srl_nokia-netinst:name = current()/srl_nokia-netinst:name]/srl_nokia-netinst:type != "srl_nokia-netinst:default")' {
          error-message "The bgp-evpn configuration is not possible on network-instance of type default.";
        }
        description
          "List of vxlan-interfaces used by this network-instance";
        leaf name {
          type srl_nokia-netinst:network-instance-vxlan-if-ref;
          must "(starts-with(.,'vxlan'))" {
            error-message "vxlan-interface name must start with the string vxlan";
          }
          must "../../type != 'srl_nokia-netinst:host'" {
            error-message "vxlan-interface cannot be added to a network instance of type host";
          }
          description
            "Identifier of vxlan-interface used in this network-instance";
        }
      }
      container protocols {
        description
          "The routing protocols that are enabled for this
           network-instance.";
        container bgp-evpn {
          if-feature "srl-feat:evpn";
          description
            "Top-level configuration and operational state for BGP Ethernet Virtual Private Networks (EVPN)";
          presence "Configure BGP-EVPN";
          must '(/srl_nokia-netinst:network-instance[srl_nokia-netinst:name = current()/../../srl_nokia-netinst:name]/srl_nokia-netinst:type != "srl_nokia-netinst:default")' {
            error-message "The bgp-evpn configuration is not possible on network-instance of type default.";
          }
        }
        container bgp-ipvpn {
          if-feature "srl-feat:ipvpn";
          description
            "Top-level configuration and operational state for BGP IP Virtual Private Networks (IPVPN)";
          presence "Configure BGP-IPVPN";
          must '(/srl_nokia-netinst:network-instance[srl_nokia-netinst:name = current()/../../srl_nokia-netinst:name]/srl_nokia-netinst:type = "srl_nokia-netinst:ip-vrf")' {
            error-message "The bgp-ipvpn configuration is only possible on network-instance of type ip-vrf";
          }
        }
        container directly-connected {
          if-feature "srl-feat:traffic-engineering-bgpls-directly-connected";
          description
            "Container for handling directly connected routes as a pseudo-protocol";
        }
      }

    }
  }

  uses network-instance-top;
}
