module sorespo-rfs {
    yang-version "1.1";
    namespace "http://example.com/sorespo-rfs";
    prefix "sorespo-rfs";

    import orchestron-rfs {
        prefix orfs;
    }
    import ietf-inet-types {
      prefix inet;
    }

    augment "/orfs:rfs" {
        // TODO: should really be a P-container
        list base-config {
            key name;

            orchestron:rfs-transform sorespo.rfs.BaseConfig;

            leaf name {
                type string;
            }

            leaf ipv4-address {
                type string;
                mandatory true;
            }
        }
  }
}
