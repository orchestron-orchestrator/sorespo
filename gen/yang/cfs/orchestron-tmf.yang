module orchestron-tmf {
  yang-version "1.1";
  namespace "http://orchestron.org/yang/orchestron-tmf";
  prefix "otmf";
  import orchestron-tmf640 {
    prefix otmf640;
  }
  description "Orchestron TMF";
  revision 2025-10-26 {
    description "Initial revision";
  }

  container tmf-store {
    description "TMF Data Store";
    container tmf640 {
      description "TMF640 - Service Activation and Configuration";
      list service {
        key id;
        orchestron:transform sorespo.tmf.store.Tmf640Store;
        uses otmf640:Service;
      }
    }
  }
}
