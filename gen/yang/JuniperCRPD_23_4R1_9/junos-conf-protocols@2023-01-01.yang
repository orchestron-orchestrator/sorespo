module junos-conf-protocols {
  namespace "http://yang.juniper.net/junos/conf/protocols";
  prefix "jc-protocols";
  import junos-common-types {
    prefix "jt";
    revision-date 2023-01-01;
  }
  import junos-conf-root {
    prefix "jc";
    revision-date 2023-01-01;
  }
  organization "Juniper Networks, Inc.";
  contact "yang-support@juniper.net";
  description "Junos protocols configuration module";
  revision 2023-01-01 {
    description "Junos: 23.4R1.10";
  }
  augment "/jc:configuration" {
    uses protocols-group;
  }
  grouping protocols-group {
    container protocols {
      description "Routing protocol configuration";
      uses juniper-protocols;
    }
  }
  grouping juniper-protocols {
    container bgp {
      description "BGP options";
      uses juniper-protocols-bgp;
    }
    container isis {
      description "IS-IS options";
      uses juniper-protocols-isis;
    }
    container ldp {
      description "LDP options";
      uses juniper-protocols-ldp;
    }
    container mpls {
      description "Multiprotocol Label Switching options";
      uses juniper-protocols-mpls;
    }
  }
  grouping admin_group_include_exclude {
    choice include-any-choice {
      case case_1 {
        leaf-list include-any {
          ordered-by user;
          description "Groups, one or more of which must be present";
          type string;
        }
      }
    }
    choice include-all-choice {
      case case_1 {
        leaf-list include-all {
          ordered-by user;
          description "Groups, all of which must be present";
          type string;
        }
      }
    }
    choice exclude-choice {
      case case_1 {
        leaf-list exclude {
          ordered-by user;
          description "Groups, all of which must be absent";
          type string;
        }
      }
    }
  }
  grouping apply-advanced {
    description "Apply advanced configuration logic";
    leaf-list apply-groups {
      ordered-by user;
      description "Groups from which to inherit configuration data";
      type string;
    }
    leaf-list apply-groups-except {
      ordered-by user;
      description "Don't inherit configuration data from these groups";
      type string;
    }
    list apply-macro {
      key name;
      ordered-by user;
      description "Macro and parameters for commit script expansion";
      uses apply-macro-type;
    }
  }
  grouping apply-macro-type {
    description "Macro data for commit-script expansion";
    leaf name {
      description "Name of the macro to be expanded";
      type string;
    }
    list data {
      key name;
      uses macro-data-type;
    }
  }
  grouping bandwidth-type {
    leaf per-traffic-class-bandwidth {
      description "Bandwidth to reserve";
      units bps;
      type string;
    }
    leaf ct0 {
      description "Bandwidth from traffic class 0";
      units bps;
      type string;
    }
    leaf ct1 {
      description "Bandwidth from traffic class 1";
      units bps;
      type string;
    }
    leaf ct2 {
      description "Bandwidth from traffic class 2";
      units bps;
      type string;
    }
    leaf ct3 {
      description "Bandwidth from traffic class 3";
      units bps;
      type string;
    }
  }
  grouping cfm-traceoptions {
    description "Trace options for connectivity fault management";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    list flag {
      key name;
      ordered-by user;
      description "Tracing parameters";
      leaf name {
        type enumeration {
          enum configuration {
            description "Trace configuration events";
          }
          enum routing-socket {
            description "Trace routing socket events";
          }
          enum protocol {
            description "Trace protocol processing events";
          }
          enum init {
            description "Trace events related to protocol daemon start-up";
          }
          enum error {
            description "Trace events related to catestrophic errors in daemon";
          }
          enum issu {
            description "Trace ISSU related events";
          }
          enum all {
            description "Trace everything";
          }
        }
      }
    }
  }
  grouping civic-address-elements {
    leaf what {
      description "Type of address";
      default "1";
      type union {
        type string {
          pattern "<.*>|$.*";
        }
        type uint16 {
          range "0 .. 2";
        }
      }
    }
    leaf country-code {
      description "Two-letter country code";
      type string {
        length "2";
      }
    }
    list ca-type {
      key name;
      ordered-by user;
      leaf name {
        description "Address element type";
        type union {
          type string {
            pattern "<.*>|$.*";
          }
          type uint16 {
            range "0 .. 255";
          }
        }
      }
      leaf ca-value {
        description "Address element value";
        type string {
          length "1 .. 248";
        }
      }
    }
  }
  grouping clksync-traceoptions {
    description "Trace options for syncE and PTP";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    list flag {
      key name;
      ordered-by user;
      description "Tracing parameters";
      leaf name {
        type enumeration {
          enum init {
            description "Trace daemon start-up related events";
          }
          enum routing-socket {
            description "Trace routing-socket events";
          }
          enum synchronization {
            description "Trace esmc protocol events only";
          }
          enum ptp {
            description "Trace ptp protocol events only";
          }
          enum protocol {
            description "Trace protocol events";
          }
          enum configuration {
            description "Trace configuration events";
          }
          enum debug {
            description "Trace generic debug events";
          }
          enum ppm {
            description "Trace periodic packet management events";
          }
          enum error {
            description "Trace error events";
          }
          enum hybrid {
            description "Trace hybrid events";
          }
          enum framer {
            description "Trace BITS framer events";
          }
          enum ipc {
            description "Trace IPC messages";
          }
          enum all {
            description "Trace everything";
          }
        }
      }
    }
  }
  grouping co-ordinate-elements {
    description "Geographical co-ordinates";
    leaf longitude {
      description "Longitude value";
      type union {
        type string {
          pattern "<.*>|$.*";
        }
        type uint16 {
          range "0 .. 360";
        }
      }
    }
    leaf lattitude {
      description "Lattitude value";
      type union {
        type string {
          pattern "<.*>|$.*";
        }
        type uint16 {
          range "0 .. 360";
        }
      }
    }
  }
  grouping juniper-default-ri-protocols-igmp-snooping {
    description "IGMP snooping options";
    list vlan {
      key name;
      ordered-by user;
      description "VLAN options";
      leaf name {
        description "VLAN name";
        type string;
      }
      container traceoptions {
        description "Trace options for IGMP Snooping";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum packets {
                description "Trace all IGMP packets";
              }
              enum query {
                description "Trace IGMP membership query messages";
              }
              enum report {
                description "Trace membership report messages";
              }
              enum leave {
                description "Trace leave group messages (IGMPv2 only)";
              }
              enum group {
                description "Trace group operations";
              }
              enum client-notification {
                description "Trace notifications";
              }
              enum route {
                description "Trace routing information";
              }
              enum normal {
                description "Trace normal events";
              }
              enum general {
                description "Trace general events";
              }
              enum state {
                description "Trace state transitions";
              }
              enum task {
                description "Trace routing protocol task processing";
              }
              enum timer {
                description "Trace routing protocol timer processing";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
      leaf query-interval {
        description "When to send host query messages";
        default "125";
        units seconds;
        type union {
          type string {
            pattern "<.*>|$.*";
          }
          type uint32 {
            range "1 .. 1024";
          }
        }
      }
      container l2-querier {
        description "Enable L2 querier mode";
        leaf source-address {
          description "Source IP address to use for L2 querier";
          type jt:ipv4addr;
        }
      }
      leaf query-response-interval {
        description "How long to wait for a host query response";
        default "10";
        units seconds;
        type string;
      }
      leaf query-last-member-interval {
        description "When to send group query messages";
        default "1";
        units seconds;
        type string;
      }
      leaf robust-count {
        description "Expected packet loss on a subnet";
        default "2";
        type union {
          type string {
            pattern "<.*>|$.*";
          }
          type uint32 {
            range "2 .. 10";
          }
        }
      }
      leaf immediate-leave {
        description "Enable immediate group leave on interfaces";
        type empty;
      }
      container proxy {
        presence "enable proxy";
        description "Enable proxy mode";
        leaf source-address {
          description "Source IP address to use for proxy";
          type jt:ipv4addr;
        }
      }
      leaf evpn-ssm-reports-only {
        description "Accept and process only <s,g> reports of SSM groups";
        type empty;
      }
      container data-forwarding {
        description "MVR Data forwarding options";
        choice source_receiver {
          case case_1 {
            container source {
              description "MVR source vlan";
              leaf groups {
                description "Group range";
                type jt:ipv4prefix;
              }
            }
          }
          case case_2 {
            container receiver {
              description "MVR receiver vlan";
              choice enab_disab_translate {
                case case_1 {
                  leaf translate {
                    description "Translate vid of outgoing pkt to receiver vlan's tag";
                    type empty;
                  }
                }
              }
              list source-list {
                key name;
                ordered-by user;
                description "Source VLANs for this receiver vlan";
                leaf name {
                  description "VLAN name";
                  type string;
                }
              }
              leaf install {
                description "Install forwarded bridging entires";
                type empty;
              }
              leaf mode {
                description "MVR Mode";
                default "transparent";
                type enumeration {
                  enum transparent {
                    description "MVR Transparent Mode";
                  }
                  enum proxy {
                    description "MVR Proxy Mode";
                  }
                }
              }
            }
          }
        }
      }
      list interface {
        key name;
        ordered-by user;
        description "Interface options for IGMP";
        leaf name {
          description "Interface name";
          type union {
            type jt:interface-name;
            type string {
              pattern "<.*>|$.*";
            }
          }
        }
        leaf multicast-router-interface {
          description "Enabling multicast-router-interface on the interface";
          type empty;
        }
        leaf immediate-leave {
          description "Enable immediate group leave on interface";
          type empty;
        }
        leaf host-only-interface {
          description "Enable interface to be treated as host-side interface";
          type empty;
        }
        leaf group-limit {
          description "Maximum number of groups an interface can join";
          type union {
            type uint16;
            type string {
              pattern "<.*>|$.*";
            }
          }
        }
        container static {
          description "Static group or source membership";
          list group {
            key name;
            ordered-by user;
            description "IP multicast group address";
            leaf name {
              description "IP multicast group address";
              type jt:ipv4addr;
            }
            list source {
              key name;
              ordered-by user;
              description "IP multicast source address";
              leaf name {
                description "Source address of IP multicast data";
                type jt:ipv4addr;
              }
            }
          }
        }
      }
      list qualified-vlan {
        key name;
        ordered-by user;
        description "VLAN options for qualified-learning";
        leaf name {
          description "VLAN ID of the learning-domain";
          type union {
            type string {
              pattern "<.*>|$.*";
            }
            type uint32 {
              range "0 .. 1023";
            }
          }
        }
        leaf query-interval {
          description "When to send host query messages";
          units seconds;
          type union {
            type string {
              pattern "<.*>|$.*";
            }
            type uint32 {
              range "1 .. 1024";
            }
          }
        }
        container l2-querier {
          description "Enable L2 querier mode";
          leaf source-address {
            description "Source IP address to use for L2 querier";
            type jt:ipv4addr;
          }
        }
        leaf query-response-interval {
          description "How long to wait for a host query response";
          units seconds;
          type string;
        }
        leaf query-last-member-interval {
          description "When to send group query messages";
          units seconds;
          type string;
        }
        leaf robust-count {
          description "Expected packet loss on a subnet";
          type union {
            type string {
              pattern "<.*>|$.*";
            }
            type uint32 {
              range "2 .. 10";
            }
          }
        }
        leaf immediate-leave {
          description "Enable immediate group leave on interfaces";
          type empty;
        }
        container proxy {
          presence "enable proxy";
          description "Enable proxy mode";
          leaf source-address {
            description "Source IP address to use for proxy";
            type jt:ipv4addr;
          }
        }
        leaf evpn-ssm-reports-only {
          description "Accept and process only <s,g> reports of SSM groups";
          type empty;
        }
        list interface {
          key name;
          ordered-by user;
          description "Interface options for IGMP";
          leaf name {
            description "Interface name";
            type union {
              type jt:interface-name;
              type string {
                pattern "<.*>|$.*";
              }
            }
          }
          leaf multicast-router-interface {
            description "Enabling multicast-router-interface on the interface";
            type empty;
          }
          leaf immediate-leave {
            description "Enable immediate group leave on interface";
            type empty;
          }
          leaf host-only-interface {
            description "Enable interface to be treated as host-side interface";
            type empty;
          }
          leaf group-limit {
            description "Maximum number of groups an interface can join";
            type union {
              type uint16;
              type string {
                pattern "<.*>|$.*";
              }
            }
          }
          container static {
            description "Static group or source membership";
            list group {
              key name;
              ordered-by user;
              description "IP multicast group address";
              leaf name {
                description "IP multicast group address";
                type jt:ipv4addr;
              }
              list source {
                key name;
                ordered-by user;
                description "IP multicast source address";
                leaf name {
                  description "Source address of IP multicast data";
                  type jt:ipv4addr;
                }
              }
            }
          }
        }
      }
      leaf version {
        description "Set IGMP version number on interface_help_string";
        type union {
          type string {
            pattern "<.*>|$.*";
          }
          type uint8 {
            range "2 .. 3";
          }
        }
      }
    }
    container traceoptions {
      description "Trace options for IGMP Snooping";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum packets {
              description "Trace all IGMP packets";
            }
            enum query {
              description "Trace IGMP membership query messages";
            }
            enum report {
              description "Trace membership report messages";
            }
            enum leave {
              description "Trace leave group messages (IGMPv2 only)";
            }
            enum group {
              description "Trace group operations";
            }
            enum client-notification {
              description "Trace notifications";
            }
            enum host-notification {
              description "Trace host notifications";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf query-interval {
      description "When to send host query messages";
      default "125";
      units seconds;
      type union {
        type string {
          pattern "<.*>|$.*";
        }
        type uint32 {
          range "1 .. 1024";
        }
      }
    }
    leaf query-response-interval {
      description "How long to wait for a host query response";
      default "10";
      units seconds;
      type string;
    }
    leaf query-last-member-interval {
      description "When to send group query messages";
      default "1";
      units seconds;
      type string;
    }
    leaf robust-count {
      description "Expected packet loss on a subnet";
      default "2";
      type union {
        type string {
          pattern "<.*>|$.*";
        }
        type uint32 {
          range "2 .. 10";
        }
      }
    }
    leaf immediate-leave {
      description "Enable immediate group leave on interfaces";
      type empty;
    }
    leaf evpn-ssm-reports-only {
      description "Accept and process only <s,g> reports of SSM groups";
      type empty;
    }
    leaf version {
      description "Set IGMP snooping version number";
      type union {
        type string {
          pattern "<.*>|$.*";
        }
        type uint8 {
          range "2 .. 3";
        }
      }
    }
    container proxy {
      presence "enable proxy";
      description "Enable proxy mode";
      leaf source-address {
        description "Source IP address to use for proxy";
        type jt:ipv4addr;
      }
      leaf irb {
        description "Proxy IGMP reports to IRB";
        type empty;
      }
    }
    list interface {
      key name;
      ordered-by user;
      description "Interface options for IGMP";
      leaf name {
        description "Interface name";
        type union {
          type jt:interface-name;
          type string {
            pattern "<.*>|$.*";
          }
        }
      }
      leaf multicast-router-interface {
        description "Enabling multicast-router-interface on the interface";
        type empty;
      }
      leaf immediate-leave {
        description "Enable immediate group leave on interfaces";
        type empty;
      }
      leaf host-only-interface {
        description "Enable interfaces to be treated as host-side interfaces";
        type empty;
      }
      leaf group-limit {
        description "Maximum number of (source,group) per interface";
        type union {
          type string {
            pattern "<.*>|$.*";
          }
          type uint16 {
            range "1 .. 65535";
          }
        }
      }
      container static {
        description "Static group or source membership";
        list group {
          key name;
          ordered-by user;
          description "IP multicast group address";
          leaf name {
            description "IP multicast group address";
            type jt:ipv4addr;
          }
          list source {
            key name;
            ordered-by user;
            description "IP multicast source address";
            leaf name {
              description "Source address of IP multicast data";
              type jt:ipv4addr;
            }
          }
        }
      }
    }
  }
  grouping juniper-default-ri-protocols-mld-snooping {
    description "MLD snooping options";
    list vlan {
      key name;
      ordered-by user;
      description "VLAN options";
      leaf name {
        description "VLAN name";
        type string;
      }
      container traceoptions {
        description "Trace options for MLD Snooping";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum packets {
                description "Trace all MLD packets";
              }
              enum query {
                description "Trace MLD membership query messages";
              }
              enum report {
                description "Trace membership report messages";
              }
              enum leave {
                description "Trace leave group messages (MLDv1 only)";
              }
              enum group {
                description "Trace group operations";
              }
              enum client-notification {
                description "Trace notifications";
              }
              enum host-notification {
                description "Trace host notifications";
              }
              enum route {
                description "Trace routing information";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
      leaf query-interval {
        description "When to send host query messages";
        default "125";
        units seconds;
        type union {
          type string {
            pattern "<.*>|$.*";
          }
          type uint32 {
            range "1 .. 1024";
          }
        }
      }
      container l2-querier {
        description "Enable L2 querier mode";
        leaf source-address {
          description "Source IP address to use for L2 querier";
          type jt:ipv6addr;
        }
      }
      leaf query-response-interval {
        description "How long to wait for a host query response";
        default "10";
        units seconds;
        type string;
      }
      leaf query-last-member-interval {
        description "When to send group query messages";
        default "1";
        units seconds;
        type string;
      }
      leaf robust-count {
        description "Expected packet loss on a subnet";
        default "2";
        type union {
          type string {
            pattern "<.*>|$.*";
          }
          type uint32 {
            range "2 .. 10";
          }
        }
      }
      leaf immediate-leave {
        description "Enable immediate group leave on interfaces";
        type empty;
      }
      container proxy {
        description "Enable proxy mode";
        leaf source-address {
          description "Source IP address to use for proxy";
          type jt:ipv6addr;
        }
      }
      leaf evpn-ssm-reports-only {
        description "Accept and process only <s,g> reports of SSM groups";
        type empty;
      }
      leaf version {
        description "Set MLD snooping version number";
        type union {
          type string {
            pattern "<.*>|$.*";
          }
          type uint8 {
            range "1 .. 2";
          }
        }
      }
      list interface {
        key name;
        ordered-by user;
        description "Interface options for MLD";
        leaf name {
          description "Interface name";
          type union {
            type jt:interface-name;
            type string {
              pattern "<.*>|$.*";
            }
          }
        }
        leaf multicast-router-interface {
          description "Enabling multicast-router-interface on the interface";
          type empty;
        }
        leaf immediate-leave {
          description "Enable immediate group leave on interfaces";
          type empty;
        }
        leaf host-only-interface {
          description "Enable interfaces to be treated as host-side interfaces";
          type empty;
        }
        leaf group-limit {
          description "Maximum number of groups an interface can join";
          type union {
            type uint16;
            type string {
              pattern "<.*>|$.*";
            }
          }
        }
        container static {
          description "Static group or source membership";
          list group {
            key name;
            ordered-by user;
            description "IP multicast group address";
            leaf name {
              description "IP multicast group address";
              type jt:ipv6addr;
            }
            list source {
              key name;
              ordered-by user;
              description "IP multicast source address";
              leaf name {
                description "Source address of IP multicast data";
                type jt:ipv6addr;
              }
            }
          }
        }
      }
      list qualified-vlan {
        key name;
        ordered-by user;
        description "VLAN options for qualified-learning";
        leaf name {
          description "VLAN ID of the learning-domain";
          type union {
            type string {
              pattern "<.*>|$.*";
            }
            type uint32 {
              range "0 .. 1023";
            }
          }
        }
        leaf query-interval {
          description "When to send host query messages";
          units seconds;
          type union {
            type string {
              pattern "<.*>|$.*";
            }
            type uint32 {
              range "1 .. 1024";
            }
          }
        }
        container l2-querier {
          leaf source-address {
            description "Source IP address to use for L2 querier";
            type jt:ipv6addr;
          }
        }
        leaf query-response-interval {
          description "How long to wait for a host query response";
          units seconds;
          type string;
        }
        leaf query-last-member-interval {
          description "When to send group query messages";
          units seconds;
          type string;
        }
        leaf robust-count {
          description "Expected packet loss on a subnet";
          type union {
            type string {
              pattern "<.*>|$.*";
            }
            type uint32 {
              range "2 .. 10";
            }
          }
        }
        leaf immediate-leave {
          description "Enable immediate group leave on interfaces";
          type empty;
        }
        container proxy {
          description "Enable proxy mode";
          leaf source-address {
            description "Source IP address to use for proxy";
            type jt:ipv6addr;
          }
        }
        leaf evpn-ssm-reports-only {
          description "Accept and process only <s,g> reports of SSM groups";
          type empty;
        }
        list interface {
          key name;
          ordered-by user;
          description "Interface options for MLD";
          leaf name {
            description "Interface name";
            type union {
              type jt:interface-name;
              type string {
                pattern "<.*>|$.*";
              }
            }
          }
          leaf multicast-router-interface {
            description "Enabling multicast-router-interface on the interface";
            type empty;
          }
          leaf immediate-leave {
            description "Enable immediate group leave on interfaces";
            type empty;
          }
          leaf host-only-interface {
            description "Enable interfaces to be treated as host-side interfaces";
            type empty;
          }
          leaf group-limit {
            description "Maximum number of groups an interface can join";
            type union {
              type uint16;
              type string {
                pattern "<.*>|$.*";
              }
            }
          }
          container static {
            description "Static group or source membership";
            list group {
              key name;
              ordered-by user;
              description "IP multicast group address";
              leaf name {
                description "IP multicast group address";
                type jt:ipv6addr;
              }
              list source {
                key name;
                ordered-by user;
                description "IP multicast source address";
                leaf name {
                  description "Source address of IP multicast data";
                  type jt:ipv6addr;
                }
              }
            }
          }
        }
      }
    }
    container traceoptions {
      description "Trace options for MLD Snooping";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum packets {
              description "Trace all MLD packets";
            }
            enum query {
              description "Trace MLD membership query messages";
            }
            enum report {
              description "Trace membership report messages";
            }
            enum leave {
              description "Trace leave group messages (MLDv2 only)";
            }
            enum group {
              description "Trace group operations";
            }
            enum client-notification {
              description "Trace notifications";
            }
            enum host-notification {
              description "Trace host notifications";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf query-interval {
      description "When to send host query messages";
      default "125";
      units seconds;
      type union {
        type string {
          pattern "<.*>|$.*";
        }
        type uint32 {
          range "1 .. 1024";
        }
      }
    }
    leaf query-response-interval {
      description "How long to wait for a host query response";
      default "10";
      units seconds;
      type string;
    }
    leaf query-last-member-interval {
      description "When to send group query messages";
      default "1";
      units seconds;
      type string;
    }
    leaf robust-count {
      description "Expected packet loss on a subnet";
      default "2";
      type union {
        type string {
          pattern "<.*>|$.*";
        }
        type uint32 {
          range "2 .. 10";
        }
      }
    }
    leaf immediate-leave {
      description "Enable immediate group leave on interfaces";
      type empty;
    }
    leaf evpn-ssm-reports-only {
      description "Accept and process only <s,g> reports of SSM groups";
      type empty;
    }
    leaf version {
      description "Set MLD snooping version number";
      type union {
        type string {
          pattern "<.*>|$.*";
        }
        type uint8 {
          range "1 .. 2";
        }
      }
    }
    container proxy {
      description "Enable proxy mode";
      leaf source-address {
        description "Source IP address to use for proxy";
        type jt:ipv6addr;
      }
      leaf irb {
        description "Proxy IGMP reports to IRB";
        type empty;
      }
    }
    list interface {
      key name;
      ordered-by user;
      description "Interface options for MLD";
      leaf name {
        description "Interface name";
        type union {
          type jt:interface-name;
          type string {
            pattern "<.*>|$.*";
          }
        }
      }
      leaf multicast-router-interface {
        description "Enabling multicast-router-interface on the interface";
        type empty;
      }
      leaf immediate-leave {
        description "Enable immediate group leave on interfaces";
        type empty;
      }
      leaf host-only-interface {
        description "Enable interfaces to be treated as host-side interfaces";
        type empty;
      }
      leaf group-limit {
        description "Maximum number of (source,group) per interface";
        type union {
          type string {
            pattern "<.*>|$.*";
          }
          type uint16 {
            range "1 .. 65535";
          }
        }
      }
      container static {
        description "Static group or source membership";
        list group {
          key name;
          ordered-by user;
          description "IP multicast group address";
          leaf name {
            description "IP multicast group address";
            type jt:ipv6addr;
          }
          list source {
            key name;
            ordered-by user;
            description "IP multicast source address";
            leaf name {
              description "Source address of IP multicast data";
              type jt:ipv6addr;
            }
          }
        }
      }
    }
  }
  grouping juniper-protocols-amt {
    container traceoptions {
      description "Trace options for AMT";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum packets {
              description "Trace all AMT packets";
            }
            enum errors {
              description "Trace all error messages";
            }
            enum tunnels {
              description "Trace all AMT tunnel messages";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    container relay {
      description "AMT relay";
      presence "enable relay";
      uses juniper-protocols-amt-relay;
    }
  }
  grouping juniper-protocols-amt-relay {
    container family {
      presence "enable family";
      description "Protocol family";
      container inet {
        presence "enable inet";
        leaf anycast-prefix {
          description "IPv4 anycast prefix";
          type jt:ipv4prefix;
        }
        leaf local-address {
          description "IPv4 local address";
          type jt:ipv4addr;
        }
      }
    }
    leaf secret-key-timeout {
      description "Time interval for the secret key to expire";
      units minutes;
      type union {
        type string {
          pattern "<.*>|$.*";
        }
        type uint32 {
          range "5 .. 1440";
        }
      }
    }
    leaf tunnel-limit {
      description "Number of AMT tunnels";
      type union {
        type uint32;
        type string {
          pattern "<.*>|$.*";
        }
      }
    }
    leaf unicast-stream-limit {
      description "Maximum number of AMT unicast streams(s,g,intf)";
      type union {
        type uint32;
        type string {
          pattern "<.*>|$.*";
        }
      }
    }
    leaf accounting {
      description "Enable AMT accounting";
      type empty;
    }
    leaf-list tunnel-devices {
      ordered-by user;
      description "Tunnel devices to be used for creating ud interfaces";
      type union {
        type jt:interface-device;
        type string {
          pattern "<.*>|$.*";
        }
      }
    }
  }
  grouping juniper-protocols-ancp {
    container traceoptions {
      description "Trace options for ANCP";
      leaf no-remote-trace {
        description "Disable remote tracing";
        type empty;
      }
      container file {
        description "Trace file information";
        leaf filename {
          description "Name of file in which to write trace information";
          type string {
            length "1 .. 1024";
          }
        }
        leaf size {
          description "Maximum trace file size";
          type string;
        }
        leaf files {
          description "Maximum number of trace files";
          default "3";
          type union {
            type string {
              pattern "<.*>|$.*";
            }
            type uint32 {
              range "2 .. 1000";
            }
          }
        }
        choice world-readable-choice {
          leaf world-readable {
            description "Allow any user to read the log file";
            type empty;
          }
          leaf no-world-readable {
            description "Don't allow any user to read the log file";
            type empty;
          }
        }
        leaf match {
          description "Regular expression for lines to be logged";
          type jt:regular-expression;
        }
      }
      leaf level {
        description "Level of debugging output";
        default "error";
        type enumeration {
          enum error {
            description "Match error conditions";
          }
          enum warning {
            description "Match warning messages";
          }
          enum notice {
            description "Match conditions that should be handled specially";
          }
          enum info {
            description "Match informational messages";
          }
          enum verbose {
            description "Match verbose messages";
          }
          enum all {
            description "Match all levels";
          }
        }
      }
      list flag {
        key name;
        ordered-by user;
        description "Tracing parameters";
        leaf name {
          type enumeration {
            enum config {
              description "Trace config events";
            }
            enum cos {
              description "Trace CoS events";
            }
            enum routing-socket {
              description "Trace routing-socket events";
            }
            enum packet {
              description "Trace ANCP packet Transmit/Receive";
            }
            enum protocol {
              description "Trace protocol events";
            }
            enum process {
              description "Trace process internals";
            }
            enum startup {
              description "Trace ANCP startup events/flow";
            }
            enum session {
              description "Trace connection events/sessions";
            }
            enum general {
              description "Trace general flow";
            }
            enum restart {
              description "Trace process restart flow";
            }
            enum subscriber {
              description "Trace subscriber events";
            }
            enum timer {
              description "Trace timer processing";
            }
            enum all {
              description "Trace everything";
            }
          }
        }
        leaf disable {
          description "Disable this trace flag";
          type empty;
        }
      }
    }
    container qos-adjust {
      presence "enable qos-adjust";
      description "Enable QoS adjust for interfaces and interface-sets";
      leaf sdsl-bytes {
        description "Set SDSL byte adjust value";
        status deprecated;
        default "0";
        units bytes;
        type union {
          type string {
            pattern "<.*>|$.*";
          }
          type int32 {
            range "-100 .. 100";
          }
        }
      }
      leaf sdsl-overhead-adjust {
        description "Set SDSL overhead adjusted";
        status deprecated;
        default "100";
        units percent;
        type union {
          type string {
            pattern "<.*>|$.*";
          }
          type uint32 {
            range "80 .. 100";
          }
        }
      }
      leaf vdsl-bytes {
        description "Set VDSL byte adjust value";
        status deprecated;
        default "0";
        units bytes;
        type union {
          type string {
            pattern "<.*>|$.*";
          }
          type int32 {
            range "-100 .. 100";
          }
        }
      }
      leaf vdsl-overhead-adjust {
        description "Set VDSL overhead adjusted";
        status deprecated;
        default "100";
        units percent;
        type union {
          type string {
            pattern "<.*>|$.*";
          }
          type uint32 {
            range "80 .. 100";
          }
        }
      }
      leaf vdsl2-bytes {
        description "Set VDSL2 byte adjust value";
        status deprecated;
        default "0";
        units bytes;
        type union {
          type string {
            pattern "<.*>|$.*";
          }
          type int32 {
            range "-100 .. 100";
          }
        }
      }
      leaf vdsl2-overhead-adjust {
        description "Set VDSL2 overhead adjusted";
        status deprecated;
        default "100";
        units percent;
        type union {
          type string {
            pattern "<.*>|$.*";
          }
          type uint32 {
            range "80 .. 100";
          }
        }
      }
      leaf adsl-bytes {
        description "Set ADSL byte adjust value";
        status deprecated;
        default "0";
        units bytes;
        type union {
          type string {
            pattern "<.*>|$.*";
          }
          type int32 {
            range "-100 .. 100";
          }
        }
      }
      leaf adsl2-bytes {
        description "Set ADSL2 byte adjust value";
        status deprecated;
        default "0";
        units bytes;
        type union {
          type string {
            pattern "<.*>|$.*";
          }
          type int32 {
            range "-100 .. 100";
          }
        }
      }
      leaf adsl2-plus-bytes {
        description "Set ADSL-PLUS byte adjust value";
        status deprecated;
        default "0";
        units bytes;
        type union {
          type string {
            pattern "<.*>|$.*";
          }
          type int32 {
            range "-100 .. 100";
          }
        }
      }
      leaf other-bytes {
        description "Set OTHER byte adjust value";
        status deprecated;
        default "0";
        units bytes;
        type union {
          type string {
            pattern "<.*>|$.*";
          }
          type int32 {
            range "-100 .. 100";
          }
        }
      }
      leaf other-overhead-adjust {
        description "Set OTHER overhead adjusted";
        status deprecated;
        default "100";
        units percent;
        type union {
          type string {
            pattern "<.*>|$.*";
          }
          type uint32 {
            range "80 .. 100";
          }
        }
      }
    }
    leaf pre-ietf-mode {
      description "Enable backward compatibility mode";
      type empty;
    }
    leaf maximum-discovery-table-entries {
      description "Maximum number of discovery table entries per neighbor";
      type union {
        type string {
          pattern "<.*>|$.*";
        }
        type uint32 {
          range "1 .. 100000";
        }
      }
    }
    leaf adjacency-timer {
      description "Set adjacency timer in seconds";
      type union {
        type string {
          pattern "<.*>|$.*";
        }
        type uint32 {
          range "1 .. 25";
        }
      }
    }
    leaf maximum-helper-restart-time {
      description "Set maximum helper restart timer";
      units seconds;
      type union {
        type string {
          pattern "<.*>|$.*";
        }
        type uint32 {
          range "45 .. 600";
        }
      }
    }
    leaf qos-adjust-adsl {
      description "Set ADSL QoS adjustment factor";
      status deprecated;
      default "100";
      units percent;
      type union {
        type string {
          pattern "<.*>|$.*";
        }
        type uint32 {
          range "0 .. 100";
        }
      }
    }
    leaf qos-adjust-adsl2 {
      description "Set ADSL2 QoS adjustment factor";
      status deprecated;
      default "100";
      units percent;
      type union {
        type string {
          pattern "<.*>|$.*";
        }
        type uint32 {
          range "0 .. 100";
        }
      }
    }
    leaf qos-adjust-adsl2-plus {
      description "Set ADSL2+ QoS adjustment factor";
      status deprecated;
      default "100";
      units percent;
      type union {
        type string {
          pattern "<.*>|$.*";
        }
        type uint32 {
          range "0 .. 100";
        }
      }
    }
    leaf qos-adjust-vdsl {
      description "Set VDSL QoS adjustment factor";
      status deprecated;
      default "100";
      units percent;
      type union {
        type string {
          pattern "<.*>|$.*";
        }
        type uint32 {
          range "0 .. 100";
        }
      }
    }
    leaf qos-adjust-vdsl2 {
      description "Set VDSL2 QoS adjustment factor";
      status deprecated;
      default "100";
      units percent;
      type union {
        type string {
          pattern "<.*>|$.*";
        }
        type uint32 {
          range "0 .. 100";
        }
      }
    }
    leaf qos-adjust-sdsl {
      description "Set SDSL QoS adjustment factor";
      status deprecated;
      default "100";
      units percent;
      type union {
        type string {
          pattern "<.*>|$.*";
        }
        type uint32 {
          range "0 .. 100";
        }
      }
    }
    leaf qos-adjust-other {
      description "Set OTHER QoS adjustment factor";
      status deprecated;
      default "100";
      units percent;
      type union {
        type string {
          pattern "<.*>|$.*";
        }
        type uint32 {
          range "0 .. 100";
        }
      }
    }
    leaf gsmp-syn-wait {
      description "Enable partition ID learning";
      type empty;
    }
    leaf gsmp-syn-timeout {
      description "Set partition ID learning timeout";
      default "30";
      units seconds;
      type union {
        type string {
          pattern "<.*>|$.*";
        }
        type uint32 {
          range "1 .. 60";
        }
      }
    }
    leaf adjacency-loss-hold-time {
      description "Audit duration upon adjacency loss";
      default "0";
      units seconds;
      type union {
        type string {
          pattern "<.*>|$.*";
        }
        type uint32 {
          range "0 .. 1800";
        }
      }
    }
    container interfaces {
      description "ANCP interface config options";
      list interface-set {
        key name;
        description "ANCP interface-set specific options";
        leaf name {
          description "Name of the interface set";
          type string;
        }
        leaf access-identifier {
          description "Subscriber specific access identifier information";
          type string;
        }
        leaf neighbor {
          description "Neighbor IP address";
          status deprecated;
          type jt:ipaddr;
        }
      }
      list interface {
        key name;
        uses ancp_interfaces_type;
      }
    }
    list neighbor {
      key name;
      description "ANCP neighbor config options";
      leaf name {
        description "IP address of neighbor";
        type jt:ipaddr;
      }
      leaf discovery-mode {
        description "Enable topology discovery";
        status deprecated;
        type empty;
      }
      choice ietf-mode-option {
        case case_1 {
          leaf pre-ietf-mode {
            description "Enable backward compatibility mode";
            type empty;
          }
        }
        case case_2 {
          leaf ietf-mode {
            description "Enable IETF mode";
            type empty;
          }
        }
      }
      leaf adjacency-timer {
        description "Set adjacency timer in seconds";
        type union {
          type string {
            pattern "<.*>|$.*";
          }
          type uint32 {
            range "1 .. 25";
          }
        }
      }
      leaf maximum-discovery-table-entries {
        description "Maximum number of discovery table entries";
        type union {
          type string {
            pattern "<.*>|$.*";
          }
          type uint32 {
            range "1 .. 100000";
          }
        }
      }
      container auto-configure-trigger {
        presence "enable auto-configure-trigger";
        description "Auto-configure trigger support";
        leaf interface {
          type union {
            type jt:interface-device;
            type string {
              pattern "<.*>|$.*";
            }
          }
        }
      }
      leaf adjacency-loss-hold-time {
        description "Audit duration upon adjacency loss";
        units seconds;
        type union {
          type string {
            pattern "<.*>|$.*";
          }
          type uint32 {
            range "0 .. 1800";
          }
        }
      }
    }
  }
  grouping ancp_interfaces_type {
    description "Physical interface";
    leaf name {
      type union {
        type jt:interface-name;
        type string {
          pattern "<.*>|$.*";
        }
      }
    }
    leaf access-identifier {
      description "Subscriber specific access identifier information";
      type string;
    }
    leaf neighbor {
      description "Neighbor IP address";
      status deprecated;
      type jt:ipaddr;
    }
    leaf overhead-accounting {
      description "Enable overhead accounting on per ACI basis";
      status deprecated;
      type empty;
    }
  }
  grouping juniper-protocols-bgp {
    container path-selection {
      description "Configure path selection strategy";
      leaf l2vpn-use-bgp-rules {
        description "Use standard BGP rules during L2VPN path selection";
        type empty;
      }
      leaf cisco-non-deterministic {
        description "Use Cisco IOS nondeterministic path selection algorithm";
        type empty;
      }
      leaf always-compare-med {
        description "Always compare MED values, regardless of neighbor AS";
        type empty;
      }
      container med-plus-igp {
        presence "enable med-plus-igp";
        description "Add IGP cost to next-hop to MED before comparing MED values";
        leaf med-multiplier {
          description "Multiplier for MED";
          default "1";
          type union {
            type string {
              pattern "<.*>|$.*";
            }
            type uint16 {
              range "1 .. 1000";
            }
          }
        }
        leaf igp-multiplier {
          description "Multiplier for IGP cost to next-hop";
          default "1";
          type union {
            type string {
              pattern "<.*>|$.*";
            }
            type uint16 {
              range "1 .. 1000";
            }
          }
        }
      }
      leaf external-router-id {
        description "Compare router ID on BGP externals";
        type empty;
      }
      leaf as-path-ignore {
        description "Ignore AS path comparison during path selection";
        type empty;
      }
    }
    list group {
      key name;
      ordered-by user;
      description "Define a peer group";
      leaf name {
        description "Group name";
        type string;
      }
      leaf type {
        description "Type of peer group";
        type enumeration {
          enum internal {
            description "IBGP group";
          }
          enum external {
            description "EBGP group";
          }
        }
      }
      leaf description {
        description "Text description";
        type string {
          length "1 .. 255";
        }
      }
      leaf local-address {
        description "Address of local end of BGP session";
        type jt:ipaddr;
      }
      leaf hold-time {
        description "Hold time used when negotiating with a peer";
        type union {
          type string {
            pattern "<.*>|$.*";
          }
          type uint32 {
            range "0 .. 65535";
          }
        }
      }
      container family {
        description "Protocol family for NLRIs in updates";
        container inet-vpn {
          description "IPv4 Layer 3 VPN NLRI parameters";
          container unicast {
            description "Include unicast NLRI";
            presence "enable unicast";
            uses bgp-afi-l3vpn;
          }
        }
        container inet6-vpn {
          description "IPv6 Layer 3 VPN NLRI parameters";
          container unicast {
            description "Include unicast NLRI";
            presence "enable unicast";
            uses bgp-afi-l3vpn;
          }
        }
        container evpn {
          description "EVPN NLRI parameters";
          container signaling {
            description "Include EVPN signaling NLRI";
            presence "enable signaling";
          }
        }
        container route-target {
          presence "enable route-target";
          description "Route target NLRI used for VPN route filtering";
        }
      }
      leaf authentication-key {
        description "MD5 authentication key";
        type string {
          length "1 .. 126";
        }
      }
      leaf authentication-algorithm {
        description "Authentication algorithm name";
        type enumeration {
          enum md5 {
            description "Message Digest 5";
          }
          enum hmac-sha-1-96 {
            description "Hash-based Message Authentication Code (SHA1) (96 bits)";
          }
          enum aes-128-cmac-96 {
            description "Cipher-based Message Authentication Code (AES128) (96 bits)";
          }
          enum ao {
            description "TCP Authentication Option";
          }
        }
      }
      leaf tcpao-auth-mismatch {
        description "Continue without TCP-AO if any one TCP endpoint does not have TCP-AO configured";
        type enumeration {
          enum allow-without-tcpao {
            description "Allow the connection establishment without TCP-AO";
          }
        }
      }
      leaf authentication-key-chain {
        description "Key chain name";
        type string {
          length "1 .. 128";
        }
      }
      leaf-list export {
        ordered-by user;
        description "Export policy";
        type jt:policy-algebra;
      }
      leaf tcp-mss {
        description "Maximum TCP segment size";
        type union {
          type string {
            pattern "<.*>|$.*";
          }
          type uint32 {
            range "1 .. 4096";
          }
        }
      }
      list neighbor {
        key name;
        ordered-by user;
        description "Configure a neighbor";
        leaf name {
          type jt:ipaddr-scoped;
        }
        leaf description {
          description "Text description";
          type string {
            length "1 .. 255";
          }
        }
        leaf passive {
          description "Do not send open messages to a peer";
          type empty;
        }
      }
    }
    leaf log-updown {
      description "Log a message for peer state transitions";
      type empty;
    }
  }
  grouping bgp-af-gr {
    container long-lived {
      description "Long-lived graceful restart options";
      container restarter {
        description "Long-lived graceful restart restarter options";
        choice enable-disable {
          case case_1 {
            leaf disable {
              description "Disable restarter functionality";
              type empty;
            }
          }
        }
        leaf stale-time {
          description "Stale time in seconds or dhms notation (1..16777215)";
          type string;
        }
      }
      container extended-route-retention {
        description "Extended route retention (LLGR-helper extended) options";
        choice enable-disable {
          case case_1 {
            leaf disable {
              description "Disable extended-route-retention (LLGR-helper) functionality";
              type empty;
            }
          }
        }
        leaf retention-time {
          description "Retention time in seconds or dhms notation (1..16777215)";
          type string;
        }
        leaf-list retention-policy {
          ordered-by user;
          description "Retention policy for Extended Route Retention";
          type jt:policy-algebra;
        }
      }
    }
    leaf forwarding-state-bit {
      description "Control forwarding-state flag negotiation";
      type enumeration {
        enum set {
          description "Always set";
        }
        enum from-fib {
          description "Use state of associated FIB(s)";
        }
      }
    }
  }
  grouping bgp-afi-default {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
  }
  grouping apath-options {
    description "Number of paths to advertise";
    leaf receive {
      description "Receive multiple paths from peer";
      type empty;
    }
    container send {
      presence "enable send";
      description "Send multiple paths to peer";
      container path-selection-mode {
        description "Configure how to select add-path routes";
        choice mode {
          case case_1 {
            leaf all-paths {
              description "Advertise all paths allowed by path count";
              type empty;
            }
          }
          case case_2 {
            leaf equal-cost-paths {
              description "Advertise equal cost paths";
              type empty;
            }
          }
        }
      }
      leaf-list prefix-policy {
        ordered-by user;
        description "Perform add-path only for prefixes that match policy";
        type jt:policy-algebra;
      }
      leaf path-count {
        description "Number of paths to advertise";
        type union {
          type string {
            pattern "<.*>|$.*";
          }
          type int32 {
            range "2 .. 64";
          }
        }
      }
      leaf include-backup-path {
        description "Number of backup paths to advertise";
        type union {
          type string {
            pattern "<.*>|$.*";
          }
          type int32 {
            range "1 .. 2";
          }
        }
      }
      leaf multipath {
        description "Include only multipath contributor routes";
        type empty;
      }
    }
  }
  grouping bgp-afi-flow {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    leaf-list no-validate {
      ordered-by user;
      description "Bypass validation procedure for routes that match policy";
      type jt:policy-algebra;
    }
    leaf strip-nexthop {
      description "Strip the next-hop from the outgoing flow update";
      type empty;
    }
    leaf allow-policy-add-nexthop {
      description "Allow policy to add nexthop to a route without nexthop";
      status deprecated;
      type empty;
    }
  }
  grouping bgp-afi-flow-with-redirect-ip-action {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    leaf-list no-validate {
      ordered-by user;
      description "Bypass validation procedure for routes that match policy";
      type jt:policy-algebra;
    }
    leaf strip-nexthop {
      description "Strip the next-hop from the outgoing flow update";
      type empty;
    }
    container legacy-redirect-ip-action {
      presence "enable legacy-redirect-ip-action";
      description "Configure legacy redirect to IP support";
      leaf receive {
        description "Accept legacy encoded redirect-to-ip action attribute";
        type empty;
      }
      leaf send {
        description "Advertise Redirect action as legacy redirect attribute";
        type empty;
      }
    }
    leaf secondary-independent-resolution {
      description "Resolve FLOW routes in VRF table independent of VPN FLOW route";
      type empty;
    }
  }
  grouping bgp-afi-inet-transport {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    leaf per-prefix-label {
      description "Allocate a unique label to each advertised prefix";
      type empty;
    }
    leaf per-group-label {
      description "Advertise prefixes with unique labels per group";
      type empty;
    }
    container traffic-statistics {
      description "Collect statistics for BGP label-switched paths";
      presence "enable traffic-statistics";
      uses bgpaf-traffic-statistics;
    }
    container protection {
      presence "enable protection";
      description "Compute backup path for active nexthop failure";
    }
  }
  grouping bgp-afi-inet6-labeled {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    leaf per-group-label {
      description "Advertise prefixes with unique labels per group";
      type empty;
    }
    container traffic-statistics {
      description "Collect statistics for BGP label-switched paths";
      presence "enable traffic-statistics";
      uses bgpaf-traffic-statistics;
    }
    container rib {
      description "Select table used by labeled unicast routes";
      leaf inet6.3 {
        description "Use inet6.3 to exchange labeled unicast routes";
        type empty;
      }
    }
    container explicit-null {
      presence "enable explicit-null";
      description "Advertise explicit null";
      leaf connected-only {
        description "Advertise explicit null only for connected routes";
        type empty;
      }
    }
    container protection {
      presence "enable protection";
      description "Compute backup path for active nexthop failure";
    }
    list topology {
      key name;
      ordered-by user;
      description "Multi topology routing tables";
      leaf name {
        description "Topology name";
        type string;
      }
      leaf community {
        description "Community to identify multi topology routes";
        type string;
      }
    }
  }
  grouping bgp-afi-inet6-transport {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    leaf per-prefix-label {
      description "Allocate a unique label to each advertised prefix";
      type empty;
    }
    leaf per-group-label {
      description "Advertise prefixes with unique labels per group";
      type empty;
    }
    container traffic-statistics {
      description "Collect statistics for BGP label-switched paths";
      presence "enable traffic-statistics";
      uses bgpaf-traffic-statistics;
    }
    container lu-export {
      presence "enable lu-export";
      description "Install Classful Transport routes in inet6.3";
    }
    container protection {
      presence "enable protection";
      description "Compute backup path for active nexthop failure";
    }
  }
  grouping bgp-afi-l2vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container egress-protection {
      presence "enable egress-protection";
      description "Egress router protection";
      container context-identifier {
        description "Context identifier";
        leaf context-id {
          description "IP address";
          type jt:ipv4addr;
        }
      }
      leaf-list keep-import {
        ordered-by user;
        description "Import policy";
        type jt:policy-algebra;
      }
    }
  }
  grouping bgp-afi-l3vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    container egress-protection {
      presence "enable egress-protection";
      description "Egress router protection";
      container context-identifier {
        description "Context identifier";
        leaf context-id {
          description "IP address";
          type jt:ipv4addr;
        }
      }
      leaf-list keep-import {
        ordered-by user;
        description "Import policy";
        type jt:policy-algebra;
      }
    }
    leaf accept-local-nexthop {
      description "Enable processing of routes with own nexthop";
      type empty;
    }
    leaf accept-own {
      description "Enable processing of routes with own originator-id or nexthop";
      type empty;
    }
  }
  grouping bgp-afi-labeled {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    leaf per-prefix-label {
      description "Allocate a unique label to each advertised prefix";
      type empty;
    }
    leaf per-group-label {
      description "Advertise prefixes with unique labels per group";
      type empty;
    }
    container traffic-statistics {
      description "Collect statistics for BGP label-switched paths";
      presence "enable traffic-statistics";
      uses bgpaf-traffic-statistics;
    }
    list topology {
      key name;
      ordered-by user;
      description "Multi topology routing tables";
      leaf name {
        description "Topology name";
        type string;
      }
      leaf community {
        description "Community to identify multi topology routes";
        type string;
      }
    }
    container rib {
      description "Select table used by labeled unicast routes";
      uses rib-inet3;
    }
    container explicit-null {
      presence "enable explicit-null";
      description "Advertise explicit null";
      leaf connected-only {
        description "Advertise explicit null only for connected routes";
        type empty;
      }
    }
    container protection {
      presence "enable protection";
      description "Compute backup path for active nexthop failure";
    }
    container egress-protection {
      presence "enable egress-protection";
      description "Egress router protection";
      container context-identifier {
        description "Context identifier";
        leaf context-id {
          description "IP address";
          type jt:ipv4addr;
        }
      }
      leaf-list keep-import {
        ordered-by user;
        description "Import policy";
        type jt:policy-algebra;
      }
    }
    leaf resolve-vpn {
      description "Install received NLRI in inet.3 also";
      type empty;
    }
    container entropy-label {
      presence "enable entropy-label";
      description "Use entropy label for entropy label capable BGP LSPs";
      leaf-list import {
        ordered-by user;
        description "Policy to select BGP LSPs to use entropy label";
        type jt:policy-algebra;
      }
      leaf no-next-hop-validation {
        description "Don't validate next hop field against route next hop";
        type empty;
      }
      leaf elc-v2-compatible {
        description "Send and accept ELCv2 in addition to ELCv3";
        type empty;
      }
    }
  }
  grouping bgp-afi-srte {
    container prefix-limit {
      description "Limit maximum number of prefixes from a peer";
      uses bgpaf-prefix-limit;
    }
    container accepted-prefix-limit {
      description "Limit maximum number of prefixes accepted from a peer";
      uses bgpaf-accepted-prefix-limit;
    }
    leaf damping {
      description "Enable route flap damping";
      type empty;
    }
    container loops {
      description "Allow local AS in received AS paths";
      uses bgpaf-loops;
    }
    container graceful-restart {
      description "BGP graceful restart options";
      uses bgp-af-gr;
    }
    leaf no-install {
      description "Dont install received routes in forwarding";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
  }
  grouping bgp-afi-topo {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container protection {
      presence "enable protection";
      description "Compute backup path for active nexthop failure";
    }
    list topology {
      key name;
      ordered-by user;
      description "Multi topology routing tables";
      leaf name {
        description "Topology name";
        type string;
      }
      leaf community {
        description "Community to identify multi topology routes";
        type string;
      }
    }
  }
  grouping bgp-afi-vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
  }
  grouping bgp-afi-vpn-protection {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      description "Enable route flap damping";
      type empty;
    }
    leaf local-ipv4-address {
      description "Local IPv4 address";
      type jt:ipv4addr;
    }
    container loops {
      description "Allow local AS in received AS paths";
      uses bgpaf-loops;
    }
    container delay-route-advertisements {
      presence "enable delay-route-advertisements";
      description "Delay route updates for this family until FIB-sync";
      leaf always-wait-for-krt-drain {
        description "Wait for KRT-queue drain for more-specific prefixes";
        type empty;
      }
      container minimum-delay {
        description "Minimum-delay to ensure KRT sees the route flash";
        leaf routing-uptime {
          description "Min delay(sec) advertisement after RPD start";
          type union {
            type string {
              pattern "<.*>|$.*";
            }
            type uint32 {
              range "1 .. 36000";
            }
          }
        }
        leaf inbound-convergence {
          description "Min delay(sec) advertisement after source-peer sent all routes";
          type union {
            type string {
              pattern "<.*>|$.*";
            }
            type uint32 {
              range "1 .. 36000";
            }
          }
        }
      }
      container maximum-delay {
        description "Maximum delay deferring routes";
        leaf route-age {
          description "Max delay(sec) advertisement route age";
          type union {
            type string {
              pattern "<.*>|$.*";
            }
            type uint32 {
              range "1 .. 36000";
            }
          }
        }
        leaf routing-uptime {
          description "Max delay(sec) advertisement after RPD start";
          type union {
            type string {
              pattern "<.*>|$.*";
            }
            type uint32 {
              range "1 .. 36000";
            }
          }
        }
      }
    }
    container nexthop-resolution {
      description "Configure nexthop resolution properties";
      leaf no-resolution {
        description "Consider nexthop good without resolution attempt";
        type empty;
      }
      leaf preserve-nexthop-hierarchy {
        description "Attempt preserving resolved nexthop chain in forwarding";
        type empty;
      }
    }
    container defer-initial-multipath-build {
      presence "enable defer-initial-multipath-build";
      description "Defer initial multipath build until EOR is received";
      leaf maximum-delay {
        description "Max delay(sec) multipath build after peer is up";
        type union {
          type string {
            pattern "<.*>|$.*";
          }
          type uint32 {
            range "1 .. 3600";
          }
        }
      }
    }
    container graceful-restart {
      description "BGP graceful restart options";
      uses bgp-af-gr;
    }
    leaf extended-nexthop {
      description "Extended nexthop encoding";
      type empty;
    }
    leaf extended-nexthop-color {
      description "Resolve using extended color nexthop";
      type empty;
    }
    leaf extended-nexthop-tunnel {
      description "Use BGP tunnel attribute";
      type empty;
    }
    leaf no-install {
      description "Dont install received routes in forwarding";
      type empty;
    }
    leaf route-age-bgp-view {
      description "Maintain BGP route's age based on Update messages only";
      type empty;
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      description "Advertise SRv6 service";
      type empty;
    }
    leaf accept-srv6-service {
      description "Accept SRv6 service";
      type empty;
    }
    container aggregate-label {
      presence "enable aggregate-label";
      description "Aggregate labels of incoming routes with the same FEC";
      leaf community {
        description "Community to identify the FEC of incoming routes";
        type string;
      }
    }
    container egress-protection {
      presence "enable egress-protection";
      description "Egress router protection";
      container context-identifier {
        description "Context identifier";
        leaf context-id {
          description "IP address";
          type jt:ipv4addr;
        }
      }
      leaf-list keep-import {
        ordered-by user;
        description "Import policy";
        type jt:policy-algebra;
      }
    }
  }
  grouping bgp-output-queue-priority-class {
    choice class {
      case case_1 {
        leaf priority {
          description "Output queue priority; higher is better";
          type union {
            type string {
              pattern "<.*>|$.*";
            }
            type uint32 {
              range "1 .. 16";
            }
          }
        }
      }
      case case_2 {
        leaf expedited {
          description "Expedited queue; highest priority";
          type empty;
        }
      }
    }
  }
  grouping bgp_filter_obj {
    description "Filter to apply to tracing";
    leaf match-on {
      description "Argument on which to match";
      type enumeration {
        enum prefix {
          description "Filter based on prefix";
        }
      }
    }
    leaf-list policy {
      ordered-by user;
      description "Filter policy";
      type jt:policy-algebra;
    }
  }
  grouping bgpaf-accepted-prefix-limit {
    leaf maximum {
      description "Maximum number of prefixes accepted from a peer";
      type union {
        type string {
          pattern "<.*>|$.*";
        }
        type uint32 {
          range "1 .. 4294967295";
        }
      }
    }
    container teardown {
      presence "enable teardown";
      description "Clear peer connection on reaching limit";
      leaf limit-threshold {
        description "Percentage of prefix-limit to start warnings";
        type union {
          type string {
            pattern "<.*>|$.*";
          }
          type uint32 {
            range "1 .. 100";
          }
        }
      }
      container idle-timeout {
        presence "enable idle-timeout";
        description "Timeout before attempting to restart peer";
        choice idle-parm {
          case case_1 {
            leaf forever {
              description "Idle the peer until the user intervenes";
              type empty;
            }
          }
          case case_2 {
            leaf timeout {
              description "Timeout value, in minutes, for restarting peer";
              type union {
                type string {
                  pattern "<.*>|$.*";
                }
                type uint32 {
                  range "1 .. 2400";
                }
              }
            }
          }
        }
      }
    }
    container drop-excess {
      presence "enable drop-excess";
      description "Drop routes from peer on reaching limit";
      leaf limit-threshold {
        description "Percentage of prefix-limit to start warnings";
        type union {
          type string {
            pattern "<.*>|$.*";
          }
          type uint32 {
            range "1 .. 100";
          }
        }
      }
    }
    container hide-excess {
      presence "enable hide-excess";
      description "Hide routes from peer on reaching limit";
      leaf limit-threshold {
        description "Percentage of prefix-limit to start warnings";
        type union {
          type string {
            pattern "<.*>|$.*";
          }
          type uint32 {
            range "1 .. 100";
          }
        }
      }
    }
  }
  grouping bgpaf-aigp-options {
    leaf disable {
      description "Disable sending and receiving of AIGP attribute";
      type empty;
    }
  }
  grouping bgpaf-loops {
    leaf loops {
      description "AS-Path loop count";
      type union {
        type string {
          pattern "<.*>|$.*";
        }
        type int32 {
          range "1 .. 10";
        }
      }
    }
  }
  grouping bgpaf-prefix-limit {
    leaf maximum {
      description "Maximum number of prefixes from a peer";
      type union {
        type string {
          pattern "<.*>|$.*";
        }
        type uint32 {
          range "1 .. 4294967295";
        }
      }
    }
    container teardown {
      presence "enable teardown";
      description "Clear peer connection on reaching limit";
      leaf limit-threshold {
        description "Percentage of prefix-limit to start warnings";
        type union {
          type string {
            pattern "<.*>|$.*";
          }
          type uint32 {
            range "1 .. 100";
          }
        }
      }
      container idle-timeout {
        presence "enable idle-timeout";
        description "Timeout before attempting to restart peer";
        choice idle-parm {
          case case_1 {
            leaf forever {
              description "Idle the peer until the user intervenes";
              type empty;
            }
          }
          case case_2 {
            leaf timeout {
              description "Timeout value, in minutes, for restarting peer";
              type union {
                type string {
                  pattern "<.*>|$.*";
                }
                type uint32 {
                  range "1 .. 2400";
                }
              }
            }
          }
        }
      }
    }
    container drop-excess {
      presence "enable drop-excess";
      description "Drop routes from peer on reaching limit";
      leaf limit-threshold {
        description "Percentage of prefix-limit to start warnings";
        type union {
          type string {
            pattern "<.*>|$.*";
          }
          type uint32 {
            range "1 .. 100";
          }
        }
      }
    }
    container hide-excess {
      presence "enable hide-excess";
      description "Hide routes from peer on reaching limit";
      leaf limit-threshold {
        description "Percentage of prefix-limit to start warnings";
        type union {
          type string {
            pattern "<.*>|$.*";
          }
          type uint32 {
            range "1 .. 100";
          }
        }
      }
    }
  }
  grouping bgpaf-traffic-statistics {
    leaf labeled-path {
      description "Ingress labeled path statistics";
      type empty;
    }
    container file {
      description "Statistics file options";
      leaf filename {
        description "Name of file in which to write trace information";
        type string {
          length "1 .. 1024";
        }
      }
      leaf replace {
        description "Replace trace file rather than appending to it";
        status deprecated;
        type empty;
      }
      leaf size {
        description "Maximum trace file size";
        type string;
      }
      leaf files {
        description "Maximum number of trace files";
        default "10";
        type union {
          type string {
            pattern "<.*>|$.*";
          }
          type uint32 {
            range "2 .. 1000";
          }
        }
      }
      leaf no-stamp {
        description "Do not timestamp trace file";
        status deprecated;
        type empty;
      }
      choice world-readable-choice {
        leaf world-readable {
          description "Allow any user to read the log file";
          type empty;
        }
        leaf no-world-readable {
          description "Don't allow any user to read the log file";
          type empty;
        }
      }
    }
    leaf interval {
      description "Time to collect statistics (seconds)";
      type union {
        type string {
          pattern "<.*>|$.*";
        }
        type int32 {
          range "60 .. 65535";
        }
      }
    }
  }
  grouping juniper-protocols-bgpmcast {
    description "BGP Multicast configuration";
    container traceoptions {
      description "Trace options for BGP Multicast";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
  }
  grouping juniper-protocols-bridge {
    container traceoptions {
      description "Trace options for Layer 2 address service";
      leaf no-remote-trace {
        description "Disable remote tracing";
        type empty;
      }
      container file {
        description "Trace file information";
        leaf filename {
          description "Name of file in which to write trace information";
          type string {
            length "1 .. 1024";
          }
        }
        leaf size {
          description "Maximum trace file size";
          type string;
        }
        leaf files {
          description "Maximum number of trace files";
          default "3";
          type union {
            type string {
              pattern "<.*>|$.*";
            }
            type uint32 {
              range "2 .. 1000";
            }
          }
        }
        choice world-readable-choice {
          leaf world-readable {
            description "Allow any user to read the log file";
            type empty;
          }
          leaf no-world-readable {
            description "Don't allow any user to read the log file";
            type empty;
          }
        }
        leaf match {
          description "Regular expression for lines to be logged";
          type jt:regular-expression;
        }
      }
      leaf level {
        description "Level of debugging output";
        default "error";
        type enumeration {
          enum error {
            description "Match error conditions";
          }
          enum warning {
            description "Match warning messages";
          }
          enum notice {
            description "Match conditions that should be handled specially";
          }
          enum info {
            description "Match informational messages";
          }
          enum verbose {
            description "Match verbose messages";
          }
          enum all {
            description "Match all levels";
          }
        }
      }
      list flag {
        key name;
        ordered-by user;
        description "Type of operation or event to include in trace";
        leaf name {
          type enumeration {
            enum configuration {
              description "Configuration operations";
            }
            enum routing-socket {
              description "Routing socket operations";
            }
            enum interface-device {
              description "Interface device operations";
            }
            enum interface-logical {
              description "Logical interface operations";
            }
            enum interface-family {
              description "Interface family operations";
            }
            enum bridging-domain {
              description "Bridging domain operations";
            }
            enum routing-instance {
              description "Routing instance operations";
            }
            enum bridge-interface {
              description "Interface bridge operations";
            }
            enum learning-domain {
              description "Learning domain operations";
            }
            enum ipc {
              description "Inter-process communications operations";
            }
            enum mac-learning {
              description "MAC address learning operations";
            }
            enum initialization {
              description "Initialization operations";
            }
            enum flood-next-hop {
              description "Flood next hop operations";
            }
            enum irb {
              description "Integrated routing and bridging operations";
            }
            enum vpls-ping {
              description "VPLS ping operations";
            }
            enum vpls-loop-prev {
              description "VPLS loop prevention";
            }
            enum logical-system {
              description "Logical system operations";
            }
            enum bmac-next-hop {
              description "Backbone Mac Next hop operations ";
            }
            enum bridge-bmac-next-hop {
              description "Bmac Next hop bridge operations";
            }
            enum isid {
              description "I-Tagged Service ID";
            }
            enum mc-ae {
              description "Multi-chassis AE";
            }
            enum kack {
              description "Kernel-acknowledgment";
            }
            enum storm-control {
              description "Storm-control";
            }
            enum redundant-trunk-group {
              description "Redundant trunk group";
            }
            enum unknown-unicast-forwarding {
              description "Trace unknown unicast forwarding events";
            }
            enum vxlan {
              description "VXLAN";
            }
            enum l2-license {
              description "L2 license trace";
            }
            enum telemetry {
              description "Telemetry";
            }
            enum network-isolation {
              description "Network isolation detection";
            }
            enum all {
              description "All operations";
            }
          }
        }
      }
      container kernel {
        presence "enable kernel";
        description "Trace options for kernel";
        container irb {
          presence "enable irb";
          description "Trace options for irb";
        }
      }
      container in-memory-debug {
        presence "enable in-memory-debug";
        description "Enable trace parameters in the memory";
      }
    }
    container global-mac-move {
      presence "enable global-mac-move";
      description "Enable mac move related options at global level";
      leaf notification-time {
        description "Periodical time interval in secs during which MAC move notification occurs";
        units seconds;
        type union {
          type uint32;
          type string {
            pattern "<.*>|$.*";
          }
        }
      }
      leaf threshold-time {
        description "Time during which if certain number of MAC moves happen warrant recording";
        units seconds;
        type union {
          type uint32;
          type string {
            pattern "<.*>|$.*";
          }
        }
      }
      leaf reopen-time {
        description "Time after which a blocked interface is reopened";
        units seconds;
        type union {
          type uint32;
          type string {
            pattern "<.*>|$.*";
          }
        }
      }
      leaf threshold-count {
        description "Count of MAC moves which warrant recording when happen in certain time";
        units seconds;
        type union {
          type uint32;
          type string {
            pattern "<.*>|$.*";
          }
        }
      }
      container traceoptions {
        description "Enable logging for the MAC moves";
        leaf no-remote-trace {
          description "Disable remote tracing";
          type empty;
        }
        container file {
          description "Trace file information";
          leaf filename {
            description "Name of file in which to write trace information";
            type string {
              length "1 .. 1024";
            }
          }
          leaf size {
            description "Maximum trace file size";
            type string;
          }
          leaf files {
            description "Maximum number of trace files";
            default "3";
            type union {
              type string {
                pattern "<.*>|$.*";
              }
              type uint32 {
                range "2 .. 1000";
              }
            }
          }
          choice world-readable-choice {
            leaf world-readable {
              description "Allow any user to read the log file";
              type empty;
            }
            leaf no-world-readable {
              description "Don't allow any user to read the log file";
              type empty;
            }
          }
          leaf match {
            description "Regular expression for lines to be logged";
            type jt:regular-expression;
          }
        }
      }
      leaf log {
        description "Syslog all the MAC moves as stored in the mac-move-buffer";
        type empty;
      }
      leaf disable-action {
        description "Disable mac move action globally";
        type empty;
      }
      leaf cooloff-time {
        description "Time interval in secs during which no further actions are taken";
        units seconds;
        type union {
          type uint32;
          type string {
            pattern "<.*>|$.*";
          }
        }
      }
      leaf statistical-approach-wait-time {
        description "Time during which MAC moves are monitored to collect statistics";
        units seconds;
        type union {
          type uint32;
          type string {
            pattern "<.*>|$.*";
          }
        }
      }
      leaf interface-recovery-time {
        description "Time interval after which interface is made operationally up";
        units seconds;
        type union {
          type uint32;
          type string {
            pattern "<.*>|$.*";
          }
        }
      }
      list exclusive-mac {
        key name;
        ordered-by user;
        description "MAC addresses to be excluded in mac-move-limit or in VPLS loop prevention algorithm";
        leaf name {
          description "Source MAC address";
          type jt:mac-addr-prefix;
        }
      }
    }
    leaf global-mac-table-aging-time {
      description "System level MAC table aging time";
      units seconds;
      type union {
        type string {
          pattern "<.*>|$.*";
        }
        type uint32;
      }
    }
    leaf global-mac-ip-table-aging-time {
      description "System level MAC+IP table aging time";
      units seconds;
      type union {
        type string {
          pattern "<.*>|$.*";
        }
        type uint32 {
          range "60 .. 1000000";
        }
      }
    }
    leaf global-le-aging-time {
      description "Set LE aging time";
      units seconds;
      type union {
        type string {
          pattern "<.*>|$.*";
        }
        type uint32 {
          range "120 .. 1000000";
        }
      }
    }
    leaf global-le-bridge-domain-aging-time {
      description "Set LE bridge-domain aging time";
      units seconds;
      type union {
        type string {
          pattern "<.*>|$.*";
        }
        type uint32 {
          range "120 .. 1000000";
        }
      }
    }
    leaf mclag-arpreq-sync {
      description "Enable syncing ARP REQ packets to peer MCLAG PE";
      type empty;
    }
    leaf global-mac-pinning-discard-notification-interval {
      description "Set interval for MAC Pinning discard notification";
      units seconds;
      type union {
        type string {
          pattern "<.*>|$.*";
        }
        type uint32 {
          range "2 .. 86400";
        }
      }
    }
    container global-ctx-limit {
      presence "enable global-ctx-limit";
      description "Debug context history limit";
      leaf ctx-limit {
        description "Debug context history limit";
        type union {
          type string {
            pattern "<.*>|$.*";
          }
          type uint32 {
            range "0 .. 5000000";
          }
        }
      }
    }
    container global-mac-limit {
      presence "enable global-mac-limit";
      description "System level MAC limit options";
      leaf mac-limit {
        description "System level MAC limit";
        type union {
          type string {
            pattern "<.*>|$.*";
          }
          type uint64;
        }
      }
      leaf packet-action {
        type enumeration {
          enum drop {
            description "Enable packet-action drop when MAC limit is reached";
          }
        }
      }
    }
    container global-mac-ip-limit {
      presence "enable global-mac-ip-limit";
      description "System level MAC+IP limit options";
      leaf mac-ip-limit {
        description "System level MAC+IP limit";
        type union {
          type string {
            pattern "<.*>|$.*";
          }
          type uint64 {
            range "20 .. 1048575";
          }
        }
      }
    }
    leaf global-mac-statistics {
      description "Enable MAC address statistics at system level";
      type empty;
    }
    leaf global-static-mac-move-drop-log {
      description "Set global static mac move drop and log notification.";
      type empty;
    }
    leaf source-udp-port {
      description "VXLAN source UDP port";
      type union {
        type string {
          pattern "<.*>|$.*";
        }
        type uint16 {
          range "49152 .. 65535";
        }
      }
    }
    container telemetry {
      presence "enable telemetry";
      description "Streaming Telemetry Data";
      leaf enable-remote-entries {
        description "Enable Remote mac and mac-ip entries";
        type empty;
      }
    }
    leaf global-no-mac-learning {
      description "Disable dynamic MAC address learning at system level";
      type empty;
    }
    leaf global-no-hw-mac-learning {
      description "Disable hardware MAC-address learning at system level";
      type empty;
    }
    leaf global-no-control-mac-aging {
      description "Disable control MAC-address aging from software";
      type empty;
    }
    leaf mclag-arp-nd-sync {
      description "Arp and ND entry sync from peer device.";
      type empty;
    }
    leaf no-mclag-ifa-sync {
      description "IFA entry disable sync from/to peer device.";
      type empty;
    }
    container platform-parameters {
      presence "enable platform-parameters";
      description "Platform Parameters Setting";
      container no-mac-flush-on-aa-ae-down {
        presence "enable no-mac-flush-on-aa-ae-down";
        description "Do not flush MAC & MAC-IP entries when active-active AE interface goes down";
        choice enable-disable {
          case case_1 {
            leaf disable {
              description "Disable no-mac-flush-on-aa-ae-down";
              type empty;
            }
          }
        }
      }
    }
    container crb-proxy-mac {
      description "Configure proxy MAC address to be used in MAC-IP refresh";
      container family {
        description "Address family";
        container inet {
          description "Inet version 4 family";
          leaf mac-address {
            description "Proxy MAC address";
            type jt:mac-unicast;
          }
        }
        container inet6 {
          description "Inet version 6 family";
          leaf mac-address {
            description "Proxy MAC address";
            type jt:mac-unicast;
          }
        }
      }
    }
    leaf arp-nd-probe-disable {
      description "Disable probing for ip address";
      type empty;
    }
    leaf arp-nd-probe-failed-log {
      description "Enable syslog when probing for ip address fails";
      type empty;
    }
    leaf garp-na-enable {
      description "Send GARP or unsolicited NA to all connected access devices";
      type empty;
    }
  }
  grouping juniper-protocols-dot1x {
    container traceoptions {
      description "Trace options for 802.1X";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum dot1x-debug {
              description "Trace dot1x events";
            }
            enum parse {
              description "Trace configuration parsing";
            }
            enum esw-if {
              description "Trace ESW Interactions";
            }
            enum eapol {
              description "Trace EAPOL Transmit/Receive";
            }
            enum config-internal {
              description "Trace configuration internals";
            }
            enum normal {
              description "Trace normal events";
            }
            enum general {
              description "Trace general events";
            }
            enum state {
              description "Trace state transitions";
            }
            enum task {
              description "Trace routing protocol task processing";
            }
            enum timer {
              description "Trace routing protocol task timer processing";
            }
            enum vlan {
              description "Trace VLAN transactions";
            }
            enum all {
              description "Trace everything";
            }
            enum dot1x-ipc {
              description "Trace dot1x IPC interactions";
            }
            enum dot1x-event {
              description "Trace dot1x events";
            }
            enum iccp {
              description "Trace iccp events";
            }
          }
        }
        leaf disable {
          description "Disable this trace flag";
          type empty;
        }
      }
    }
    leaf ssl-certificate-path {
      description "Load SSL certificates for authentication";
      default "/var/tmp/";
      type string;
    }
    container authenticator {
      presence "enable authenticator";
      description "802.1X authenticator options";
      leaf authentication-profile-name {
        description "Access profile name to use for authentication";
        type string {
          length "1 .. 63";
        }
      }
      leaf no-mac-table-binding {
        description "Disable association between mac table and dot1x";
        type empty;
      }
      leaf ip-mac-session-binding {
        description "DHCP or DHCPv6 or SLAAC snooping checking for mac ageout";
        type empty;
      }
      leaf dynamic-vlan-cleanup-interval {
        description "Dynamic vlan cleanup interval";
        units seconds;
        type union {
          type string {
            pattern "<.*>|$.*";
          }
          type uint32 {
            range "60 .. 86400";
          }
        }
      }
      container radius-reachability {
        presence "enable radius-reachability";
        description "Enable radius-rechability feature";
        leaf query-period {
          description "Query period interval";
          default "120";
          units seconds;
          type union {
            type string {
              pattern "<.*>|$.*";
            }
            type uint32 {
              range "20 .. 65535";
            }
          }
        }
      }
      container radius-options {
        presence "enable radius-options";
        description "Info sent to radius server";
        leaf add-interface-text-description {
          description "Appends interface text description to NAS-Port-Id";
          type empty;
        }
        choice vlan {
          case case_1 {
            leaf use-vlan-name {
              description "Vlan name";
              type empty;
            }
          }
          case case_2 {
            leaf use-vlan-id {
              description "Vlan id";
              type empty;
            }
          }
        }
      }
      list static {
        key name;
        ordered-by user;
        description "Static MAC configuration needed to bypass 802.1X";
        leaf name {
          description "MAC addresses to bypass authentication";
          type jt:mac-addr-prefix;
        }
        leaf vlan-assignment {
          description "VLAN name or 802.1q tag for the MAC address";
          type string;
        }
        leaf bridge-domain-assignment {
          description "Bridge-domain name or 802.1q tag for the MAC address";
          type string;
        }
        leaf interface {
          description "Interface on which authentication is bypassed";
          type union {
            type jt:interface-name;
            type string {
              pattern "<.*>|$.*";
            }
          }
        }
      }
      list interface {
        key name;
        description "802.1X  interface specific options";
        leaf name {
          type string;
        }
        leaf ignore-port-bounce {
          description "To ignore the port-bounce request received from RADIUS server";
          type empty;
        }
        leaf-list authentication-order {
          ordered-by user;
          description "Flexible authentication order";
          type enumeration {
            enum dot1x {
              description "Dot1x mode";
            }
            enum mac-radius {
              description "Mac radius mode";
            }
            enum captive-portal {
              description "Captive portal mode";
            }
          }
        }
        leaf disable {
          description "Disable 802.1X on this interface";
          type empty;
        }
        leaf supplicant {
          description "Set supplicant mode for this interface";
          default "single";
          type enumeration {
            enum single {
              description "Allow multiple clients; authenticate first client only";
            }
            enum single-secure {
              description "Allow and authenticate only a single client";
            }
            enum multiple {
              description "Allow multiple clients; authenticate each individually";
            }
          }
        }
        leaf retries {
          description "Number of retries after which port is placed into wait state";
          type union {
            type string {
              pattern "<.*>|$.*";
            }
            type uint32 {
              range "0 .. 10";
            }
          }
        }
        leaf quiet-period {
          description "Time to wait after an authentication failure";
          units seconds;
          type union {
            type string {
              pattern "<.*>|$.*";
            }
            type uint32 {
              range "0 .. 65535";
            }
          }
        }
        leaf transmit-period {
          description "Interval before retransmitting initial EAPOL PDUs";
          units seconds;
          type union {
            type string {
              pattern "<.*>|$.*";
            }
            type uint32 {
              range "1 .. 65535";
            }
          }
        }
        container multi-domain {
          presence "enable multi-domain";
          description "Enable multi domain authentication";
          leaf packet-action {
            description "Set packet action for this interface";
            default "drop-and-log";
            type enumeration {
              enum drop-and-log {
                description " Drop the client and generate the log message";
              }
              enum shutdown {
                description "Disable port for excessive client authentication";
              }
            }
          }
          leaf max-data-session {
            description "Data session limit in multi domain authentication";
            type union {
              type string {
                pattern "<.*>|$.*";
              }
              type uint32 {
                range "1 .. 1000";
              }
            }
          }
          leaf recovery-timeout {
            description "Multi domain recovery timeout";
            units seconds;
            type union {
              type string {
                pattern "<.*>|$.*";
              }
              type uint32 {
                range "60 .. 3600";
              }
            }
          }
        }
        container mac-radius {
          presence "enable mac-radius";
          description "Enable MAC-RADIUS";
          leaf restrict {
            description "Bypass dot1x authentication, use MAC RADIUS only";
            type empty;
          }
          leaf flap-on-disconnect {
            description "Reset an interface on receiving a disconnect request";
            type empty;
          }
          container authentication-protocol {
            description "Set mac-radius authentication method";
            choice protocols {
              case case_1 {
                leaf eap-md5 {
                  description "Authentication protocol EAP-MD5";
                  type empty;
                }
              }
              case case_2 {
                leaf pap {
                  description "Authentication protocol PAP";
                  type empty;
                }
              }
              case case_3 {
                container eap-peap {
                  presence "enable eap-peap";
                  description "Authentication protocol EAP-PEAP";
                  leaf resume {
                    description "Enable resume functionality for faster authentication";
                    type empty;
                  }
                }
              }
            }
          }
        }
        choice reauthentication-mode {
          case case_1 {
            leaf no-reauthentication {
              description "Disable reauthentication";
              type empty;
            }
          }
          case case_2 {
            leaf reauthentication {
              description "Reauthentication interval";
              units seconds;
              type union {
                type string {
                  pattern "<.*>|$.*";
                }
                type uint32 {
                  range "1 .. 65535";
                }
              }
            }
          }
        }
        leaf supplicant-timeout {
          description "Time to wait for a client response";
          units seconds;
          type union {
            type string {
              pattern "<.*>|$.*";
            }
            type uint32 {
              range "1 .. 60";
            }
          }
        }
        leaf server-timeout {
          description "Authentication server timeout interval";
          units seconds;
          type union {
            type string {
              pattern "<.*>|$.*";
            }
            type uint32 {
              range "1 .. 60";
            }
          }
        }
        leaf maximum-requests {
          description "Number of EAPOL RequestIDs to send before timing out";
          type union {
            type string {
              pattern "<.*>|$.*";
            }
            type uint32 {
              range "1 .. 10";
            }
          }
        }
        leaf request-retry-count {
          description "Number of requests to send before timing out";
          type union {
            type string {
              pattern "<.*>|$.*";
            }
            type uint32 {
              range "1 .. 10";
            }
          }
        }
        leaf guest-vlan {
          description "VLAN name or 802.1q tag for unauthenticated or non-responsive hosts";
          type string;
        }
        leaf guest-gbp-tag {
          description "GBP tag for unauthenticated or non-responsive hosts";
          type union {
            type string {
              pattern "<.*>|$.*";
            }
            type uint32 {
              range "1 .. 65535";
            }
          }
        }
        leaf guest-bridge-domain {
          description "Bridge-domain name or 802.1q tag for unauthenticated or non-responsive hosts";
          type string;
        }
        container server-reject-vlan {
          description "VLAN name or 802.1q tag for authentication rejected clients";
          leaf vlan-name {
            description "VLAN name or VLAN Tag (1..4095)";
            type string;
          }
          leaf block-interval {
            description "Interval for authenticator to ignore the EAP-Start packets.";
            units seconds;
            type union {
              type string {
                pattern "<.*>|$.*";
              }
              type uint32 {
                range "120 .. 65535";
              }
            }
          }
          leaf eapol-block {
            description "Force the authenticator to ignore EAPOL-Start packets.";
            type empty;
          }
          leaf gbp-tag {
            description "GBP tag for authentication rejected clients";
            type union {
              type string {
                pattern "<.*>|$.*";
              }
              type uint32 {
                range "1 .. 65535";
              }
            }
          }
        }
        container server-reject-bridge-domain {
          description "VLAN name or 802.1q tag for authentication rejected clients";
          leaf bridge-domain {
            description "Bridge-domain name or VLAN Tag (1..4095)";
            type string;
          }
          leaf block-interval {
            description "Interval for authenticator to ignore the EAP-Start packets.";
            units seconds;
            type union {
              type string {
                pattern "<.*>|$.*";
              }
              type uint32 {
                range "120 .. 65535";
              }
            }
          }
          leaf eapol-block {
            description "Force the authenticator to ignore EAPOL-Start packets.";
            type empty;
          }
        }
        container eapol-block {
          description "Force the authenticator to ignore EAPOL-Start packets";
          container server-fail {
            presence "enable server-fail";
            description "Block EAPOL-Start during RADIUS Timeout";
            leaf block-interval {
              description "Interval for authenticator to ignore the EAP-Start packets.";
              units seconds;
              type union {
                type string {
                  pattern "<.*>|$.*";
                }
                type uint32 {
                  range "120 .. 65535";
                }
              }
            }
          }
          container mac-radius {
            presence "enable mac-radius";
            description "Block EAPOL-Start when client is authenticated in mac-radius mode";
          }
          container captive-portal {
            presence "enable captive-portal";
            description "Block EAPOL-Start when client is authenticated in captive-portal mode";
          }
        }
        leaf lldp-med-bypass {
          description "Bypass dot1x authentication, use lldp-med based authentication";
          type empty;
        }
        container server-fail {
          description "Action to be taken when server is inaccessible";
          leaf gbp-tag {
            description "GBP tag to be assigned when server is inaccessible";
            type union {
              type string {
                pattern "<.*>|$.*";
              }
              type uint32 {
                range "1 .. 65535";
              }
            }
          }
          choice server-fail-options {
            case case_1 {
              leaf deny {
                description "Force client authentication to fail";
                type empty;
              }
            }
            case case_2 {
              leaf permit {
                description "Force client authentication to succeed";
                type empty;
              }
            }
            case case_3 {
              leaf vlan-name {
                description "VLAN name or 802.1q tag for unreachable servers";
                type string;
              }
            }
            case case_4 {
              leaf bridge-domain {
                description "Bridge-domain name or 802.1q tag for unreachable servers";
                type string;
              }
            }
            case case_5 {
              leaf use-cache {
                description "Use the previous state of the client";
                type empty;
              }
            }
          }
        }
        container server-fail-voip {
          description "Action to be taken for VOIP client when server is inaccessible";
          choice server-fail-options {
            case case_1 {
              leaf deny {
                description "Force VoIP client authentication to fail";
                type empty;
              }
            }
            case case_2 {
              leaf permit {
                description "Force VoIP client authentication to succeed";
                type empty;
              }
            }
            case case_3 {
              leaf vlan-name {
                description "Configured VoIP VLAN name or 802.1q tag for unreachable servers";
                type string;
              }
            }
            case case_4 {
              leaf use-cache {
                description "Use the previous state of the VoIP client";
                type empty;
              }
            }
          }
        }
        leaf redirect-url {
          description "CWA redirect URL to be used for unauthenticated users";
          type string {
            length "10 .. 247";
          }
        }
        leaf no-tagged-mac-authentication {
          description "Don't allow tagged mac for radius authentication";
          type empty;
        }
        leaf retain-mac-aged-session {
          description "Retain mac aged out session";
          type empty;
        }
      }
      container mac-radius {
        presence "enable mac-radius";
        description "User-defined options for mac-radius mode";
        leaf password {
          description "Specify the user-defined password to be used for mac authentication";
          type string {
            length "1 .. 128";
          }
        }
      }
    }
    container supplicant {
      description "802.1X supplicant options";
      list interface {
        key name;
        description "802.1X supplicant interface specific options";
        leaf name {
          type string;
        }
        leaf authentication-method {
          description "802.1X supplicant authentication protocol for this interface";
          default "eap-tls";
          type enumeration {
            enum eap-tls {
              description "Supplicant authentication protocol EAP-TLS";
            }
          }
        }
        leaf local-certificate {
          description "Local certificate identifier to be presented for authentication";
          type string;
        }
        leaf user-id {
          description "User id, to be presented for authentication";
          type string {
            length "1 .. 63";
          }
        }
        leaf password {
          description "Password, to be presented for authentication";
          type string {
            length "1 .. 63";
          }
        }
      }
    }
  }
  grouping juniper-protocols-esis {
    choice enable-disable {
      case case_1 {
        leaf disable {
          description "Disable ES-IS";
          type empty;
        }
      }
    }
    container traceoptions {
      description "Trace options for ES-IS";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum error {
              description "Trace errored packets";
            }
            enum esh {
              description "Trace end system hello packets";
            }
            enum ish {
              description "Trace intermediate system hello packets";
            }
            enum graceful-restart {
              description "Trace graceful restart events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf preference {
      description "Preference of routes";
      type union {
        type uint32;
        type string {
          pattern "<.*>|$.*";
        }
      }
    }
    container graceful-restart {
      description "ES-IS graceful restart options";
      choice enable-disable {
        case case_1 {
          leaf disable {
            description "Disable graceful restart";
            type empty;
          }
        }
      }
      leaf restart-duration {
        description "Maximum time for graceful restart to finish";
        units seconds;
        type union {
          type string {
            pattern "<.*>|$.*";
          }
          type uint32 {
            range "30 .. 300";
          }
        }
      }
    }
    list interface {
      key name;
      description "Interface configuration";
      leaf name {
        description "Interface name";
        type union {
          type jt:interface-name;
          type string {
            pattern "<.*>|$.*";
          }
        }
      }
      leaf hold-time {
        description "Time after which neighbors think the interface is down";
        units seconds;
        type union {
          type string {
            pattern "<.*>|$.*";
          }
          type uint32 {
            range "1 .. 65535";
          }
        }
      }
      leaf end-system-configuration-timer {
        description "Suggested end system configuration timer";
        units seconds;
        type union {
          type string {
            pattern "<.*>|$.*";
          }
          type uint32 {
            range "1 .. 65535";
          }
        }
      }
      choice enable-disable {
        case case_1 {
          leaf disable {
            description "Disable ES-IS on this interface";
            type empty;
          }
        }
      }
    }
  }
  grouping juniper-protocols-evpn-interconnect {
    description "Interconnect configuration for the routing instance";
    leaf-list vrf-import {
      ordered-by user;
      description "Import policy for Interconnect";
      type jt:policy-algebra;
    }
    leaf-list vrf-export {
      ordered-by user;
      description "Export policy for Interconnect";
      type jt:policy-algebra;
    }
    container vrf-target {
      description "Interconnect target community configuration";
      leaf community {
        description "Target community to use in import and export";
        type string;
      }
      leaf import {
        description "Target community to use when filtering on import";
        type string;
      }
      leaf export {
        description "Target community to use when marking routes on export";
        type string;
      }
    }
    container route-distinguisher {
      description "Route distinguisher for this interconnect";
      leaf rd-type {
        description "Number in (16 bit:32 bit) or (32 bit 'L':16 bit) or (IP address:16 bit) format";
        type string;
      }
    }
    list domain-path-id {
      key name;
      ordered-by user;
      description "DCI VRF domain path id configuration";
      max-elements 1;
      uses domain-id-type;
    }
    container esi {
      description "ESI configuration of interconnect";
      leaf identifier {
        description "ESI value for interconnect";
        type jt:esi;
      }
      choice mode {
        case case_1 {
          leaf all-active {
            description "All-active mode";
            type empty;
          }
        }
      }
      container df-election-type {
        presence "enable df-election-type";
        description "DF Election Type";
        choice pref_choice {
          case case_1 {
            container preference {
              presence "enable preference";
              description "Preference based DF election";
              leaf value {
                description "Preference value for EVPN Multihoming DF election";
                default "32767";
                type union {
                  type string {
                    pattern "<.*>|$.*";
                  }
                  type uint32 {
                    range "0 .. 65535";
                  }
                }
              }
            }
          }
        }
        choice mod_choice {
          case case_1 {
            container mod {
              presence "enable mod";
              description "MOD based DF election";
            }
          }
        }
      }
    }
    leaf-list interconnected-vni-list {
      description "List of translated VNIs (1..16777214) or all, that are to be EVPN interconnected";
      type string;
    }
    leaf-list interconnected-vlan-list {
      ordered-by user;
      description "List of VLAN identifiers that are to be EVPN interconnected";
      type string;
    }
    container irb-symmetric-routing {
      description "Enable EVPN T-2 symmetric DCI routing";
      leaf vni {
        description "VXLAN network identifier used for T-2 symmetric routing IP prefixes";
        type union {
          type string {
            pattern "<.*>|$.*";
          }
          type uint32 {
            range "1 .. 16777214";
          }
        }
      }
    }
    leaf encapsulation {
      type enumeration {
        enum mpls {
          description "MPLS encapsulation";
        }
        enum vxlan {
          description "VXLAN encapsulation";
        }
      }
    }
  }
  grouping domain-id-type {
    leaf name {
      description "Domain id for type 5 evpn DCI";
      type string;
    }
  }
  grouping juniper-protocols-isis {
    list interface {
      key name;
      description "Interface configuration";
      leaf name {
        description "Interface name";
        type union {
          type jt:interface-name;
          type string {
            pattern "<.*>|$.*";
          }
        }
      }
      container ldp-synchronization {
        description "Advertise maximum metric until LDP is operational";
        presence "enable ldp-synchronization";
        uses ldp-sync-obj;
      }
      list level {
        key name;
        ordered-by user;
        description "Configure levels on this interface";
        leaf name {
          description "IS-IS level number";
          type union {
            type string {
              pattern "<.*>|$.*";
            }
            type uint32 {
              range "1 .. 2";
            }
          }
        }
        choice enable-disable {
          case case_1 {
            leaf disable {
              description "Disable IS-IS for this level";
              type empty;
            }
          }
        }
        leaf metric {
          description "Metric for this level";
          type union {
            type string {
              pattern "<.*>|$.*";
            }
            type uint32 {
              range "0 .. 16777215";
            }
          }
        }
      }
      leaf lsp-interval {
        description "Interval between LSP transmissions";
        default "100";
        units milliseconds;
        type union {
          type string {
            pattern "<.*>|$.*";
          }
          type uint32 {
            range "1 .. 1000";
          }
        }
      }
      leaf point-to-point {
        description "Treat interface as point to point";
        type empty;
      }
      container passive {
        presence "enable passive";
        description "Do not run IS-IS, but advertise it";
        leaf remote-node-iso {
          description "ISO System-ID of the remote node";
          type jt:sysid;
        }
        leaf remote-node-id {
          description "Remote address of the link";
          type jt:ipv4addr;
        }
      }
      list family {
        key name;
        ordered-by user;
        description "Address family specific interface attributes";
        leaf name {
          type enumeration {
            enum inet {
              description "IPv4 family";
            }
            enum inet6 {
              description "IPv6 family";
            }
          }
        }
        container bfd-liveness-detection {
          description "Bidirectional Forwarding Detection options";
          leaf version {
            description "BFD protocol version number";
            default "automatic";
            type enumeration {
              enum 0 {
                description "BFD version 0 (deprecated)";
              }
              enum 1 {
                description "BFD version 1";
              }
              enum automatic {
                description "Choose BFD version automatically";
              }
            }
          }
          leaf minimum-interval {
            description "Minimum transmit and receive interval";
            units milliseconds;
            type union {
              type string {
                pattern "<.*>|$.*";
              }
              type uint32 {
                range "1 .. 255000";
              }
            }
          }
          leaf minimum-transmit-interval {
            description "Minimum transmit interval";
            status deprecated;
            units milliseconds;
            type union {
              type string {
                pattern "<.*>|$.*";
              }
              type uint32 {
                range "1 .. 255000";
              }
            }
          }
          leaf minimum-receive-interval {
            description "Minimum receive interval";
            units milliseconds;
            type union {
              type string {
                pattern "<.*>|$.*";
              }
              type uint32 {
                range "1 .. 255000";
              }
            }
          }
          leaf multiplier {
            description "Detection time multiplier";
            default "3";
            type union {
              type string {
                pattern "<.*>|$.*";
              }
              type uint32 {
                range "1 .. 255";
              }
            }
          }
          leaf inline-disable {
            description "Disable inline mode for this BFD session";
            type empty;
          }
          leaf pdu-size {
            description "BFD transport protocol payload size";
            default "24";
            type union {
              type string {
                pattern "<.*>|$.*";
              }
              type uint32 {
                range "24 .. 9000";
              }
            }
          }
          choice adaptation-choice {
            case case_1 {
              leaf no-adaptation {
                description "Disable adaptation";
                type empty;
              }
            }
          }
          container transmit-interval {
            description "Transmit-interval options";
            leaf minimum-interval {
              description "Minimum transmit interval";
              units milliseconds;
              type union {
                type string {
                  pattern "<.*>|$.*";
                }
                type uint32 {
                  range "1 .. 255000";
                }
              }
            }
            leaf threshold {
              description "High transmit interval triggering a trap";
              units milliseconds;
              type union {
                type uint32;
                type string {
                  pattern "<.*>|$.*";
                }
              }
            }
          }
          container detection-time {
            description "Detection-time options";
            leaf threshold {
              description "High detection-time triggering a trap";
              units milliseconds;
              type union {
                type uint32;
                type string {
                  pattern "<.*>|$.*";
                }
              }
            }
          }
          container authentication {
            description "Authentication options";
            leaf key-chain {
              description "Key chain name";
              type string;
            }
            leaf algorithm {
              description "Algorithm name";
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
            }
            leaf loose-check {
              description "Verify authentication only if authentication is negotiated";
              type empty;
            }
          }
          container echo {
            description "Echo mode parameters";
            leaf minimum-interval {
              description "Minimum transmit and receive interval";
              units milliseconds;
              type union {
                type string {
                  pattern "<.*>|$.*";
                }
                type uint32 {
                  range "100 .. 255000";
                }
              }
            }
          }
          container echo-lite {
            description "Echo-lite more parameters";
            leaf minimum-interval {
              description "Minimum transmit and receive interval";
              units milliseconds;
              type union {
                type string {
                  pattern "<.*>|$.*";
                }
                type uint32 {
                  range "100 .. 255000";
                }
              }
            }
          }
          leaf holddown-interval {
            description "Time to hold the session-UP notification to the client";
            units milliseconds;
            type union {
              type string {
                pattern "<.*>|$.*";
              }
              type uint32 {
                range "0 .. 255000";
              }
            }
          }
        }
      }
    }
    container source-packet-routing {
      presence "enable source-packet-routing";
      description "Enable Source Packet Routing (SPRING)";
      container adjacency-segment {
        description "Configure attributes for Adjacency Segments in SPRING";
        leaf hold-time {
          description "Duration(ms) for which adjacency segments will be retained after isolating from an interface";
          type union {
            type string {
              pattern "<.*>|$.*";
            }
            type uint32 {
              range "180000 .. 900000";
            }
          }
        }
      }
      container udp-tunneling {
        description "Enable SR over UDP feature";
        leaf encapsulation {
          description "Enable UDP Tunnel Encapsulation";
          type empty;
        }
        leaf decapsulation {
          description "Enable UDP Tunnel decapsulation";
          type empty;
        }
      }
      container srgb {
        description "Set the SRGB global block in SPRING";
        leaf start-label {
          description "Start range for SRGB label block";
          type union {
            type string {
              pattern "<.*>|$.*";
            }
            type uint32;
          }
        }
        leaf index-range {
          description "Index to the SRGB start label block";
          type union {
            type string {
              pattern "<.*>|$.*";
            }
            type uint32;
          }
        }
      }
      container node-segment {
        description "Enable support for Node segments in SPRING";
        leaf ipv4-index {
          description "Set IPv4 Node Segment index";
          type union {
            type string {
              pattern "<.*>|$.*";
            }
            type uint32 {
              range "0 .. 199999";
            }
          }
        }
        leaf ipv6-index {
          description "Set IPv6 Node Segment index";
          type union {
            type string {
              pattern "<.*>|$.*";
            }
            type uint32 {
              range "0 .. 199999";
            }
          }
        }
        leaf index-range {
          description "Set Range of Node Segment indices allowed";
          type union {
            type string {
              pattern "<.*>|$.*";
            }
            type uint32 {
              range "32 .. 16385";
            }
          }
        }
      }
      leaf-list flex-algorithm {
        description "Flex-algorithms we would like to participate in";
        type union {
          type string {
            pattern "<.*>|$.*";
          }
          type uint32 {
            range "128 .. 255";
          }
        }
        max-elements 16;
      }
      leaf use-flex-algorithm-metric-always {
        description "Use flex-algo prefix metric whenever available";
        type empty;
      }
      leaf strict-asla-based-flex-algorithm {
        description "Flex-Algorithm to ignore links not having ASLA sub-TLVs";
        type empty;
      }
      leaf new-capability-subtlv {
        description "Advertise all ranges in single spring capability subtlv";
        type empty;
      }
      leaf explicit-null {
        description "Set E and P bits in all Prefix SID advertisements";
        type empty;
      }
      leaf mapping-server {
        description "Mapping server name";
        type string;
      }
      leaf no-strict-spf {
        description " Disable strict spf algo 1 advertisement";
        type empty;
      }
      leaf no-binding-sid-leaking {
        description " Disable SRMS binding sid leaking";
        type empty;
      }
      leaf ldp-stitching {
        description "Enable SR to LDP stitching";
        type empty;
      }
      container srv6 {
        presence "enable srv6";
        description "Enable IPv6 Segment Routing (SRv6)";
        list locator {
          key name;
          ordered-by user;
          description "SRv6 Locator";
          leaf name {
            description "Locator name";
            type string;
          }
          leaf anycast {
            description "Set A flag in the Prefix-Attribute sub-TLV";
            type empty;
          }
          list end-sid {
            key name;
            ordered-by user;
            leaf name {
              type jt:ipv6addr;
            }
            container flavor {
              presence "enable flavor";
              description "Configure end-SID flavor";
              leaf psp {
                description "Penultimate segment pop of the SRH";
                type empty;
              }
              leaf usp {
                description "Ultimate segment pop of the SRH";
                type empty;
              }
              leaf usd {
                description "Ultimate segment decapsulation";
                type empty;
              }
            }
          }
          container dynamic-end-sid {
            presence "enable dynamic-end-sid";
            description "Allocate end SID dynamically";
            container flavor {
              presence "enable flavor";
              description "Configure end-SID flavor";
              leaf psp {
                description "Penultimate segment pop of the SRH";
                type empty;
              }
              leaf usp {
                description "Ultimate segment pop of the SRH";
                type empty;
              }
              leaf usd {
                description "Ultimate segment decapsulation";
                type empty;
              }
            }
          }
          leaf micro-node-sid {
            description "Program and advertise micro-node-SID";
            type empty;
          }
        }
      }
      container sensor-based-stats {
        description "Configure sensor based stats in SPRING";
        container per-interface-per-member-link {
          description "Configure sensor based stats per nexthop";
          leaf ingress {
            description "Enable sensor based stats on ingress interface";
            type empty;
          }
          leaf egress {
            description "Enable sensor based stats on egress interface";
            type empty;
          }
        }
        container per-sid {
          description "Configure sensor based stats per spring route";
          leaf ingress {
            description "Enable sensor based stats for per-sid ingress accounting";
            type empty;
          }
          leaf egress {
            description "Enable sensor based stats for IP-MPLS egress accounting";
            type empty;
          }
        }
        container subscribe {
          presence "enable subscribe";
          description "Enable on-box sensor-based statistics collection";
          leaf interval {
            description "Statistics collection interval (seconds)";
            type union {
              type string {
                pattern "<.*>|$.*";
              }
              type uint32 {
                range "30 .. 86400";
              }
            }
          }
        }
      }
      container traffic-statistics {
        description "Enable support for traffic statistics in SPRING";
        container statistics-granularity {
          description "Granularity for traffic statistics in SPRING";
          leaf per-interface {
            description "Interface Based traffic statistics in SPRING";
            type empty;
          }
        }
        leaf congestion-protection {
          description "Enable tactical traffic engineering";
          type empty;
        }
        leaf auto-bandwidth {
          description "Auto bandwidth name";
          type string;
        }
      }
    }
    list level {
      key name;
      ordered-by user;
      description "Configure global level attributes";
      leaf name {
        description "IS-IS level number";
        type union {
          type string {
            pattern "<.*>|$.*";
          }
          type uint32 {
            range "1 .. 2";
          }
        }
      }
      choice enable-disable {
        case case_1 {
          leaf disable {
            description "Disable IS-IS on this level";
            type empty;
          }
        }
      }
      leaf authentication-key {
        description "Authentication key (password)";
        type jt:unreadable;
      }
      leaf authentication-type {
        description "Authentication type";
        type enumeration {
          enum md5 {
            description "MD5 authentication";
          }
          enum simple {
            description "Simple password authentication";
          }
        }
      }
      leaf no-hello-authentication {
        description "Disable authentication for hello packets";
        type empty;
      }
      leaf no-csnp-authentication {
        description "Disable authentication for CSN packets";
        type empty;
      }
      leaf no-psnp-authentication {
        description "Disable authentication for PSN packets";
        type empty;
      }
      leaf wide-metrics-only {
        description "Generate wide metrics only";
        type empty;
      }
    }
    leaf lsp-lifetime {
      description "Lifetime of LSPs";
      units seconds;
      type union {
        type string {
          pattern "<.*>|$.*";
        }
        type uint32 {
          range "350 .. 65535";
        }
      }
    }
  }
  grouping juniper-protocols-l2control {
    container traceoptions {
      description "Global tracing options for STP";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum parse {
              description "Trace configuration parsing";
            }
            enum regex-parse {
              description "Trace regular-expression parsing";
            }
            enum config-internal {
              description "Trace configuration internals";
            }
            enum normal {
              description "Trace normal events";
            }
            enum general {
              description "Trace general events";
            }
            enum state {
              description "Trace state transitions";
            }
            enum task {
              description "Trace routing protocol task processing";
            }
            enum timer {
              description "Trace routing protocol task timer processing";
            }
            enum ppmlite {
              description "Trace libppmlite processing";
            }
            enum all {
              description "Trace everything";
            }
          }
        }
        leaf disable {
          description "Disable this trace flag";
          type empty;
        }
      }
    }
    leaf nonstop-bridging {
      description "Enable nonstop operation";
      type empty;
    }
    container options {
      description "Layer2 control options";
      container nsb-extended-timers {
        presence "enable nsb-extended-timers";
        description "Extend expiration of timers during switchover";
        choice enable-disable {
          case case_1 {
            leaf disable {
              description "Disable timer extension during switchover";
              type empty;
            }
          }
        }
      }
      container nsb-optimized-config-read {
        presence "enable nsb-optimized-config-read";
        description "Optimize config re-prasing during switchover";
        choice enable-disable {
          case case_1 {
            leaf disable {
              description "Disable optimized re-parsing of config during switchover";
              type empty;
            }
          }
        }
      }
    }
    choice ephemeral-db-support-choice {
      leaf ephemeral-db-support {
        description "Enable ephemeral DB supoort for STP";
        type empty;
      }
      leaf no-ephemeral-db-support {
        description "Don't enable ephemeral DB supoort for STP";
        type empty;
      }
    }
    container bpdu-block {
      presence "enable bpdu-block";
      description "Block BPDU on interface (BPDU Protect)";
      list interface {
        key name;
        ordered-by user;
        description "Interface name to block BPDU on";
        leaf name {
          type string;
        }
        leaf disable {
          description "Disable bpdu-block on a port";
          type empty;
        }
        leaf drop {
          description "Drop xSTP BPDUs";
          type empty;
        }
      }
      leaf disable-timeout {
        description "Disable timeout for BPDU Protect";
        units seconds;
        type union {
          type string {
            pattern "<.*>|$.*";
          }
          type int32 {
            range "10 .. 3600";
          }
        }
      }
    }
    container l2pt {
      description "L2 protocol tunneling functionality";
      list interface {
        key name;
        ordered-by user;
        leaf name {
          type union {
            type jt:interface-device;
            type string {
              pattern "<.*>|$.*";
            }
          }
        }
        leaf enable-all-ifl {
          description "Enable tunneling for all the IFLs under the interface";
          type empty;
        }
        container protocol {
          description "Protocols for which L2 protocol tunneling need to be enabled";
          container stp {
            presence "enable stp";
            description "Enable L2 protocol tunneling for STP";
          }
          container vtp {
            presence "enable vtp";
            description "Enable L2 protocol tunneling for VTP";
          }
          container cdp {
            presence "enable cdp";
            description "Enable L2 protocol tunneling for CDP";
          }
          container ieee8021x {
            presence "enable ieee8021x";
            description "Enable L2 protocol tunneling for 8021X";
          }
          container ieee8023ah {
            presence "enable ieee8023ah";
            description "Enable L2 protocol tunneling for 8023AH";
          }
          container elmi {
            presence "enable elmi";
            description "Enable L2 protocol tunneling for ELMI";
          }
          container lacp {
            presence "enable lacp";
            description "Enable L2 protocol tunneling for LACP";
          }
          container lldp {
            presence "enable lldp";
            description "Enable L2 protocol tunneling for LLDP";
          }
          container mmrp {
            presence "enable mmrp";
            description "Enable L2 protocol tunneling for MMRP";
          }
          container mvrp {
            presence "enable mvrp";
            description "Enable L2 protocol tunneling for MVRP";
          }
          container pvstp {
            presence "enable pvstp";
            description "Enable L2 protocol tunneling for PVSTP+";
          }
          container gvrp {
            presence "enable gvrp";
            description "Enable L2 protocol tunneling for GVRP";
          }
          container vstp {
            presence "enable vstp";
            description "Enable L2 protocol tunneling for VSTP";
          }
          container udld {
            presence "enable udld";
            description "Enable L2 protocol tunneling for UDLD";
          }
          container all {
            presence "enable all";
            description "Enable L2 protocol tunneling for all protocols";
          }
        }
        container destination {
          description "Destination tunnel for which L2 protocol tunneling need to be enabled";
          leaf vxlan-tunnel {
            description "Enable L2 protocol tunneling in vxlan-tunnel";
            type empty;
          }
        }
      }
    }
    container mac-rewrite {
      description "Mac rewrite functionality";
      list interface {
        key name;
        ordered-by user;
        leaf name {
          type union {
            type jt:interface-device;
            type string {
              pattern "<.*>|$.*";
            }
          }
        }
        leaf enable-all-ifl {
          description "Enable tunneling for all the IFLs under the interface";
          type empty;
        }
        container protocol {
          description "Protocols for which L2 protocol tunneling need to be enabled";
          container stp {
            presence "enable stp";
            description "Enable L2 protocol tunneling for STP";
          }
          container vtp {
            presence "enable vtp";
            description "Enable L2 protocol tunneling for VTP";
          }
          container cdp {
            presence "enable cdp";
            description "Enable L2 protocol tunneling for CDP";
          }
          container ieee8021x {
            presence "enable ieee8021x";
            description "Enable L2 protocol tunneling for 8021X";
          }
          container ieee8023ah {
            presence "enable ieee8023ah";
            description "Enable L2 protocol tunneling for 8023AH";
          }
          container elmi {
            presence "enable elmi";
            description "Enable L2 protocol tunneling for ELMI";
          }
          container lacp {
            presence "enable lacp";
            description "Enable L2 protocol tunneling for LACP";
          }
          container lldp {
            presence "enable lldp";
            description "Enable L2 protocol tunneling for LLDP";
          }
          container mmrp {
            presence "enable mmrp";
            description "Enable L2 protocol tunneling for MMRP";
          }
          container mvrp {
            presence "enable mvrp";
            description "Enable L2 protocol tunneling for MVRP";
          }
          container pvstp {
            presence "enable pvstp";
            description "Enable L2 protocol tunneling for PVSTP+";
          }
          container gvrp {
            presence "enable gvrp";
            description "Enable L2 protocol tunneling for GVRP";
          }
          container vstp {
            presence "enable vstp";
            description "Enable L2 protocol tunneling for VSTP";
          }
          container udld {
            presence "enable udld";
            description "Enable L2 protocol tunneling for UDLD";
          }
          container all {
            presence "enable all";
            description "Enable L2 protocol tunneling for all protocols";
          }
        }
      }
      container tunnel-destination-mac {
        presence "enable tunnel-destination-mac";
        description "Tunnel destination mac to be used in L2PT packets";
        leaf source {
          description "L2 multicast mac to be used as tunnel destination mac";
          type jt:mac-multicast;
        }
      }
    }
  }
  grouping juniper-protocols-ldp {
    container traffic-statistics {
      description "Collect statistics for LDP label-switched paths";
      container file {
        description "Statistics file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      leaf interval {
        description "Time to collect statistics (seconds)";
        type union {
          type string {
            pattern "<.*>|$.*";
          }
          type int32 {
            range "60 .. 65535";
          }
        }
      }
      leaf sensor-based-stats {
        description "Enable sensor based statistics collection";
        type empty;
      }
      leaf no-penultimate-hop {
        description "No penultimate hop statistics collection";
        type empty;
      }
    }
    leaf preference {
      description "Route preference";
      type union {
        type uint32;
        type string {
          pattern "<.*>|$.*";
        }
      }
    }
    container transport-address {
      description "Address used for TCP sessions";
      choice address-choice {
        case case_1 {
          leaf router-id {
            description "Use router ID for TCP connections";
            type empty;
          }
        }
        case case_2 {
          leaf interface {
            description "Use interface address for TCP connections";
            type empty;
          }
        }
        case case_3 {
          leaf address {
            description "Use specified address for TCP connections";
            type jt:ipaddr;
          }
        }
      }
    }
    list interface {
      key name;
      description "Enable LDP on this interface";
      leaf name {
        description "Interface name";
        type union {
          type jt:interface-name;
          type string {
            pattern "<.*>|$.*";
          }
        }
      }
      choice enable-disable {
        case case_1 {
          leaf disable {
            description "Disable LDP on this interface";
            type empty;
          }
        }
      }
      leaf hello-interval {
        description "Hello interval (seconds)";
        type union {
          type string {
            pattern "<.*>|$.*";
          }
          type uint32 {
            range "1 .. 65535";
          }
        }
      }
      leaf hold-time {
        description "Hello hold time (seconds)";
        type union {
          type string {
            pattern "<.*>|$.*";
          }
          type uint32 {
            range "1 .. 65535";
          }
        }
      }
      container link-protection {
        presence "enable link-protection";
        description "Enable link protection to protect interface for link faults only";
        choice enable-disable {
          case case_1 {
            leaf disable {
              description "Disable link-protection";
              type empty;
            }
          }
        }
        leaf dynamic-rsvp-lsp {
          description "Enable setup of dynamic rsvp lsp for link protection";
          type empty;
        }
      }
      container transport-address {
        description "Address used for TCP sessions";
        choice address-choice {
          case case_1 {
            leaf router-id {
              description "Use router ID for TCP connections";
              type empty;
            }
          }
          case case_2 {
            leaf interface {
              description "Use interface address for TCP connections";
              type empty;
            }
          }
          case case_3 {
            leaf address {
              description "Use specified address for TCP connections";
              type jt:ipaddr;
            }
          }
        }
      }
      choice allow-subnet-mismatch-choice {
        leaf allow-subnet-mismatch {
          description "Allow subnet mismatch for source address in hello packet";
          type empty;
        }
        leaf no-allow-subnet-mismatch {
          description "Don't allow subnet mismatch for source address in hello packet";
          type empty;
        }
      }
    }
  }
  grouping juniper-protocols-lmp {
    list te-link {
      key name;
      ordered-by user;
      description "Traffic engineering link";
      leaf name {
        description "Name of TE link";
        type string;
      }
      leaf local-address {
        description "Address of the local end of the link";
        type jt:ipaddr;
      }
      leaf remote-address {
        description "Address of the remote end of the link";
        type jt:ipaddr;
      }
      leaf remote-id {
        description "Link ID for the remote end of the link";
        type union {
          type string {
            pattern "<.*>|$.*";
          }
          type uint32 {
            range "1 .. 4294967295";
          }
        }
      }
      leaf te-metric {
        description "Traffic engineering metric of the link";
        type union {
          type string {
            pattern "<.*>|$.*";
          }
          type uint32 {
            range "1 .. 65535";
          }
        }
      }
      choice enable-disable {
        case case_1 {
          leaf disable {
            description "Disable TE link";
            type empty;
          }
        }
      }
      container ethernet-vlan {
        presence "enable ethernet-vlan";
        description "TE link used for setup of  L2 VLAN LSP";
        leaf-list vlan-id-range {
          description "VLAN id";
          type jt:vlan-range;
          max-elements 1;
        }
      }
      choice resource-option {
        case case_1 {
          list interface {
            key name;
            ordered-by user;
            description "Member interface of TE link";
            leaf name {
              description "Interface name";
              type union {
                type jt:interface-device;
                type string {
                  pattern "<.*>|$.*";
                }
              }
            }
            leaf local-address {
              description "Local address of the resource";
              type jt:ipaddr;
            }
            leaf remote-address {
              description "Remote address of the resource";
              type jt:ipaddr;
            }
            leaf remote-id {
              description "Interface ID for the remote end of the resource";
              type union {
                type string {
                  pattern "<.*>|$.*";
                }
                type uint32 {
                  range "1 .. 4294967295";
                }
              }
            }
            choice enable-disable {
              case case_1 {
                leaf disable {
                  description "Disable resource on this TE link";
                  type empty;
                }
              }
            }
          }
        }
        case case_2 {
          list label-switched-path {
            key name;
            ordered-by user;
            description "Member forwarding adjacency LSP of TE link";
            max-elements 1;
            leaf name {
              description "Name of label-switched path";
              type string;
            }
            leaf local-address {
              description "Local address of the resource";
              type jt:ipaddr;
            }
            leaf remote-address {
              description "Remote address of the resource";
              type jt:ipaddr;
            }
            leaf remote-id {
              description "Interface ID for the remote end of the resource";
              type union {
                type string {
                  pattern "<.*>|$.*";
                }
                type uint32 {
                  range "1 .. 4294967295";
                }
              }
            }
            choice enable-disable {
              case case_1 {
                leaf disable {
                  description "Disable resource on this TE link";
                  type empty;
                }
              }
            }
          }
        }
      }
    }
    list peer {
      key name;
      ordered-by user;
      description "Define a network or LMP peer";
      leaf name {
        description "Name of peer";
        type string;
      }
      leaf address {
        description "Address of peer";
        type jt:ipaddr;
      }
      container lmp-protocol {
        presence "enable lmp-protocol";
        description "LMP protocol attributes";
        leaf hello-interval {
          description "Interval between Hello messages";
          units milliseconds;
          type union {
            type string {
              pattern "<.*>|$.*";
            }
            type uint32 {
              range "150 .. 21845";
            }
          }
        }
        leaf hello-dead-interval {
          description "Delay for control channel shutdown when no Hello received";
          units milliseconds;
          type union {
            type string {
              pattern "<.*>|$.*";
            }
            type uint32 {
              range "500 .. 65535";
            }
          }
        }
        leaf retransmission-interval {
          description "Minimum time before retransmitting a message";
          units milliseconds;
          type union {
            type string {
              pattern "<.*>|$.*";
            }
            type uint32 {
              range "500 .. 300000";
            }
          }
        }
        leaf retry-limit {
          description "Number of times to retransmit a message";
          type union {
            type string {
              pattern "<.*>|$.*";
            }
            type uint32 {
              range "3 .. 1000";
            }
          }
        }
        leaf passive {
          description "Do not send Config messages to peer";
          type empty;
        }
      }
      leaf-list control-channel {
        ordered-by user;
        description "Control channel interfaces by priority";
        type union {
          type jt:interface-name;
          type string {
            pattern "<.*>|$.*";
          }
        }
      }
      list lmp-control-channel {
        key name;
        ordered-by user;
        description "Control channel IDs";
        uses lmp_control_channel_type;
      }
      leaf-list te-link {
        ordered-by user;
        description "List of TE links managed by this peer";
        type string;
      }
    }
    container traceoptions {
      description "LMP trace options";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum init {
              description "Trace initialization events";
            }
            enum show {
              description "Trace show command servicing";
            }
            enum route-socket {
              description "Trace route-socket events";
            }
            enum parse {
              description "Trace parser processing";
            }
            enum process {
              description "Trace general configuration processing";
            }
            enum server {
              description "Trace server processing";
            }
            enum routing {
              description "Trace routing protocols interworking";
            }
            enum packets {
              description "Trace packet processing";
            }
            enum hello-packets {
              description "Trace hello packet processing";
            }
            enum state {
              description "Trace state transitions";
            }
            enum nsr-synchronization {
              description "Trace mirror and nsr transitions";
            }
            enum all {
              description "Trace everything";
            }
          }
        }
        leaf send {
          description "Trace transmitted packets";
          status deprecated;
          type empty;
        }
        leaf receive {
          description "Trace received packets";
          status deprecated;
          type empty;
        }
        leaf detail {
          description "Trace detailed information";
          status deprecated;
          type empty;
        }
        leaf disable {
          description "Disable this trace flag";
          status deprecated;
          type empty;
        }
      }
    }
  }
  grouping juniper-protocols-mpls {
    description "Multiprotocol Label Switching options";
    leaf no-propagate-ttl {
      description "Disable TTL propagation from IP to MPLS (on push) and MPLS to IP (on pop)";
      type empty;
    }
    leaf ipv6-tunneling {
      description "Allow MPLS LSPs to be used for tunneling IPv6 traffic";
      type empty;
    }
    list interface {
      key name;
      ordered-by user;
      description "MPLS interface options";
      uses juniper-protocols-mpls-interface;
    }
  }
  grouping juniper-protocols-mpls-interface {
    leaf name {
      description "Interface name";
      type union {
        type jt:interface-name;
        type string {
          pattern "<.*>|$.*";
        }
      }
    }
    choice enable-disable {
      case case_1 {
        leaf disable {
          description "Disable MPLS on this interface";
          type empty;
        }
      }
    }
    leaf-list srlg {
      ordered-by user;
      description "SRLG Name";
      type string;
      max-elements 64;
    }
    leaf always-mark-connection-protection-tlv {
      description "Mark connection protection tlv on this interface";
      type empty;
    }
    leaf switch-away-lsps {
      description "Switch away protected LSPs to their bypass LSPs";
      type empty;
    }
    leaf-list admin-group {
      ordered-by user;
      description "Administrative groups";
      type string;
    }
    leaf-list admin-group-extended {
      ordered-by user;
      description "Extended administrative groups";
      type string;
    }
    container static {
      description "Static label-switch path related configurations";
      leaf protection-revert-time {
        description "FRR revert wait time, 0 means disable";
        units seconds;
        type union {
          type string {
            pattern "<.*>|$.*";
          }
          type uint32 {
            range "0 .. 65535";
          }
        }
      }
    }
  }
  grouping juniper-protocols-msdp {
    leaf data-encapsulation {
      description "Set encapsulation of data packets";
      type enumeration {
        enum disable {
          description "Disable data encapsulation";
        }
        enum enable {
          description "Enable data encapsulation";
        }
      }
    }
    container rib-group {
      description "Routing table group";
      uses rib_group_inet_type;
    }
    container active-source-limit {
      description "Limit the number of active sources accepted";
      leaf maximum {
        description "Maximum number of active sources accepted";
        default "25000";
        type union {
          type string {
            pattern "<.*>|$.*";
          }
          type uint32 {
            range "1 .. 1000000";
          }
        }
      }
      leaf threshold {
        description "RED threshold for active source acceptance";
        default "24000";
        type union {
          type string {
            pattern "<.*>|$.*";
          }
          type uint32 {
            range "1 .. 1000000";
          }
        }
      }
      leaf log-warning {
        description "Percentage of maximum at which to start generating warnings";
        default "100";
        type union {
          type string {
            pattern "<.*>|$.*";
          }
          type uint32 {
            range "1 .. 100";
          }
        }
      }
      leaf log-interval {
        description "Time between log messages";
        type union {
          type string {
            pattern "<.*>|$.*";
          }
          type uint32 {
            range "6 .. 32767";
          }
        }
      }
    }
    choice enable-disable {
      case case_1 {
        leaf disable {
          description "Disable MSDP";
          type empty;
        }
      }
    }
    leaf-list export {
      ordered-by user;
      description "Export policy";
      type jt:policy-algebra;
    }
    leaf-list import {
      ordered-by user;
      description "Import policy";
      type jt:policy-algebra;
    }
    leaf local-address {
      description "Local address";
      type jt:ipv4addr;
    }
    container traceoptions {
      description "Trace options for MSDP";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum packets {
              description "Trace all MSDP packets";
            }
            enum route {
              description "Trace routing information";
            }
            enum nsr-synchronization {
              description "Trace NSR synchronization events";
            }
            enum source-active {
              description "Trace source-active messages";
            }
            enum source-active-request {
              description "Trace source-active request messages";
            }
            enum source-active-response {
              description "Trace source-active response messages";
            }
            enum keepalive {
              description "Trace keepalive messages";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    list peer {
      key name;
      ordered-by user;
      description "Configure an MSDP peer";
      leaf name {
        description "Peer address";
        type jt:ipv4addr;
      }
      choice enable-disable {
        case case_1 {
          leaf disable {
            description "Disable MSDP";
            type empty;
          }
        }
      }
      leaf-list export {
        ordered-by user;
        description "Export policy";
        type jt:policy-algebra;
      }
      leaf-list import {
        ordered-by user;
        description "Import policy";
        type jt:policy-algebra;
      }
      leaf local-address {
        description "Local address";
        type jt:ipv4addr;
      }
      container traceoptions {
        description "Trace options for MSDP";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum packets {
                description "Trace all MSDP packets";
              }
              enum route {
                description "Trace routing information";
              }
              enum nsr-synchronization {
                description "Trace NSR synchronization events";
              }
              enum source-active {
                description "Trace source-active messages";
              }
              enum source-active-request {
                description "Trace source-active request messages";
              }
              enum source-active-response {
                description "Trace source-active response messages";
              }
              enum keepalive {
                description "Trace keepalive messages";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
      container active-source-limit {
        description "Limit the number of active sources accepted";
        leaf maximum {
          description "Maximum number of active sources accepted";
          default "25000";
          type union {
            type string {
              pattern "<.*>|$.*";
            }
            type uint32 {
              range "1 .. 1000000";
            }
          }
        }
        leaf threshold {
          description "RED threshold for active source acceptance";
          default "24000";
          type union {
            type string {
              pattern "<.*>|$.*";
            }
            type uint32 {
              range "1 .. 1000000";
            }
          }
        }
        leaf log-warning {
          description "Percentage of maximum at which to start generating warnings";
          default "100";
          type union {
            type string {
              pattern "<.*>|$.*";
            }
            type uint32 {
              range "1 .. 100";
            }
          }
        }
        leaf log-interval {
          description "Time between log messages";
          type union {
            type string {
              pattern "<.*>|$.*";
            }
            type uint32 {
              range "6 .. 32767";
            }
          }
        }
      }
      leaf keep-alive {
        description "Time limit for sending out periodic keep alive to peer";
        units seconds;
        type union {
          type string {
            pattern "<.*>|$.*";
          }
          type uint32 {
            range "10 .. 60";
          }
        }
      }
      leaf hold-time {
        description "Max time to terminating a peer for having not received any message from ";
        units seconds;
        type union {
          type string {
            pattern "<.*>|$.*";
          }
          type uint32 {
            range "15 .. 150";
          }
        }
      }
      leaf sa-hold-time {
        description "Max time for holding a sa message before timing out";
        units seconds;
        type union {
          type string {
            pattern "<.*>|$.*";
          }
          type uint32 {
            range "75 .. 300";
          }
        }
      }
      leaf default-peer {
        description "Default RPF peer";
        type empty;
      }
      leaf authentication-key {
        description "MD5 authentication key";
        type string {
          length "1 .. 126";
        }
      }
    }
    leaf keep-alive {
      description "Time limit for sending out periodic keep alive to peer";
      units seconds;
      type union {
        type string {
          pattern "<.*>|$.*";
        }
        type uint32 {
          range "10 .. 60";
        }
      }
    }
    leaf hold-time {
      description "Max time to terminating a peer for having not received any message from ";
      units seconds;
      type union {
        type string {
          pattern "<.*>|$.*";
        }
        type uint32 {
          range "15 .. 150";
        }
      }
    }
    leaf sa-hold-time {
      description "Max time for holding a sa message before timing out";
      units seconds;
      type union {
        type string {
          pattern "<.*>|$.*";
        }
        type uint32 {
          range "75 .. 300";
        }
      }
    }
    list source {
      key name;
      ordered-by user;
      description "Configure parameters for each source";
      leaf name {
        description "Source address or prefix";
        type jt:ipprefix;
      }
      container active-source-limit {
        description "Limit the number of active sources accepted";
        leaf maximum {
          description "Maximum number of active sources accepted";
          default "25000";
          type union {
            type string {
              pattern "<.*>|$.*";
            }
            type uint32 {
              range "1 .. 1000000";
            }
          }
        }
        leaf threshold {
          description "RED threshold for active source acceptance";
          default "24000";
          type union {
            type string {
              pattern "<.*>|$.*";
            }
            type uint32 {
              range "1 .. 1000000";
            }
          }
        }
        leaf log-warning {
          description "Percentage of maximum at which to start generating warnings";
          default "100";
          type union {
            type string {
              pattern "<.*>|$.*";
            }
            type uint32 {
              range "1 .. 100";
            }
          }
        }
        leaf log-interval {
          description "Time between log messages";
          type union {
            type string {
              pattern "<.*>|$.*";
            }
            type uint32 {
              range "6 .. 32767";
            }
          }
        }
      }
    }
    list group {
      key name;
      ordered-by user;
      description "Configure MSDP peer groups";
      leaf name {
        description "MSDP peer group name";
        type string;
      }
      leaf mode {
        description "MSDP group source-active flooding mode";
        default "standard";
        type enumeration {
          enum standard {
            description "Use standard MSDP source-active flooding rules";
          }
          enum mesh-group {
            description "Group peers are mesh group members";
          }
        }
      }
      choice enable-disable {
        case case_1 {
          leaf disable {
            description "Disable MSDP";
            type empty;
          }
        }
      }
      leaf-list export {
        ordered-by user;
        description "Export policy";
        type jt:policy-algebra;
      }
      leaf-list import {
        ordered-by user;
        description "Import policy";
        type jt:policy-algebra;
      }
      leaf local-address {
        description "Local address";
        type jt:ipv4addr;
      }
      container traceoptions {
        description "Trace options for MSDP";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum packets {
                description "Trace all MSDP packets";
              }
              enum route {
                description "Trace routing information";
              }
              enum nsr-synchronization {
                description "Trace NSR synchronization events";
              }
              enum source-active {
                description "Trace source-active messages";
              }
              enum source-active-request {
                description "Trace source-active request messages";
              }
              enum source-active-response {
                description "Trace source-active response messages";
              }
              enum keepalive {
                description "Trace keepalive messages";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
      list peer {
        key name;
        ordered-by user;
        description "Configure an MSDP peer";
        leaf name {
          description "Peer address";
          type jt:ipv4addr;
        }
        choice enable-disable {
          case case_1 {
            leaf disable {
              description "Disable MSDP";
              type empty;
            }
          }
        }
        leaf-list export {
          ordered-by user;
          description "Export policy";
          type jt:policy-algebra;
        }
        leaf-list import {
          ordered-by user;
          description "Import policy";
          type jt:policy-algebra;
        }
        leaf local-address {
          description "Local address";
          type jt:ipv4addr;
        }
        container traceoptions {
          description "Trace options for MSDP";
          container file {
            description "Trace file options";
            leaf filename {
              description "Name of file in which to write trace information";
              type string {
                length "1 .. 1024";
              }
            }
            leaf replace {
              description "Replace trace file rather than appending to it";
              status deprecated;
              type empty;
            }
            leaf size {
              description "Maximum trace file size";
              type string;
            }
            leaf files {
              description "Maximum number of trace files";
              default "10";
              type union {
                type string {
                  pattern "<.*>|$.*";
                }
                type uint32 {
                  range "2 .. 1000";
                }
              }
            }
            leaf no-stamp {
              description "Do not timestamp trace file";
              status deprecated;
              type empty;
            }
            choice world-readable-choice {
              leaf world-readable {
                description "Allow any user to read the log file";
                type empty;
              }
              leaf no-world-readable {
                description "Don't allow any user to read the log file";
                type empty;
              }
            }
          }
          list flag {
            key name;
            ordered-by user;
            description "Tracing parameters";
            leaf name {
              type enumeration {
                enum packets {
                  description "Trace all MSDP packets";
                }
                enum route {
                  description "Trace routing information";
                }
                enum nsr-synchronization {
                  description "Trace NSR synchronization events";
                }
                enum source-active {
                  description "Trace source-active messages";
                }
                enum source-active-request {
                  description "Trace source-active request messages";
                }
                enum source-active-response {
                  description "Trace source-active response messages";
                }
                enum keepalive {
                  description "Trace keepalive messages";
                }
                enum normal {
                  description "Trace normal events";
                }
                enum general {
                  description "Trace general events";
                }
                enum state {
                  description "Trace state transitions";
                }
                enum policy {
                  description "Trace policy processing";
                }
                enum task {
                  description "Trace routing protocol task processing";
                }
                enum timer {
                  description "Trace routing protocol timer processing";
                }
                enum all {
                  description "Trace everything";
                }
              }
            }
            leaf send {
              description "Trace transmitted packets";
              type empty;
            }
            leaf receive {
              description "Trace received packets";
              type empty;
            }
            leaf detail {
              description "Trace detailed information";
              type empty;
            }
            leaf disable {
              description "Disable this trace flag";
              type empty;
            }
          }
        }
        container active-source-limit {
          description "Limit the number of active sources accepted";
          leaf maximum {
            description "Maximum number of active sources accepted";
            default "25000";
            type union {
              type string {
                pattern "<.*>|$.*";
              }
              type uint32 {
                range "1 .. 1000000";
              }
            }
          }
          leaf threshold {
            description "RED threshold for active source acceptance";
            default "24000";
            type union {
              type string {
                pattern "<.*>|$.*";
              }
              type uint32 {
                range "1 .. 1000000";
              }
            }
          }
          leaf log-warning {
            description "Percentage of maximum at which to start generating warnings";
            default "100";
            type union {
              type string {
                pattern "<.*>|$.*";
              }
              type uint32 {
                range "1 .. 100";
              }
            }
          }
          leaf log-interval {
            description "Time between log messages";
            type union {
              type string {
                pattern "<.*>|$.*";
              }
              type uint32 {
                range "6 .. 32767";
              }
            }
          }
        }
        leaf keep-alive {
          description "Time limit for sending out periodic keep alive to peer";
          units seconds;
          type union {
            type string {
              pattern "<.*>|$.*";
            }
            type uint32 {
              range "10 .. 60";
            }
          }
        }
        leaf hold-time {
          description "Max time to terminating a peer for having not received any message from ";
          units seconds;
          type union {
            type string {
              pattern "<.*>|$.*";
            }
            type uint32 {
              range "15 .. 150";
            }
          }
        }
        leaf sa-hold-time {
          description "Max time for holding a sa message before timing out";
          units seconds;
          type union {
            type string {
              pattern "<.*>|$.*";
            }
            type uint32 {
              range "75 .. 300";
            }
          }
        }
        leaf default-peer {
          description "Default RPF peer";
          type empty;
        }
        leaf authentication-key {
          description "MD5 authentication key";
          type string {
            length "1 .. 126";
          }
        }
      }
    }
  }
  grouping juniper-protocols-mstp {
    choice enable-disable {
      case case_1 {
        leaf disable {
          description "Disable MSTP";
          type empty;
        }
      }
    }
    leaf bpdu-destination-mac-address {
      description "Destination MAC address in the spanning tree BPDUs";
      type enumeration {
        enum provider-bridge-group {
          description "802.1ad provider bridge group address";
        }
      }
    }
    leaf configuration-name {
      description "Configuration name (part of MST configuration identifier)";
      type string {
        length "1 .. 32";
      }
    }
    leaf revision-level {
      description "Revision level (part of MST configuration identifier)";
      type union {
        type uint16;
        type string {
          pattern "<.*>|$.*";
        }
      }
    }
    leaf max-hops {
      description "Maximum number of hops";
      type union {
        type string {
          pattern "<.*>|$.*";
        }
        type uint16 {
          range "1 .. 255";
        }
      }
    }
    leaf max-age {
      description "Maximum age of received protocol bpdu";
      units seconds;
      type union {
        type string {
          pattern "<.*>|$.*";
        }
        type uint16 {
          range "6 .. 40";
        }
      }
    }
    leaf hello-time {
      description "Time interval between configuration BPDUs";
      units seconds;
      type union {
        type string {
          pattern "<.*>|$.*";
        }
        type uint16 {
          range "1 .. 10";
        }
      }
    }
    leaf forward-delay {
      description "Time spent in listening or learning state";
      units seconds;
      type union {
        type string {
          pattern "<.*>|$.*";
        }
        type uint16 {
          range "4 .. 30";
        }
      }
    }
    leaf system-identifier {
      description "Sytem identifier to represent this node";
      type jt:mac-unicast;
    }
    container traceoptions {
      description "Tracing options for debugging protocol operation";
      uses stp-trace-options;
    }
    leaf bridge-priority {
      description "Priority of the bridge (in increments of 4k - 0,4k,8k,..60k)";
      type string;
    }
    leaf backup-bridge-priority {
      description "Priority of the bridge (in increments of 4k - 4k,8k,..60k)";
      type string;
    }
    leaf bpdu-block-on-edge {
      description "Block BPDU on all interfaces configured as edge (BPDU Protect)";
      type empty;
    }
    leaf vpls-flush-on-topology-change {
      description "Enable VPLS MAC flush on root protected CE interface receving topology change";
      type empty;
    }
    leaf priority-hold-time {
      description "Hold time before switching to primary priority when core domain becomes up";
      units seconds;
      type union {
        type string {
          pattern "<.*>|$.*";
        }
        type uint16 {
          range "1 .. 255";
        }
      }
    }
    list system-id {
      key name;
      ordered-by user;
      description "System ID to IP mapping";
      uses system-id-ip-map;
    }
    list interface {
      key name;
      description "Interface options";
      uses mstp-interface;
    }
    list msti {
      key name;
      description "Per-MSTI options";
      leaf name {
        type union {
          type string {
            pattern "<.*>|$.*";
          }
          type int32 {
            range "1 .. 64";
          }
        }
      }
      leaf bridge-priority {
        description "Priority of the bridge (in increments of 4k - 0,4k,8k,..60k)";
        type string;
      }
      leaf backup-bridge-priority {
        description "Priority of the bridge (in increments of 4k - 4k,8k,..60k)";
        type string;
      }
      leaf-list vlan {
        ordered-by user;
        description "VLAN ID or VLAN ID range [1..4094]";
        type string;
      }
      list interface {
        key name;
        description "Interface options";
        uses mstp-interface;
      }
    }
  }
  grouping juniper-protocols-mvpn {
    description "BGP-MVPN configuration";
    container traceoptions {
      description "Trace options for BGP-MVPN";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum error {
              description "Trace errors";
            }
            enum nlri {
              description "Trace MVPN advertisements";
            }
            enum topology {
              description "Trace MVPN topology changes";
            }
            enum tunnel {
              description "Trace provider tunnel events";
            }
            enum umh {
              description "Trace Upstream Multicast Hop (UMH) events";
            }
            enum intra-as-ad {
              description "Trace MVPN intra-AS auto discovery routes";
            }
            enum inter-as-ad {
              description "Trace MVPN inter-AS auto discovery routes";
            }
            enum spmsi-ad {
              description "Trace MVPN SPMSI auto discovery routes";
            }
            enum leaf-ad {
              description "Trace MVPN leaf auto discovery routes";
            }
            enum source-active {
              description "Trace MVPN source active routes";
            }
            enum cmcast-join {
              description "Trace MVPN c-multicast join routes";
            }
            enum mdt-safi-ad {
              description "Trace MVPN MDT SAFI auto discovery routes";
            }
            enum mvpn-limit {
              description "Trace MVPN spmsi and cmcast limit events";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    container autodiscovery-only {
      description "Use MVPN exclusively for PE router autodiscovery";
      status deprecated;
      container intra-as {
        description "Intra-AS autodiscovery options";
        leaf inclusive {
          description "Inclusive provider tunnel autodiscovery";
          type empty;
        }
      }
    }
    container family {
      description "BGP-MVPN address family";
      container any {
        presence "enable any";
        description "BGP-MVPN properties for all families";
        leaf disable {
          description "Disable all families";
          type empty;
        }
      }
      container inet {
        description "IPv4 BGP-MVPN properties";
        container autodiscovery-only {
          description "Use MVPN exclusively for PE router autodiscovery";
          container intra-as {
            description "Intra-AS autodiscovery options";
            leaf inclusive {
              description "Inclusive provider tunnel autodiscovery";
              type empty;
            }
          }
        }
        leaf disable {
          description "Disable family IPv4";
          type empty;
        }
      }
      container inet6 {
        presence "enable inet6";
        description "IPv6 BGP-MVPN properties";
        container autodiscovery-only {
          description "Use MVPN exclusively for PE router autodiscovery";
          container intra-as {
            description "Intra-AS autodiscovery options";
            leaf inclusive {
              description "Inclusive provider tunnel autodiscovery";
              type empty;
            }
          }
        }
        leaf disable {
          description "Disable family IPv6";
          type empty;
        }
      }
    }
    choice sender-receiver-site-choice {
      case case_1 {
        leaf receiver-site {
          description "MVPN instance has sites only with multicast receivers";
          type empty;
        }
      }
      case case_2 {
        leaf sender-site {
          description "MVPN instance has sites only with multicast sources";
          type empty;
        }
      }
    }
    leaf unicast-umh-election {
      description "Upstream Multicast Hop election based on unicast route preference";
      type empty;
    }
    container static-umh {
      description "Upstream Multicast Hop election based on static configuration";
      leaf primary {
        description "Primary Upstream Multicast Hop";
        type jt:ipv4addr;
      }
      leaf backup {
        description "Secondary Upstream Multicast Hop";
        type jt:ipv4addr;
      }
      choice source-tree_choice {
        case case_1 {
          leaf source-tree {
            description "Mandatory attribute - static-umh applies only to MVPN source-tree c-multicast joins";
            type empty;
          }
        }
      }
    }
    leaf cmcast-joins-limit-inet {
      description "Maximum number of cmcast entries for v4";
      type union {
        type string {
          pattern "<.*>|$.*";
        }
        type uint32 {
          range "0 .. 15000";
        }
      }
    }
    leaf cmcast-joins-limit-inet6 {
      description "Maximum number of cmcast entries for v6";
      type union {
        type string {
          pattern "<.*>|$.*";
        }
        type uint32 {
          range "0 .. 15000";
        }
      }
    }
    container mvpn-mode {
      description "MVPN mode of operation";
      choice mode {
        case case_1 {
          container rpt-spt {
            presence "enable rpt-spt";
            description "MVPN works in multicast RPT and SPT mode";
            leaf spt-switch-timer {
              description "Timeout before a PE router switches between RPT and SPT";
              units seconds;
              type union {
                type string {
                  pattern "<.*>|$.*";
                }
                type uint32 {
                  range "0 .. 60";
                }
              }
            }
          }
        }
        case case_2 {
          container spt-only {
            presence "enable spt-only";
            description "MVPN works in multicast SPT only mode (default mode)";
            container source-active-advertisement {
              description "Attributes associated with advertising Source-Active A-D routes";
              leaf dampen {
                description "Time to wait before re-advertising source-active route";
                units minutes;
                type union {
                  type string {
                    pattern "<.*>|$.*";
                  }
                  type uint32 {
                    range "1 .. 30";
                  }
                }
              }
              leaf min-rate {
                description "Minimum traffic rate required to advertise Source-Active route";
                units "bits per second";
                type string;
              }
            }
            leaf convert-sa-to-msdp {
              description "Turn on MVPN SA route to MSDP SA conversion";
              type empty;
            }
          }
        }
      }
    }
    container route-target {
      description "Configure route-targets for MVPN routes";
      container import-target {
        description "Target communities used when importing routes";
        container unicast {
          presence "enable unicast";
          description "Use the same target community as configured for unicast";
          choice receiver-sender-target-choice {
            case case_1 {
              leaf receiver {
                description "Target community used when importing receiver site routes";
                type empty;
              }
            }
            case case_2 {
              leaf sender {
                description "Target community used when importing sender site routes";
                type empty;
              }
            }
          }
        }
        container target {
          presence "enable target";
          description "Target community";
          leaf target-value {
            type string;
          }
          choice receiver-sender-target-choice {
            case case_1 {
              leaf receiver {
                description "Target community used when importing receiver site routes";
                type empty;
              }
            }
            case case_2 {
              leaf sender {
                description "Target community used when importing sender site routes";
                type empty;
              }
            }
          }
        }
      }
      container export-target {
        description "Target communities used when exporting routes";
        leaf unicast {
          description "Use the same target community as configured for unicast";
          type empty;
        }
        leaf target {
          description "Target community";
          type string;
        }
      }
    }
    container mvpn-join-load-balance {
      description "MVPN Join Load Balancing Algorithm";
      choice algorithm {
        case case_1 {
          container bytewise-xor-hash {
            presence "enable bytewise-xor-hash";
            description "Upstream selection using bytewise XOR hash";
          }
        }
      }
    }
    leaf install-discard {
      description "Install MVPN discard forwarding entries";
      type empty;
    }
    leaf sender-based-rpf {
      description "Forward multicast traffic only from a selected sender PE";
      type empty;
    }
    container hot-root-standby {
      description "MVPN live-live - hot root standby";
      choice tree {
        case case_1 {
          container source-tree {
            presence "enable source-tree";
            description "MVPN live-live - hot root standby for source tree";
          }
        }
      }
      container min-rate {
        description "Minimum traffic rate for the provider tunnel below which switchover is initiated (in bps)";
        leaf rate {
          description "Minium traffic rate for the provider tunnel below which switchover is initiated (in bps)";
          units "bits per second";
          type string;
        }
        leaf revert-delay {
          description "Time to delay updating of multicast routes to allow for multicast convergence";
          units seconds;
          type union {
            type string {
              pattern "<.*>|$.*";
            }
            type uint32 {
              range "0 .. 20";
            }
          }
        }
      }
    }
    leaf hierarchical-nexthop {
      description "Enable hierarchical nexthop usage";
      type empty;
    }
    leaf no-nexthop-sharing-for-selective-tunnel {
      description "Disable Tunnel nexthops from getting shared for selective tunnel";
      type empty;
    }
    container inter-region-template {
      description "MVPN inter-region tunnel mapping template";
      list template {
        key name;
        ordered-by user;
        description "Define a inter-region template";
        leaf name {
          description "MVPN Template Name";
          type string;
        }
        list region {
          key name;
          ordered-by user;
          description "BGP peer group names used as region";
          leaf name {
            description "Region name";
            type string;
          }
          choice tunnel-type {
            case case_1 {
              container rsvp-te {
                description "RSVP-TE point-to-multipoint LSP for flooding";
                choice static-or-dynamic {
                  case case_1 {
                    leaf static-lsp {
                      description "Name of point-to-multipoint LSP";
                      type string;
                    }
                  }
                  case case_2 {
                    container label-switched-path-template {
                      description "Template for dynamic point-to-multipoint LSP parameters";
                      choice dynamic-template {
                        case case_1 {
                          leaf template-name {
                            description "Name of point-to-multipoint LSP template";
                            type string;
                          }
                        }
                        case case_2 {
                          leaf default-template {
                            description "Use default parameters";
                            type empty;
                          }
                        }
                      }
                    }
                  }
                }
              }
            }
            case case_2 {
              container ldp-p2mp {
                presence "enable ldp-p2mp";
                description "LDP point-to-multipoint LSP for flooding";
              }
            }
            case case_3 {
              container ingress-replication {
                description "Ingress replication tunnel";
                leaf create-new-ucast-tunnel {
                  description "Create new unicast tunnel for ingress replication";
                  type empty;
                }
                container label-switched-path {
                  presence "enable label-switched-path";
                  description "Point-to-point LSP unicast tunnel";
                  container label-switched-path-template {
                    description "Template for dynamic point-to-point LSP parameters";
                    choice dynamic-template {
                      case case_1 {
                        leaf template-name {
                          description "Name of point-to-point LSP template";
                          type string;
                        }
                      }
                      case case_2 {
                        leaf default-template {
                          description "Use default parameters";
                          type empty;
                        }
                      }
                    }
                  }
                }
              }
            }
            case case_4 {
              leaf incoming {
                description "Same as incoming provider tunnel";
                type empty;
              }
            }
          }
        }
        container all-regions {
          description "Used for all regions not specified";
          choice tunnel-type {
            case case_1 {
              container rsvp-te {
                description "RSVP-TE point-to-multipoint LSP for flooding";
                choice static-or-dynamic {
                  case case_1 {
                    leaf static-lsp {
                      description "Name of point-to-multipoint LSP";
                      type string;
                    }
                  }
                  case case_2 {
                    container label-switched-path-template {
                      description "Template for dynamic point-to-multipoint LSP parameters";
                      choice dynamic-template {
                        case case_1 {
                          leaf template-name {
                            description "Name of point-to-multipoint LSP template";
                            type string;
                          }
                        }
                        case case_2 {
                          leaf default-template {
                            description "Use default parameters";
                            type empty;
                          }
                        }
                      }
                    }
                  }
                }
              }
            }
            case case_2 {
              container ldp-p2mp {
                presence "enable ldp-p2mp";
                description "LDP point-to-multipoint LSP for flooding";
              }
            }
            case case_3 {
              container ingress-replication {
                description "Ingress replication tunnel";
                leaf create-new-ucast-tunnel {
                  description "Create new unicast tunnel for ingress replication";
                  type empty;
                }
                container label-switched-path {
                  presence "enable label-switched-path";
                  description "Point-to-point LSP unicast tunnel";
                  container label-switched-path-template {
                    description "Template for dynamic point-to-point LSP parameters";
                    choice dynamic-template {
                      case case_1 {
                        leaf template-name {
                          description "Name of point-to-point LSP template";
                          type string;
                        }
                      }
                      case case_2 {
                        leaf default-template {
                          description "Use default parameters";
                          type empty;
                        }
                      }
                    }
                  }
                }
              }
            }
            case case_4 {
              leaf incoming {
                description "Same as incoming provider tunnel";
                type empty;
              }
            }
          }
        }
      }
    }
    leaf source-redundancy {
      description "Assume all the sources for a particular group is sending same data";
      type empty;
    }
    container umh-selection-additional-input {
      description "Additional parameters to consider during UMH";
      leaf source-active-preference {
        description "Use the preference set in the source active route";
        type empty;
      }
      leaf tunnel-status {
        description "Use the RSVP tunnel status";
        type empty;
      }
    }
  }
  grouping juniper-protocols-mvrp {
    description "MVRP Configuration";
    container traceoptions {
      description "Tracing options for MVRP";
      uses mrp-trace-options;
    }
    leaf join-timer {
      description "Join timer interval";
      default "200";
      units milliseconds;
      type union {
        type string {
          pattern "<.*>|$.*";
        }
        type uint16 {
          range "100 .. 500";
        }
      }
    }
    leaf leave-timer {
      description "Leave timer interval";
      default "800";
      units milliseconds;
      type union {
        type string {
          pattern "<.*>|$.*";
        }
        type uint16 {
          range "300 .. 1000";
        }
      }
    }
    leaf leaveall-timer {
      description "Leaveall timer interval";
      default "10";
      units seconds;
      type union {
        type string {
          pattern "<.*>|$.*";
        }
        type uint16 {
          range "10 .. 60";
        }
      }
    }
    leaf no-dynamic-vlan {
      description "Disable dynamic VLAN creation";
      type empty;
    }
    leaf no-attribute-length-in-pdu {
      description "No attribute length while sending pdu ";
      type empty;
    }
    leaf bpdu-destination-mac-address {
      description "Destination MAC address in the MVRP BPDUs";
      type enumeration {
        enum provider-bridge-group {
          description "802.1ad provider bridge group address";
        }
      }
    }
    list interface {
      key name;
      ordered-by user;
      description "Configure interface options";
      leaf name {
        description "Interface name";
        type union {
          type jt:interface-device;
          type string {
            pattern "<.*>|$.*";
          }
        }
      }
      leaf join-timer {
        description "Join timer interval";
        units milliseconds;
        type union {
          type string {
            pattern "<.*>|$.*";
          }
          type uint16 {
            range "100 .. 500";
          }
        }
      }
      leaf leave-timer {
        description "Leave timer interval";
        units milliseconds;
        type union {
          type string {
            pattern "<.*>|$.*";
          }
          type uint16 {
            range "300 .. 1000";
          }
        }
      }
      leaf leaveall-timer {
        description "Leaveall timer interval";
        units seconds;
        type union {
          type string {
            pattern "<.*>|$.*";
          }
          type uint16 {
            range "10 .. 60";
          }
        }
      }
      leaf point-to-point {
        description "Port is point to point";
        type empty;
      }
      leaf registration {
        description "Registration mode";
        default "normal";
        type enumeration {
          enum normal {
            description "Normal registration mode";
          }
          enum restricted {
            description "Restricted registration mode";
          }
          enum forbidden {
            description "Forbidden registration mode";
          }
        }
      }
    }
  }
  grouping juniper-protocols-openflow {
    list switch {
      key name;
      ordered-by user;
      description "OpenFlow switch";
      max-elements 1;
      leaf name {
        description "Switch name";
        type string {
          length "1 .. 64";
        }
      }
      container default-action {
        description "Action for packets that not have a matching flow entry";
        choice drop-pktin {
          case case_1 {
            leaf drop {
              description "Drop all packets that do not have a matching flow entry";
              type empty;
            }
          }
          case case_2 {
            leaf packet-in {
              description "Send packets to client if no matching flow entry";
              type empty;
            }
          }
        }
      }
      list interfaces {
        key name;
        ordered-by user;
        description "Interfaces configured for use with Openflow";
        leaf name {
          description "Interface name";
          type union {
            type jt:interface-name;
            type string {
              pattern "<.*>|$.*";
            }
          }
        }
        leaf port-id {
          description "Openflow port ID";
          type union {
            type string {
              pattern "<.*>|$.*";
            }
            type int32 {
              range "1 .. 32640";
            }
          }
        }
      }
      leaf purge-flow-timer {
        description "Purge timer value for invalid flows";
        units seconds;
        type union {
          type string {
            pattern "<.*>|$.*";
          }
          type uint32 {
            range "0 .. 300";
          }
        }
      }
      container controller {
        description "OpenFlow controller's IP address, port and protocol";
        container protocol {
          description "Protocol type for controller connection";
          container tcp {
            description "Set protocol type to 'TCP' (default)";
            leaf port {
              description "Controller's port number (default 6633)";
              type union {
                type string {
                  pattern "<.*>|$.*";
                }
                type int32 {
                  range "1024 .. 65535";
                }
              }
            }
          }
        }
        leaf role {
          description "Controller role";
          type enumeration {
            enum equal {
              description "Set role to 'equal'";
            }
          }
        }
        leaf address {
          description "Controller's IPv4 address";
          type jt:ipaddr;
        }
        leaf id {
          description "Controller id";
          type union {
            type uint32;
            type string {
              pattern "<.*>|$.*";
            }
          }
        }
      }
    }
    container traceoptions {
      description "OpenFlow switch daemon trace options";
      leaf no-remote-trace {
        description "Disable remote tracing";
        type empty;
      }
      container file {
        description "Trace file information";
        leaf filename {
          description "Name of file in which to write trace information";
          type string {
            length "1 .. 1024";
          }
        }
        leaf size {
          description "Maximum trace file size";
          type string;
        }
        leaf files {
          description "Maximum number of trace files";
          default "3";
          type union {
            type string {
              pattern "<.*>|$.*";
            }
            type uint32 {
              range "2 .. 1000";
            }
          }
        }
        choice world-readable-choice {
          leaf world-readable {
            description "Allow any user to read the log file";
            type empty;
          }
          leaf no-world-readable {
            description "Don't allow any user to read the log file";
            type empty;
          }
        }
        leaf match {
          description "Regular expression for lines to be logged";
          type jt:regular-expression;
        }
      }
      list flag {
        key name;
        ordered-by user;
        description "Tracing flag parameters";
        leaf name {
          type enumeration {
            enum switch {
              description "Trace openflow switch events";
            }
            enum configuration {
              description "Trace openflow configuration events";
            }
            enum flow {
              description "Trace openflow flow events";
            }
            enum filter {
              description "Trace openflow filter events";
            }
            enum function {
              description "Trace openflow function entry/exit events";
            }
            enum packet-io {
              description "Trace openflow packet in/out events";
            }
            enum statistics {
              description "Trace openflow statistics events";
            }
            enum interface {
              description "Trace openflow interface events";
            }
            enum packets {
              description "Trace openflow packets";
            }
            enum barrier {
              description "Trace openflow barrier events";
            }
            enum nh {
              description "Trace openflow next-hop events";
            }
            enum group {
              description "Trace openflow group events";
            }
            enum all {
              description "Trace everything";
            }
          }
        }
      }
    }
  }
  grouping juniper-protocols-ospf {
    list topology {
      key name;
      ordered-by user;
      description "Topology parameters";
      leaf name {
        description "Topology name";
        type string;
      }
      leaf disable {
        description "Disable this topology";
        type empty;
      }
      leaf topology-id {
        description "Topology identifier";
        type union {
          type string {
            pattern "<.*>|$.*";
          }
          type uint8 {
            range "32 .. 127";
          }
        }
      }
      leaf overload {
        description "Set the overload mode (repel transit traffic)";
        type empty;
      }
      leaf rib-group {
        description "Routing table group for importing routes";
        type string;
      }
      container spf-options {
        description "Configure options for SPF";
        container microloop-avoidance {
          description "Configure microloop avoidance mechanism";
          container post-convergence-path {
            presence "enable post-convergence-path";
            description "Temporarily install post-convergence path for routes potentially affected by microloops";
            leaf delay {
              description "Time after which temporary post-convergence paths are removed";
              units milliseconds;
              type union {
                type string {
                  pattern "<.*>|$.*";
                }
                type uint32 {
                  range "500 .. 60000";
                }
              }
            }
            leaf maximum-labels {
              description "Maximum number of labels installed for post-convergence paths";
              type union {
                type string {
                  pattern "<.*>|$.*";
                }
                type uint32 {
                  range "2 .. 8";
                }
              }
            }
          }
        }
        leaf delay {
          description "Time to wait before running an SPF";
          units milliseconds;
          type union {
            type string {
              pattern "<.*>|$.*";
            }
            type uint32 {
              range "50 .. 8000";
            }
          }
        }
        leaf holddown {
          description "Time to hold down before running an SPF";
          units milliseconds;
          type union {
            type string {
              pattern "<.*>|$.*";
            }
            type uint32 {
              range "2000 .. 20000";
            }
          }
        }
        leaf rapid-runs {
          description "Number of maximum rapid SPF runs before holddown";
          type union {
            type string {
              pattern "<.*>|$.*";
            }
            type uint32 {
              range "1 .. 10";
            }
          }
        }
        leaf no-ignore-our-externals {
          description "Do not ignore self-generated external and NSSA LSAs";
          type empty;
        }
      }
      container backup-spf-options {
        description "Configure options for backup SPF";
        container remote-backup-calculation {
          presence "enable remote-backup-calculation";
          description "Calculate Remote LFA backup nexthops";
          container pq-nodes-nearest-to-source {
            description "PQ nodes selection based upon nearest to source";
            leaf percent {
              description "Selection percentage for nearest to source";
              type union {
                type string {
                  pattern "<.*>|$.*";
                }
                type uint32 {
                  range "10 .. 100";
                }
              }
            }
          }
        }
        container use-post-convergence-lfa {
          presence "enable use-post-convergence-lfa";
          description "Calculate post-convergence backup paths";
          leaf maximum-labels {
            description "Maximum number of labels installed for post-convergence paths";
            type union {
              type string {
                pattern "<.*>|$.*";
              }
              type uint32 {
                range "2 .. 8";
              }
            }
          }
          leaf maximum-backup-paths {
            description "Maximum number of equal-cost post-convergence paths installed";
            type union {
              type string {
                pattern "<.*>|$.*";
              }
              type uint32 {
                range "1 .. 8";
              }
            }
          }
        }
        leaf use-source-packet-routing {
          description "Use spring backup paths for inet.0 routes";
          type empty;
        }
        leaf disable {
          description "Do not run backup SPF";
          type empty;
        }
        leaf no-install {
          description "Do not install backup nexthops into the RIB";
          type empty;
        }
        leaf downstream-paths-only {
          description "Use only downstream backup paths";
          type empty;
        }
        container per-prefix-calculation {
          description "Calculate backup nexthops for non-best prefix originators";
          leaf stubs {
            description "Per prefix calculation for stubs only";
            type empty;
          }
          leaf summary {
            description "Per prefix calculation for summary originators only";
            type empty;
          }
          leaf externals {
            description "Per prefix calculation for externals";
            type empty;
          }
          leaf all {
            description "Per prefix calculation for all";
            type empty;
          }
        }
        leaf node-link-degradation {
          description "Degrade to link protection when nodelink protection not available";
          type empty;
        }
      }
      leaf prefix-export-limit {
        description "Maximum number of prefixes that can be exported";
        type union {
          type string {
            pattern "<.*>|$.*";
          }
          type uint32 {
            range "0 .. 4294967295";
          }
        }
      }
    }
    container spf-options {
      description "Configure options for SPF";
      container microloop-avoidance {
        description "Configure microloop avoidance mechanism";
        container post-convergence-path {
          presence "enable post-convergence-path";
          description "Temporarily install post-convergence path for routes potentially affected by microloops";
          leaf delay {
            description "Time after which temporary post-convergence paths are removed";
            units milliseconds;
            type union {
              type string {
                pattern "<.*>|$.*";
              }
              type uint32 {
                range "500 .. 60000";
              }
            }
          }
          leaf maximum-labels {
            description "Maximum number of labels installed for post-convergence paths";
            type union {
              type string {
                pattern "<.*>|$.*";
              }
              type uint32 {
                range "2 .. 8";
              }
            }
          }
        }
      }
      leaf delay {
        description "Time to wait before running an SPF";
        units milliseconds;
        type union {
          type string {
            pattern "<.*>|$.*";
          }
          type uint32 {
            range "50 .. 8000";
          }
        }
      }
      leaf holddown {
        description "Time to hold down before running an SPF";
        units milliseconds;
        type union {
          type string {
            pattern "<.*>|$.*";
          }
          type uint32 {
            range "2000 .. 20000";
          }
        }
      }
      leaf rapid-runs {
        description "Number of maximum rapid SPF runs before holddown";
        type union {
          type string {
            pattern "<.*>|$.*";
          }
          type uint32 {
            range "1 .. 10";
          }
        }
      }
      leaf no-ignore-our-externals {
        description "Do not ignore self-generated external and NSSA LSAs";
        type empty;
      }
    }
    container backup-spf-options {
      description "Configure options for backup SPF";
      container remote-backup-calculation {
        presence "enable remote-backup-calculation";
        description "Calculate Remote LFA backup nexthops";
        container pq-nodes-nearest-to-source {
          description "PQ nodes selection based upon nearest to source";
          leaf percent {
            description "Selection percentage for nearest to source";
            type union {
              type string {
                pattern "<.*>|$.*";
              }
              type uint32 {
                range "10 .. 100";
              }
            }
          }
        }
      }
      container use-post-convergence-lfa {
        presence "enable use-post-convergence-lfa";
        description "Calculate post-convergence backup paths";
        leaf maximum-labels {
          description "Maximum number of labels installed for post-convergence paths";
          type union {
            type string {
              pattern "<.*>|$.*";
            }
            type uint32 {
              range "2 .. 8";
            }
          }
        }
        leaf maximum-backup-paths {
          description "Maximum number of equal-cost post-convergence paths installed";
          type union {
            type string {
              pattern "<.*>|$.*";
            }
            type uint32 {
              range "1 .. 8";
            }
          }
        }
      }
      leaf use-source-packet-routing {
        description "Use spring backup paths for inet.0 routes";
        type empty;
      }
      leaf disable {
        description "Do not run backup SPF";
        type empty;
      }
      leaf no-install {
        description "Do not install backup nexthops into the RIB";
        type empty;
      }
      leaf downstream-paths-only {
        description "Use only downstream backup paths";
        type empty;
      }
      container per-prefix-calculation {
        description "Calculate backup nexthops for non-best prefix originators";
        leaf stubs {
          description "Per prefix calculation for stubs only";
          type empty;
        }
        leaf summary {
          description "Per prefix calculation for summary originators only";
          type empty;
        }
        leaf externals {
          description "Per prefix calculation for externals";
          type empty;
        }
        leaf all {
          description "Per prefix calculation for all";
          type empty;
        }
      }
      leaf node-link-degradation {
        description "Degrade to link protection when nodelink protection not available";
        type empty;
      }
    }
    container traffic-engineering {
      presence "enable traffic-engineering";
      description "Configure traffic engineering attributes";
      leaf no-topology {
        description "Disable dissemination of TE link-state topology information";
        type empty;
      }
      leaf multicast-rpf-routes {
        description "Install routes for multicast RPF checks into inet.2";
        type empty;
      }
      leaf l3-unicast-topology {
        description "Download IGP topology into TED";
        type empty;
      }
      container ignore-lsp-metrics {
        presence "enable ignore-lsp-metrics";
        description "Ignore label-switched path metrics when doing shortcuts";
        leaf unconfigured-only {
          description "Ignore lsp metrics for unconfigured only";
          type empty;
        }
      }
      container shortcuts {
        presence "enable shortcuts";
        description "Use label-switched paths as next hops, if possible";
        leaf ignore-lsp-metrics {
          description "Ignore label-switched path metrics when doing shortcuts";
          status deprecated;
          type empty;
        }
        leaf lsp-metric-into-summary {
          description "Advertise LSP metric into summary LSAs";
          type empty;
        }
        list family {
          key name;
          ordered-by user;
          description "Address family specific traffic-engineering attributes";
          leaf name {
            type enumeration {
              enum inet {
                description "IPv4 family";
              }
              enum inet-mpls {
                description "IPv4-MPLS family";
              }
            }
          }
        }
      }
      leaf advertise-unnumbered-interfaces {
        description "Advertise unnumbered interfaces";
        type empty;
      }
      leaf credibility-protocol-preference {
        description "TED protocol credibility follows protocol preference";
        type empty;
      }
      container advertisement {
        description "Advertise TE parameters even if RSVP is not turned on";
        leaf always {
          description "Advertise TE parameters in TE LSAs";
          type empty;
        }
      }
      container tunnel-source-protocol {
        description "Protocols from which to pick label-switched paths";
        container rsvp {
          presence "enable rsvp";
          description "Pick label-switched paths from rsvp";
          leaf preference {
            description "Preference for label-switched paths from this protocol";
            type union {
              type string {
                pattern "<.*>|$.*";
              }
              type uint32 {
                range "1 .. 255";
              }
            }
          }
        }
        container spring-te {
          presence "enable spring-te";
          description "Pick label-switched paths from spring-te";
          leaf preference {
            description "Preference for label-switched paths from this protocol";
            type union {
              type string {
                pattern "<.*>|$.*";
              }
              type uint32 {
                range "1 .. 255";
              }
            }
          }
        }
      }
    }
    container source-packet-routing {
      presence "enable source-packet-routing";
      description "Enable source packet routing (SPRING)";
      container adjacency-segment {
        description "Attributes for adjacency segments in spring";
        leaf hold-time {
          description "Retain time of Adjacency segment after isolating from an interface";
          type union {
            type string {
              pattern "<.*>|$.*";
            }
            type uint32 {
              range "180000 .. 900000";
            }
          }
        }
      }
      leaf-list prefix-segment {
        ordered-by user;
        description "Prefix Segment policy";
        type jt:policy-algebra;
      }
      leaf explicit-null {
        description "Set E and P bits in all Prefix SID advertisements";
        type empty;
      }
      container node-segment {
        presence "enable node-segment";
        description "Enable support for Node segments in SPRING";
        leaf ipv4-index {
          description "Set ipv4 node segment index";
          type union {
            type string {
              pattern "<.*>|$.*";
            }
            type uint32 {
              range "0 .. 199999";
            }
          }
        }
        leaf index-range {
          description "Set range of node segment indices allowed";
          type union {
            type string {
              pattern "<.*>|$.*";
            }
            type uint32 {
              range "32 .. 16385";
            }
          }
        }
      }
      container srgb {
        description "Set the SRGB global block in SPRING";
        leaf start-label {
          description "Start range for SRGB label block";
          type union {
            type string {
              pattern "<.*>|$.*";
            }
            type uint32;
          }
        }
        leaf index-range {
          description "Index to the SRGB start label block";
          type union {
            type string {
              pattern "<.*>|$.*";
            }
            type uint32;
          }
        }
      }
      leaf mapping-server {
        description "Mapping server name";
        type string;
      }
      leaf install-prefix-sid-for-best-route {
        description "For best route install a exact prefix sid route";
        type empty;
      }
      leaf ldp-stitching {
        description "Enable SR to LDP stitching";
        type empty;
      }
      leaf-list flex-algorithm {
        description "Flex-algorithms we would like to participate in";
        type union {
          type string {
            pattern "<.*>|$.*";
          }
          type uint32 {
            range "128 .. 255";
          }
        }
        max-elements 16;
      }
      leaf strict-asla-based-flex-algorithm {
        description "Flex-Algorithm to ignore links not having ASLA sub-TLVs";
        type empty;
      }
      container sensor-based-stats {
        description "Configure sensor based stats in SPRING";
        container per-interface-per-member-link {
          description "Configure sensor based stats per nexthop";
          leaf ingress {
            description "Enable sensor based stats on ingress interface";
            type empty;
          }
          leaf egress {
            description "Enable sensor based stats on egress interface";
            type empty;
          }
        }
        container per-sid {
          description "Configure sensor based stats per spring route";
          leaf ingress {
            description "Enable sensor based stats for per-sid ingress accounting";
            type empty;
          }
          leaf egress {
            description "Enable sensor based stats for IP-MPLS egress accounting";
            type empty;
          }
        }
      }
    }
    list area {
      key name;
      ordered-by user;
      description "Configure an OSPF area";
      leaf name {
        description "Area ID";
        type jt:areaid;
      }
      choice stub-option {
        case case_1 {
          container stub {
            presence "enable stub";
            description "Configure a stub area";
            leaf default-metric {
              description "Metric for the default route in this stub area";
              type union {
                type string {
                  pattern "<.*>|$.*";
                }
                type uint32 {
                  range "1 .. 16777215";
                }
              }
            }
            choice summaries-choice {
              leaf summaries {
                description "Flood summary LSAs into this stub area";
                type empty;
              }
              leaf no-summaries {
                description "Don't flood summary LSAs into this stub area";
                type empty;
              }
            }
          }
        }
        case case_2 {
          container nssa {
            presence "enable nssa";
            description "Configure a not-so-stubby area";
            container default-lsa {
              presence "enable default-lsa";
              description "Configure a default LSA";
              leaf default-metric {
                description "Metric for the default route in this area";
                type union {
                  type string {
                    pattern "<.*>|$.*";
                  }
                  type uint32 {
                    range "1 .. 16777215";
                  }
                }
              }
              leaf metric-type {
                description "External metric type for the default type 7 LSA";
                type union {
                  type string {
                    pattern "<.*>|$.*";
                  }
                  type uint32 {
                    range "1 .. 2";
                  }
                }
              }
              leaf type-7 {
                description "Flood type 7 default LSA if no-summaries is configured";
                type empty;
              }
            }
            leaf default-metric {
              description "Metric for the default route in this area";
              status deprecated;
              type union {
                type string {
                  pattern "<.*>|$.*";
                }
                type uint32 {
                  range "1 .. 16777215";
                }
              }
            }
            leaf metric-type {
              description "External metric type for the default type 7 LSA";
              status deprecated;
              type union {
                type string {
                  pattern "<.*>|$.*";
                }
                type uint32 {
                  range "1 .. 2";
                }
              }
            }
            choice summaries-choice {
              leaf summaries {
                description "Flood summary LSAs into this NSSA area";
                type empty;
              }
              leaf no-summaries {
                description "Don't flood summary LSAs into this NSSA area";
                type empty;
              }
            }
            list area-range {
              key name;
              ordered-by user;
              description "Configure NSSA area ranges";
              leaf name {
                description "Range to summarize NSSA routes in this area";
                type jt:ipprefix;
              }
              leaf restrict {
                description "Restrict advertisement of this area range";
                type empty;
              }
              leaf exact {
                description "Enforce exact match for advertisement of this area range";
                type empty;
              }
              container override-metric {
                presence "enable override-metric";
                description "Override the dynamic metric for this area-range";
                leaf metric {
                  description "Metric value";
                  type union {
                    type string {
                      pattern "<.*>|$.*";
                    }
                    type uint32 {
                      range "1 .. 16777215";
                    }
                  }
                }
                leaf metric-type {
                  description "Set the metric type for the override metric";
                  default "1";
                  type union {
                    type string {
                      pattern "<.*>|$.*";
                    }
                    type uint32 {
                      range "1 .. 2";
                    }
                  }
                }
              }
            }
          }
        }
      }
      list area-range {
        key name;
        ordered-by user;
        description "Configure area ranges";
        leaf name {
          description "Range to summarize routes in this area";
          type jt:ipprefix;
        }
        leaf restrict {
          description "Restrict advertisement of this area range";
          type empty;
        }
        leaf exact {
          description "Enforce exact match for advertisement of this area range";
          type empty;
        }
        leaf override-metric {
          description "Override the dynamic metric for this area-range";
          type union {
            type string {
              pattern "<.*>|$.*";
            }
            type uint32 {
              range "1 .. 16777215";
            }
          }
        }
      }
      leaf-list network-summary-export {
        ordered-by user;
        description "Export policy for Type 3 Summary LSAs";
        type jt:policy-algebra;
      }
      leaf-list network-summary-import {
        ordered-by user;
        description "Import policy for Type 3 Summary LSAs";
        type jt:policy-algebra;
      }
      leaf-list inter-area-prefix-export {
        ordered-by user;
        description "Export policy for Inter Area Prefix LSAs";
        type jt:policy-algebra;
      }
      leaf-list inter-area-prefix-import {
        ordered-by user;
        description "Import policy for Inter Area Prefix LSAs";
        type jt:policy-algebra;
      }
      leaf authentication-type {
        description "Authentication type";
        status deprecated;
        type enumeration {
          enum none {
            description "No authentication";
            status deprecated;
          }
          enum simple {
            description "Simple password authentication";
            status deprecated;
          }
          enum md5 {
            description "MD5 authentication";
            status deprecated;
          }
        }
      }
      list virtual-link {
        key "neighbor-id transit-area";
        ordered-by user;
        description "Configure virtual links";
        leaf neighbor-id {
          description "Router ID of a virtual neighbor";
          type jt:ipv4addr;
        }
        leaf transit-area {
          description "Transit area in common with virtual neighbor";
          type jt:areaid;
        }
        choice enable-disable {
          case case_1 {
            leaf disable {
              description "Disable this virtual link";
              type empty;
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
        leaf ipsec-sa {
          description "IPSec security association name";
          type string {
            length "1 .. 32";
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
      list sham-link-remote {
        key name;
        ordered-by user;
        description "Configure parameters for remote sham link endpoint";
        leaf name {
          description "Remote sham link endpoint address";
          type jt:ipaddr;
        }
        leaf metric {
          description "Sham link metric";
          type union {
            type string {
              pattern "<.*>|$.*";
            }
            type uint16 {
              range "1 .. 65535";
            }
          }
        }
        leaf ipsec-sa {
          description "IPSec security association name";
          type string {
            length "1 .. 32";
          }
        }
        leaf demand-circuit {
          description "Interface functions as a demand circuit";
          type empty;
        }
        leaf flood-reduction {
          description "Enable flood reduction";
          type empty;
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
      list interface {
        key name;
        ordered-by user;
        description "Include an interface in this area";
        leaf name {
          description "Interface name";
          type union {
            type jt:ipv4addr-or-interface;
            type string {
              pattern "<.*>|$.*";
            }
          }
        }
        choice enable-disable {
          case case_1 {
            leaf disable {
              description "Disable OSPF on this interface";
              type empty;
            }
          }
        }
        leaf interface-type {
          description "Type of interface";
          type enumeration {
            enum nbma {
              description "Nonbroadcast multiaccess";
            }
            enum p2mp {
              description "Point-to-multipoint NBMA";
            }
            enum p2p {
              description "Point-to-point";
            }
            enum p2mp-over-lan {
              description "Point-to-multipoint over LAN mode";
            }
          }
        }
        choice protection-type {
          case case_1 {
            leaf link-protection {
              description "Protect interface from link faults only";
              type empty;
            }
          }
          case case_2 {
            leaf node-link-protection {
              description "Protect interface from both link and node faults";
              type empty;
            }
          }
        }
        leaf no-eligible-backup {
          description "Not eligible to backup traffic from protected interfaces";
          type empty;
        }
        leaf no-eligible-remote-backup {
          description "Not eligible for Remote-LFA backup traffic from protected interfaces";
          type empty;
        }
        container passive {
          presence "enable passive";
          description "Do not run OSPF, but advertise it";
          container traffic-engineering {
            description "Advertise TE link information";
            leaf remote-node-id {
              description "Remote address of the link";
              type jt:ipaddr;
            }
            leaf remote-node-router-id {
              description "TE Router-ID of the remote node";
              type jt:ipv4addr;
            }
          }
        }
        leaf secondary {
          description "Treat interface as secondary";
          type empty;
        }
        leaf own-router-lsa {
          description "Generate a separate router LSA for this interface";
          type empty;
        }
        container bandwidth-based-metrics {
          description "Configure bandwidth based metrics";
          list bandwidth {
            key name;
            description "Bandwidth threshold";
            leaf name {
              type string;
            }
            leaf metric {
              description "Metric associated with specified bandwidth";
              type union {
                type string {
                  pattern "<.*>|$.*";
                }
                type uint16 {
                  range "1 .. 65535";
                }
              }
            }
          }
        }
        leaf metric {
          description "Interface metric";
          type union {
            type string {
              pattern "<.*>|$.*";
            }
            type uint16 {
              range "1 .. 65535";
            }
          }
        }
        leaf priority {
          description "Designated router priority";
          type union {
            type string {
              pattern "<.*>|$.*";
            }
            type uint32 {
              range "0 .. 255";
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
        leaf ipsec-sa {
          description "IPSec security association name";
          type string {
            length "1 .. 32";
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
        leaf transmit-interval {
          description "OSPF packet transmit interval (milliseconds)";
          status deprecated;
          type union {
            type string {
              pattern "<.*>|$.*";
            }
            type uint32 {
              range "1 .. 4294967295";
            }
          }
        }
        container bfd-liveness-detection {
          description "Bidirectional Forwarding Detection options";
          leaf version {
            description "BFD protocol version number";
            default "automatic";
            type enumeration {
              enum 0 {
                description "BFD version 0 (deprecated)";
              }
              enum 1 {
                description "BFD version 1";
              }
              enum automatic {
                description "Choose BFD version automatically";
              }
            }
          }
          leaf minimum-interval {
            description "Minimum transmit and receive interval";
            units milliseconds;
            type union {
              type string {
                pattern "<.*>|$.*";
              }
              type uint32 {
                range "1 .. 255000";
              }
            }
          }
          leaf minimum-transmit-interval {
            description "Minimum transmit interval";
            status deprecated;
            units milliseconds;
            type union {
              type string {
                pattern "<.*>|$.*";
              }
              type uint32 {
                range "1 .. 255000";
              }
            }
          }
          leaf minimum-receive-interval {
            description "Minimum receive interval";
            units milliseconds;
            type union {
              type string {
                pattern "<.*>|$.*";
              }
              type uint32 {
                range "1 .. 255000";
              }
            }
          }
          leaf multiplier {
            description "Detection time multiplier";
            default "3";
            type union {
              type string {
                pattern "<.*>|$.*";
              }
              type uint32 {
                range "1 .. 255";
              }
            }
          }
          leaf inline-disable {
            description "Disable inline mode for this BFD session";
            type empty;
          }
          leaf pdu-size {
            description "BFD transport protocol payload size";
            default "24";
            type union {
              type string {
                pattern "<.*>|$.*";
              }
              type uint32 {
                range "24 .. 9000";
              }
            }
          }
          choice adaptation-choice {
            case case_1 {
              leaf no-adaptation {
                description "Disable adaptation";
                type empty;
              }
            }
          }
          container transmit-interval {
            description "Transmit-interval options";
            leaf minimum-interval {
              description "Minimum transmit interval";
              units milliseconds;
              type union {
                type string {
                  pattern "<.*>|$.*";
                }
                type uint32 {
                  range "1 .. 255000";
                }
              }
            }
            leaf threshold {
              description "High transmit interval triggering a trap";
              units milliseconds;
              type union {
                type uint32;
                type string {
                  pattern "<.*>|$.*";
                }
              }
            }
          }
          container detection-time {
            description "Detection-time options";
            leaf threshold {
              description "High detection-time triggering a trap";
              units milliseconds;
              type union {
                type uint32;
                type string {
                  pattern "<.*>|$.*";
                }
              }
            }
          }
          container authentication {
            description "Authentication options";
            leaf key-chain {
              description "Key chain name";
              type string;
            }
            leaf algorithm {
              description "Algorithm name";
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
            }
            leaf loose-check {
              description "Verify authentication only if authentication is negotiated";
              type empty;
            }
          }
          container echo {
            description "Echo mode parameters";
            leaf minimum-interval {
              description "Minimum transmit and receive interval";
              units milliseconds;
              type union {
                type string {
                  pattern "<.*>|$.*";
                }
                type uint32 {
                  range "100 .. 255000";
                }
              }
            }
          }
          container echo-lite {
            description "Echo-lite more parameters";
            leaf minimum-interval {
              description "Minimum transmit and receive interval";
              units milliseconds;
              type union {
                type string {
                  pattern "<.*>|$.*";
                }
                type uint32 {
                  range "100 .. 255000";
                }
              }
            }
          }
          leaf full-neighbors-only {
            description "Setup BFD sessions only to Full neighbors";
            type empty;
          }
          leaf holddown-interval {
            description "Time to hold the session-UP notification to the client";
            units milliseconds;
            type union {
              type string {
                pattern "<.*>|$.*";
              }
              type uint32 {
                range "0 .. 255000";
              }
            }
          }
        }
        leaf dynamic-neighbors {
          description "Learn neighbors dynamically on a p2mp interface";
          type empty;
        }
        leaf no-advertise-adjacency-segment {
          description "Do not advertise an adjacency segment for this interface";
          type empty;
        }
        list neighbor {
          key name;
          ordered-by user;
          description "NBMA neighbor";
          leaf name {
            description "Address of neighbor";
            type jt:ipaddr;
          }
          leaf eligible {
            description "Eligible to be DR on an NBMA network";
            type empty;
          }
        }
        leaf poll-interval {
          description "Poll interval for NBMA interfaces";
          type union {
            type string {
              pattern "<.*>|$.*";
            }
            type uint32 {
              range "1 .. 65535";
            }
          }
        }
        leaf no-interface-state-traps {
          description "Do not send interface state change traps";
          type empty;
        }
        leaf strict-bfd {
          description "Enable strict bfd over this interface";
          type empty;
        }
        container post-convergence-lfa {
          presence "enable post-convergence-lfa";
          description "Protect interface using post-convergence backup path";
          container node-protection {
            presence "enable node-protection";
            description "Compute backup path assuming node failure";
            leaf cost {
              description "Cost for node protection";
              type union {
                type string {
                  pattern "<.*>|$.*";
                }
                type uint16 {
                  range "1 .. 65535";
                }
              }
            }
          }
          leaf srlg-protection {
            description "Compute backup path assuming SRLG failure";
            type empty;
          }
          leaf fate-sharing-protection {
            description "Compute backup path assuming fate-sharing group failure";
            type empty;
          }
        }
        leaf te-metric {
          description "Traffic engineering metric";
          type union {
            type string {
              pattern "<.*>|$.*";
            }
            type uint32 {
              range "1 .. 4294967295";
            }
          }
        }
        container ldp-synchronization {
          description "Advertise maximum metric until LDP is operational";
          presence "enable ldp-synchronization";
          uses ldp-sync-obj;
        }
        container ipv4-adjacency-segment {
          description "Configure ipv4 adjacency segment";
          container protected {
            description "Adjacency SID is eligible for protection";
            choice adjsid-type {
              case case_1 {
                container index {
                  description "Adjacency SID indexed from SRGB";
                  leaf index-number {
                    type union {
                      type string {
                        pattern "<.*>|$.*";
                      }
                      type uint32 {
                        range "0 .. 199999";
                      }
                    }
                  }
                }
              }
              case case_2 {
                leaf label {
                  description "Adjacency SID from static label pool";
                  type union {
                    type string {
                      pattern "<.*>|$.*";
                    }
                    type uint32 {
                      range "16 .. 1048575";
                    }
                  }
                }
              }
              case case_3 {
                leaf dynamic {
                  description "Dynamically allocate an adjacency segment";
                  type empty;
                }
              }
            }
          }
          container unprotected {
            description "Adjacency SID uneligible for protection";
            choice adjsid-type {
              case case_1 {
                container index {
                  description "Adjacency SID indexed from SRGB";
                  leaf index-number {
                    type union {
                      type string {
                        pattern "<.*>|$.*";
                      }
                      type uint32 {
                        range "0 .. 199999";
                      }
                    }
                  }
                }
              }
              case case_2 {
                leaf label {
                  description "Adjacency SID from static label pool";
                  type union {
                    type string {
                      pattern "<.*>|$.*";
                    }
                    type uint32 {
                      range "16 .. 1048575";
                    }
                  }
                }
              }
              case case_3 {
                leaf dynamic {
                  description "Dynamically allocate an adjacency segment";
                  type empty;
                }
              }
            }
          }
        }
        list lan-neighbor {
          key name;
          ordered-by user;
          description "Configuration specific to a LAN neighbor";
          leaf name {
            description "Address of neighbor";
            type jt:ipaddr;
          }
          container ipv4-adjacency-segment {
            description "Configure ipv4 adjacency segment";
            container protected {
              description "Adjacency SID is eligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
            container unprotected {
              description "Adjacency SID uneligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
          }
        }
        leaf delay-metric {
          description "Delay metric";
          units microseconds;
          type union {
            type string {
              pattern "<.*>|$.*";
            }
            type uint32 {
              range "0 .. 16777215";
            }
          }
        }
        container delay-measurement {
          presence "enable delay-measurement";
          description "Enable delay measurement";
          leaf probe-interval {
            description "Probe interval";
            units seconds;
            type union {
              type string {
                pattern "<.*>|$.*";
              }
              type uint32 {
                range "1 .. 255";
              }
            }
          }
          leaf probe-count {
            description "Probe count";
            type union {
              type string {
                pattern "<.*>|$.*";
              }
              type uint32 {
                range "1 .. 15";
              }
            }
          }
          container advertisement {
            description "Delay advertisement";
            container periodic {
              description "Periodic advertisement parameters";
              leaf threshold {
                description "Threshold";
                units percentage;
                type union {
                  type string {
                    pattern "<.*>|$.*";
                  }
                  type uint32 {
                    range "0 .. 100";
                  }
                }
              }
              leaf interval {
                description "Interval";
                units seconds;
                type union {
                  type string {
                    pattern "<.*>|$.*";
                  }
                  type uint32 {
                    range "30 .. 3600";
                  }
                }
              }
            }
            container accelerated {
              presence "enable accelerated";
              description "Accelerated advertisement parameters";
              leaf threshold {
                description "Threshold";
                units percentage;
                type union {
                  type string {
                    pattern "<.*>|$.*";
                  }
                  type uint32 {
                    range "0 .. 100";
                  }
                }
              }
            }
          }
        }
        container application-specific {
          description "Advertise application-specific TE attributes";
          list attribute-group {
            key name;
            ordered-by user;
            description "Link attribute group name";
            max-elements 1;
            leaf name {
              description "Link attribute group name";
              type string;
            }
            leaf te-metric {
              description "Traffic engineering metric for this attribute group";
              type union {
                type string {
                  pattern "<.*>|$.*";
                }
                type uint32 {
                  range "1 .. 4294967295";
                }
              }
            }
            leaf-list admin-group {
              ordered-by user;
              description "Administrative groups for this attribute-group";
              type string;
              max-elements 16;
            }
            leaf delay-metric {
              description "Delay metric for this attribute-group";
              units microseconds;
              type union {
                type string {
                  pattern "<.*>|$.*";
                }
                type uint32 {
                  range "0 .. 16777215";
                }
              }
            }
            leaf advertise-interface-delay {
              description "Use interface specific static/dynamic delay values as applicable in ASLA Sub-TLVs";
              type empty;
            }
            container application {
              description "Standard Applications part of this attribute-group";
              leaf flex-algorithm {
                description "Set X flag in standard application bit mask";
                type empty;
              }
            }
          }
        }
      }
      leaf no-context-identifier-advertisement {
        description "Disable context identifier advertisments in this area";
        type empty;
      }
      list peer-interface {
        key name;
        ordered-by user;
        description "Configuration for peer interface";
        leaf name {
          description "Name of peer interface";
          type string;
        }
        choice enable-disable {
          case case_1 {
            leaf disable {
              description "Disable OSPF on this control peer";
              type empty;
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
      }
      leaf no-source-packet-routing {
        description "Disable SPRING in this area";
        type empty;
      }
      list context-identifier {
        key name;
        ordered-by user;
        description "Configure context identifier in support of edge protection";
        leaf name {
          description "Context identifier";
          type jt:ipv4addr;
        }
      }
      list label-switched-path {
        key name;
        ordered-by user;
        description "Configuration for advertisement of a label-switched path";
        leaf name {
          description "Name of label-switched path to be advertised";
          type string {
            length "1 .. 64";
          }
        }
        choice enable-disable {
          case case_1 {
            leaf disable {
              description "Disable OSPF on this label-switched path";
              type empty;
            }
          }
        }
        leaf metric {
          description "Interface metric";
          type union {
            type string {
              pattern "<.*>|$.*";
            }
            type uint16 {
              range "1 .. 65535";
            }
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
    }
    choice enable-disable {
      case case_1 {
        leaf disable {
          description "Disable OSPF";
          type empty;
        }
      }
    }
    container traceoptions {
      description "Trace options for OSPF";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum spf {
              description "Trace SPF calculations";
            }
            enum error {
              description "Trace errored packets";
            }
            enum event {
              description "Trace OSPF state machine events";
            }
            enum packet-dump {
              description "Dump the contents of selected packet types";
            }
            enum flooding {
              description "Trace LSA flooding";
            }
            enum lsa-analysis {
              description "Trace LSA analysis";
            }
            enum packets {
              description "Trace all OSPF packets";
            }
            enum hello {
              description "Trace hello packets";
            }
            enum database-description {
              description "Trace database description packets";
            }
            enum lsa-request {
              description "Trace LSA request packets";
            }
            enum lsa-update {
              description "Trace LSA update packets";
            }
            enum lsa-ack {
              description "Trace LSA acknowledgment packets";
            }
            enum ldp-synchronization {
              description "Trace synchronization between OSPF and LDP";
            }
            enum on-demand {
              description "Trace demand circuit extensions";
            }
            enum nsr-synchronization {
              description "Trace NSR synchronization events";
            }
            enum graceful-restart {
              description "Trace graceful restart";
            }
            enum restart-signaling {
              description "Trace restart signaling";
            }
            enum traffic-statistics {
              description "Trace Segment Routing Traffic Statistics";
            }
            enum backup-spf {
              description "Trace backup SPF (LFA) specific events";
            }
            enum source-packet-routing {
              description "Trace source packet routing (SPRING) events";
            }
            enum post-convergence-lfa {
              description "Trace post-convergence-lfa related events";
            }
            enum flex-algorithm {
              description "Trace flex-algorithm related events";
            }
            enum rmopd {
              description "Trace rmopd interactions";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf prefix-export-limit {
      description "Maximum number of prefixes that can be exported";
      type union {
        type string {
          pattern "<.*>|$.*";
        }
        type uint32 {
          range "0 .. 4294967295";
        }
      }
    }
    container rib-groups {
      description "Routing table groups for importing OSPF routes";
      leaf inet {
        description "Name of the IPv4/v6 routing table group";
        type string;
      }
      leaf inet3 {
        description "Name of the IPv4/v6 inet.3 routing table group";
        type string;
      }
    }
    leaf job-stats {
      description "Collect job statistics";
      type empty;
    }
    container overload {
      presence "enable overload";
      description "Set the overload mode (repel transit traffic)";
      leaf timeout {
        description "Time after which overload mode is reset";
        units seconds;
        type union {
          type string {
            pattern "<.*>|$.*";
          }
          type uint32 {
            range "60 .. 3600";
          }
        }
      }
      leaf allow-route-leaking {
        description "Allow routes to be leaked when overload is configured";
        type empty;
      }
      leaf stub-network {
        description "Advertise Stub Network with maximum metric";
        type empty;
      }
      leaf intra-area-prefix {
        description "Advertise Intra Area Prefix with maximum metric";
        type empty;
      }
      leaf as-external {
        description "Advertise As External with maximum usable metric";
        type empty;
      }
    }
    container database-protection {
      presence "enable database-protection";
      description "Configure database protection attributes";
      leaf maximum-lsa {
        description "Maximum allowed non self-generated LSAs";
        type union {
          type string {
            pattern "<.*>|$.*";
          }
          type uint32 {
            range "1 .. 1000000";
          }
        }
      }
      leaf warning-only {
        description "Emit only a warning when LSA maximum limit is exceeded";
        type empty;
      }
      leaf warning-threshold {
        description "Percentage of LSA maximum above which to trigger warning";
        units percent;
        type union {
          type string {
            pattern "<.*>|$.*";
          }
          type uint8 {
            range "30 .. 100";
          }
        }
      }
      leaf ignore-count {
        description "Maximum number of times to go into ignore state";
        type union {
          type string {
            pattern "<.*>|$.*";
          }
          type uint8 {
            range "1 .. 32";
          }
        }
      }
      leaf ignore-time {
        description "Time to stay in ignore state and ignore all neighbors";
        units seconds;
        type union {
          type string {
            pattern "<.*>|$.*";
          }
          type uint16 {
            range "30 .. 3600";
          }
        }
      }
      leaf reset-time {
        description "Time after which the ignore count gets reset to zero";
        units seconds;
        type union {
          type string {
            pattern "<.*>|$.*";
          }
          type uint32 {
            range "60 .. 86400";
          }
        }
      }
    }
    container graceful-restart {
      description "Configure graceful restart attributes";
      choice enable-disable {
        case case_1 {
          leaf disable {
            description "Disable OSPF graceful restart capability";
            type empty;
          }
        }
      }
      leaf restart-duration {
        description "Time for all neighbors to become full";
        units seconds;
        type union {
          type string {
            pattern "<.*>|$.*";
          }
          type uint32 {
            range "1 .. 3600";
          }
        }
      }
      leaf notify-duration {
        description "Time to send all max-aged grace LSAs";
        units seconds;
        type union {
          type string {
            pattern "<.*>|$.*";
          }
          type uint32 {
            range "1 .. 3600";
          }
        }
      }
      container helper-disable {
        presence "enable helper-disable";
        description "Disable graceful restart helper capability";
        choice disable-choices {
          case case_1 {
            leaf standard {
              description "Disable helper-mode for rfc3623 based GR";
              type empty;
            }
          }
          case case_2 {
            leaf restart-signaling {
              description "Disable helper mode for restart-signaling ";
              type empty;
            }
          }
          case case_3 {
            leaf both {
              description "Disable helper mode for both the types of GR";
              type empty;
            }
          }
        }
      }
      leaf no-strict-lsa-checking {
        description "Do not abort graceful helper mode upon LSA changes";
        type empty;
      }
    }
    leaf route-type-community {
      description "Specify BGP extended community value to encode OSPF route type";
      type enumeration {
        enum iana {
          description "BGP extended community value used is 0x0306";
        }
        enum vendor {
          description "Vendor BGP extended community value used is 0x8000";
        }
      }
    }
    container domain-id {
      description "Configure domain ID";
      choice domain_id_or_disable {
        case case_1 {
          leaf domain-id {
            description "Domain ID";
            type string;
          }
        }
        case case_2 {
          leaf disable {
            description "Disable domain ID";
            type empty;
          }
        }
      }
    }
    choice domain_vpn_tag_or_disable {
      case case_1 {
        leaf domain-vpn-tag {
          description "Domain VPN tag for external LSA";
          type union {
            type string {
              pattern "<.*>|$.*";
            }
            type uint32 {
              range "0 .. 4294967295";
            }
          }
        }
      }
      case case_2 {
        leaf no-domain-vpn-tag {
          description "Disable domain VPN tag";
          type empty;
        }
      }
    }
    leaf preference {
      description "Preference of internal routes";
      type union {
        type uint32;
        type string {
          pattern "<.*>|$.*";
        }
      }
    }
    leaf external-preference {
      description "Preference of external routes";
      type union {
        type uint32;
        type string {
          pattern "<.*>|$.*";
        }
      }
    }
    leaf labeled-preference {
      description "Preference of labeled routes";
      type union {
        type uint32;
        type string {
          pattern "<.*>|$.*";
        }
      }
    }
    leaf-list export {
      ordered-by user;
      description "Export policy";
      type jt:policy-algebra;
    }
    leaf-list import {
      ordered-by user;
      description "Import policy (for external routes or setting priority)";
      type jt:policy-algebra;
    }
    leaf reference-bandwidth {
      description "Bandwidth for calculating metric defaults";
      type string;
    }
    leaf lsa-refresh-interval {
      description "LSA refresh interval (minutes)";
      default "50";
      type union {
        type string {
          pattern "<.*>|$.*";
        }
        type uint32 {
          range "25 .. 50";
        }
      }
    }
    leaf spf-delay {
      description "Time to wait before running an SPF";
      status deprecated;
      units milliseconds;
      type union {
        type string {
          pattern "<.*>|$.*";
        }
        type uint32 {
          range "50 .. 8000";
        }
      }
    }
    leaf no-rfc-1583 {
      description "Disable RFC1583 compatibility";
      type empty;
    }
    leaf forwarding-address-to-broadcast {
      description "Set forwarding address in Type 5 LSA in broadcast network";
      type empty;
    }
    choice nssa-abr-option {
      case case_1 {
        leaf no-nssa-abr {
          description "Disable full NSSA functionality at ABR";
          type empty;
        }
      }
    }
    container sham-link {
      presence "enable sham-link";
      description "Configure parameters for sham links";
      leaf local {
        description "Local sham link endpoint address";
        type jt:ipaddr;
      }
      leaf no-advertise-local {
        description "Don't advertise local sham link endpoint as stub in router LSA";
        status deprecated;
        type empty;
      }
    }
  }
  grouping juniper-ospf-authentication {
    description "Authentication information";
    choice authentication-type {
      case case_1 {
        leaf simple-password {
          description "Authentication key";
          type jt:unreadable;
        }
      }
      case case_2 {
        list md5 {
          key name;
          ordered-by user;
          description "MD5 authentication key";
          leaf name {
            description "Key ID for MD5 authentication";
            type union {
              type string {
                pattern "<.*>|$.*";
              }
              type uint32 {
                range "0 .. 255";
              }
            }
          }
          leaf key {
            description "MD5 authentication key value";
            type jt:unreadable;
          }
          leaf start-time {
            description "Start time for key transmission (YYYY-MM-DD.HH:MM)";
            type jt:time;
          }
        }
      }
      case case_3 {
        list multi-active-md5 {
          key name;
          ordered-by user;
          description "Authentication Multiple active MD5 keys";
          leaf name {
            description "Key ID for MD5 authentication";
            type union {
              type string {
                pattern "<.*>|$.*";
              }
              type uint32 {
                range "0 .. 255";
              }
            }
          }
          leaf key {
            description "MD5 authentication key value";
            type jt:unreadable;
          }
          leaf delete-if-not-inuse {
            description "Delete this key if not in use";
            type empty;
          }
        }
      }
      case case_4 {
        leaf keychain {
          description "Key chain name";
          type string {
            length "1 .. 128";
          }
        }
      }
    }
  }
  grouping juniper-protocols-ospf3 {
    list realm {
      key name;
      ordered-by user;
      description "OSPFv3 realm configuration";
      leaf name {
        description "OSPFv3 realm name";
        type enumeration {
          enum ipv6-unicast {
            description "IPv6 unicast realm";
          }
          enum ipv6-multicast {
            description "IPv6 multicast realm";
          }
          enum ipv4-unicast {
            description "IPv4 unicast realm";
          }
          enum ipv4-multicast {
            description "IPv4 multicast realm";
          }
        }
      }
      list topology {
        key name;
        ordered-by user;
        description "Topology parameters";
        leaf name {
          description "Topology name";
          type string;
        }
        leaf disable {
          description "Disable this topology";
          type empty;
        }
        leaf topology-id {
          description "Topology identifier";
          type union {
            type string {
              pattern "<.*>|$.*";
            }
            type uint8 {
              range "32 .. 127";
            }
          }
        }
        leaf overload {
          description "Set the overload mode (repel transit traffic)";
          type empty;
        }
        leaf rib-group {
          description "Routing table group for importing routes";
          type string;
        }
        container spf-options {
          description "Configure options for SPF";
          container microloop-avoidance {
            description "Configure microloop avoidance mechanism";
            container post-convergence-path {
              presence "enable post-convergence-path";
              description "Temporarily install post-convergence path for routes potentially affected by microloops";
              leaf delay {
                description "Time after which temporary post-convergence paths are removed";
                units milliseconds;
                type union {
                  type string {
                    pattern "<.*>|$.*";
                  }
                  type uint32 {
                    range "500 .. 60000";
                  }
                }
              }
              leaf maximum-labels {
                description "Maximum number of labels installed for post-convergence paths";
                type union {
                  type string {
                    pattern "<.*>|$.*";
                  }
                  type uint32 {
                    range "2 .. 8";
                  }
                }
              }
            }
          }
          leaf delay {
            description "Time to wait before running an SPF";
            units milliseconds;
            type union {
              type string {
                pattern "<.*>|$.*";
              }
              type uint32 {
                range "50 .. 8000";
              }
            }
          }
          leaf holddown {
            description "Time to hold down before running an SPF";
            units milliseconds;
            type union {
              type string {
                pattern "<.*>|$.*";
              }
              type uint32 {
                range "2000 .. 20000";
              }
            }
          }
          leaf rapid-runs {
            description "Number of maximum rapid SPF runs before holddown";
            type union {
              type string {
                pattern "<.*>|$.*";
              }
              type uint32 {
                range "1 .. 10";
              }
            }
          }
          leaf no-ignore-our-externals {
            description "Do not ignore self-generated external and NSSA LSAs";
            type empty;
          }
        }
        container backup-spf-options {
          description "Configure options for backup SPF";
          container remote-backup-calculation {
            presence "enable remote-backup-calculation";
            description "Calculate Remote LFA backup nexthops";
            container pq-nodes-nearest-to-source {
              description "PQ nodes selection based upon nearest to source";
              leaf percent {
                description "Selection percentage for nearest to source";
                type union {
                  type string {
                    pattern "<.*>|$.*";
                  }
                  type uint32 {
                    range "10 .. 100";
                  }
                }
              }
            }
          }
          container use-post-convergence-lfa {
            presence "enable use-post-convergence-lfa";
            description "Calculate post-convergence backup paths";
            leaf maximum-labels {
              description "Maximum number of labels installed for post-convergence paths";
              type union {
                type string {
                  pattern "<.*>|$.*";
                }
                type uint32 {
                  range "2 .. 8";
                }
              }
            }
            leaf maximum-backup-paths {
              description "Maximum number of equal-cost post-convergence paths installed";
              type union {
                type string {
                  pattern "<.*>|$.*";
                }
                type uint32 {
                  range "1 .. 8";
                }
              }
            }
          }
          leaf use-source-packet-routing {
            description "Use spring backup paths for inet.0 routes";
            type empty;
          }
          leaf disable {
            description "Do not run backup SPF";
            type empty;
          }
          leaf no-install {
            description "Do not install backup nexthops into the RIB";
            type empty;
          }
          leaf downstream-paths-only {
            description "Use only downstream backup paths";
            type empty;
          }
          container per-prefix-calculation {
            description "Calculate backup nexthops for non-best prefix originators";
            leaf stubs {
              description "Per prefix calculation for stubs only";
              type empty;
            }
            leaf summary {
              description "Per prefix calculation for summary originators only";
              type empty;
            }
            leaf externals {
              description "Per prefix calculation for externals";
              type empty;
            }
            leaf all {
              description "Per prefix calculation for all";
              type empty;
            }
          }
          leaf node-link-degradation {
            description "Degrade to link protection when nodelink protection not available";
            type empty;
          }
        }
        leaf prefix-export-limit {
          description "Maximum number of prefixes that can be exported";
          type union {
            type string {
              pattern "<.*>|$.*";
            }
            type uint32 {
              range "0 .. 4294967295";
            }
          }
        }
      }
      container spf-options {
        description "Configure options for SPF";
        container microloop-avoidance {
          description "Configure microloop avoidance mechanism";
          container post-convergence-path {
            presence "enable post-convergence-path";
            description "Temporarily install post-convergence path for routes potentially affected by microloops";
            leaf delay {
              description "Time after which temporary post-convergence paths are removed";
              units milliseconds;
              type union {
                type string {
                  pattern "<.*>|$.*";
                }
                type uint32 {
                  range "500 .. 60000";
                }
              }
            }
            leaf maximum-labels {
              description "Maximum number of labels installed for post-convergence paths";
              type union {
                type string {
                  pattern "<.*>|$.*";
                }
                type uint32 {
                  range "2 .. 8";
                }
              }
            }
          }
        }
        leaf delay {
          description "Time to wait before running an SPF";
          units milliseconds;
          type union {
            type string {
              pattern "<.*>|$.*";
            }
            type uint32 {
              range "50 .. 8000";
            }
          }
        }
        leaf holddown {
          description "Time to hold down before running an SPF";
          units milliseconds;
          type union {
            type string {
              pattern "<.*>|$.*";
            }
            type uint32 {
              range "2000 .. 20000";
            }
          }
        }
        leaf rapid-runs {
          description "Number of maximum rapid SPF runs before holddown";
          type union {
            type string {
              pattern "<.*>|$.*";
            }
            type uint32 {
              range "1 .. 10";
            }
          }
        }
        leaf no-ignore-our-externals {
          description "Do not ignore self-generated external and NSSA LSAs";
          type empty;
        }
      }
      container backup-spf-options {
        description "Configure options for backup SPF";
        container remote-backup-calculation {
          presence "enable remote-backup-calculation";
          description "Calculate Remote LFA backup nexthops";
          container pq-nodes-nearest-to-source {
            description "PQ nodes selection based upon nearest to source";
            leaf percent {
              description "Selection percentage for nearest to source";
              type union {
                type string {
                  pattern "<.*>|$.*";
                }
                type uint32 {
                  range "10 .. 100";
                }
              }
            }
          }
        }
        container use-post-convergence-lfa {
          presence "enable use-post-convergence-lfa";
          description "Calculate post-convergence backup paths";
          leaf maximum-labels {
            description "Maximum number of labels installed for post-convergence paths";
            type union {
              type string {
                pattern "<.*>|$.*";
              }
              type uint32 {
                range "2 .. 8";
              }
            }
          }
          leaf maximum-backup-paths {
            description "Maximum number of equal-cost post-convergence paths installed";
            type union {
              type string {
                pattern "<.*>|$.*";
              }
              type uint32 {
                range "1 .. 8";
              }
            }
          }
        }
        leaf use-source-packet-routing {
          description "Use spring backup paths for inet.0 routes";
          type empty;
        }
        leaf disable {
          description "Do not run backup SPF";
          type empty;
        }
        leaf no-install {
          description "Do not install backup nexthops into the RIB";
          type empty;
        }
        leaf downstream-paths-only {
          description "Use only downstream backup paths";
          type empty;
        }
        container per-prefix-calculation {
          description "Calculate backup nexthops for non-best prefix originators";
          leaf stubs {
            description "Per prefix calculation for stubs only";
            type empty;
          }
          leaf summary {
            description "Per prefix calculation for summary originators only";
            type empty;
          }
          leaf externals {
            description "Per prefix calculation for externals";
            type empty;
          }
          leaf all {
            description "Per prefix calculation for all";
            type empty;
          }
        }
        leaf node-link-degradation {
          description "Degrade to link protection when nodelink protection not available";
          type empty;
        }
      }
      container traffic-engineering {
        presence "enable traffic-engineering";
        description "Configure traffic engineering attributes";
        leaf no-topology {
          description "Disable dissemination of TE link-state topology information";
          type empty;
        }
        leaf multicast-rpf-routes {
          description "Install routes for multicast RPF checks into inet.2";
          type empty;
        }
        leaf l3-unicast-topology {
          description "Download IGP topology into TED";
          type empty;
        }
        container ignore-lsp-metrics {
          presence "enable ignore-lsp-metrics";
          description "Ignore label-switched path metrics when doing shortcuts";
          leaf unconfigured-only {
            description "Ignore lsp metrics for unconfigured only";
            type empty;
          }
        }
        container shortcuts {
          presence "enable shortcuts";
          description "Use label-switched paths as next hops, if possible";
          leaf ignore-lsp-metrics {
            description "Ignore label-switched path metrics when doing shortcuts";
            status deprecated;
            type empty;
          }
          leaf lsp-metric-into-summary {
            description "Advertise LSP metric into summary LSAs";
            type empty;
          }
          list family {
            key name;
            ordered-by user;
            description "Address family specific traffic-engineering attributes";
            leaf name {
              type enumeration {
                enum inet {
                  description "IPv4 family";
                }
                enum inet-mpls {
                  description "IPv4-MPLS family";
                }
              }
            }
          }
        }
        leaf advertise-unnumbered-interfaces {
          description "Advertise unnumbered interfaces";
          type empty;
        }
        leaf credibility-protocol-preference {
          description "TED protocol credibility follows protocol preference";
          type empty;
        }
        container advertisement {
          description "Advertise TE parameters even if RSVP is not turned on";
          leaf always {
            description "Advertise TE parameters in TE LSAs";
            type empty;
          }
        }
        container tunnel-source-protocol {
          description "Protocols from which to pick label-switched paths";
          container rsvp {
            presence "enable rsvp";
            description "Pick label-switched paths from rsvp";
            leaf preference {
              description "Preference for label-switched paths from this protocol";
              type union {
                type string {
                  pattern "<.*>|$.*";
                }
                type uint32 {
                  range "1 .. 255";
                }
              }
            }
          }
          container spring-te {
            presence "enable spring-te";
            description "Pick label-switched paths from spring-te";
            leaf preference {
              description "Preference for label-switched paths from this protocol";
              type union {
                type string {
                  pattern "<.*>|$.*";
                }
                type uint32 {
                  range "1 .. 255";
                }
              }
            }
          }
        }
      }
      container source-packet-routing {
        presence "enable source-packet-routing";
        description "Enable source packet routing (SPRING)";
        container adjacency-segment {
          description "Attributes for adjacency segments in spring";
          leaf hold-time {
            description "Retain time of Adjacency segment after isolating from an interface";
            type union {
              type string {
                pattern "<.*>|$.*";
              }
              type uint32 {
                range "180000 .. 900000";
              }
            }
          }
        }
        leaf-list prefix-segment {
          ordered-by user;
          description "Prefix Segment policy";
          type jt:policy-algebra;
        }
        leaf explicit-null {
          description "Set E and P bits in all Prefix SID advertisements";
          type empty;
        }
        container node-segment {
          presence "enable node-segment";
          description "Enable support for Node segments in SPRING";
          leaf ipv4-index {
            description "Set ipv4 node segment index";
            type union {
              type string {
                pattern "<.*>|$.*";
              }
              type uint32 {
                range "0 .. 199999";
              }
            }
          }
          leaf index-range {
            description "Set range of node segment indices allowed";
            type union {
              type string {
                pattern "<.*>|$.*";
              }
              type uint32 {
                range "32 .. 16385";
              }
            }
          }
        }
        container srgb {
          description "Set the SRGB global block in SPRING";
          leaf start-label {
            description "Start range for SRGB label block";
            type union {
              type string {
                pattern "<.*>|$.*";
              }
              type uint32;
            }
          }
          leaf index-range {
            description "Index to the SRGB start label block";
            type union {
              type string {
                pattern "<.*>|$.*";
              }
              type uint32;
            }
          }
        }
        leaf mapping-server {
          description "Mapping server name";
          type string;
        }
        leaf install-prefix-sid-for-best-route {
          description "For best route install a exact prefix sid route";
          type empty;
        }
        leaf ldp-stitching {
          description "Enable SR to LDP stitching";
          type empty;
        }
        leaf-list flex-algorithm {
          description "Flex-algorithms we would like to participate in";
          type union {
            type string {
              pattern "<.*>|$.*";
            }
            type uint32 {
              range "128 .. 255";
            }
          }
          max-elements 16;
        }
        leaf strict-asla-based-flex-algorithm {
          description "Flex-Algorithm to ignore links not having ASLA sub-TLVs";
          type empty;
        }
        container sensor-based-stats {
          description "Configure sensor based stats in SPRING";
          container per-interface-per-member-link {
            description "Configure sensor based stats per nexthop";
            leaf ingress {
              description "Enable sensor based stats on ingress interface";
              type empty;
            }
            leaf egress {
              description "Enable sensor based stats on egress interface";
              type empty;
            }
          }
          container per-sid {
            description "Configure sensor based stats per spring route";
            leaf ingress {
              description "Enable sensor based stats for per-sid ingress accounting";
              type empty;
            }
            leaf egress {
              description "Enable sensor based stats for IP-MPLS egress accounting";
              type empty;
            }
          }
        }
      }
      list area {
        key name;
        ordered-by user;
        description "Configure an OSPF area";
        leaf name {
          description "Area ID";
          type jt:areaid;
        }
        choice stub-option {
          case case_1 {
            container stub {
              presence "enable stub";
              description "Configure a stub area";
              leaf default-metric {
                description "Metric for the default route in this stub area";
                type union {
                  type string {
                    pattern "<.*>|$.*";
                  }
                  type uint32 {
                    range "1 .. 16777215";
                  }
                }
              }
              choice summaries-choice {
                leaf summaries {
                  description "Flood summary LSAs into this stub area";
                  type empty;
                }
                leaf no-summaries {
                  description "Don't flood summary LSAs into this stub area";
                  type empty;
                }
              }
            }
          }
          case case_2 {
            container nssa {
              presence "enable nssa";
              description "Configure a not-so-stubby area";
              container default-lsa {
                presence "enable default-lsa";
                description "Configure a default LSA";
                leaf default-metric {
                  description "Metric for the default route in this area";
                  type union {
                    type string {
                      pattern "<.*>|$.*";
                    }
                    type uint32 {
                      range "1 .. 16777215";
                    }
                  }
                }
                leaf metric-type {
                  description "External metric type for the default type 7 LSA";
                  type union {
                    type string {
                      pattern "<.*>|$.*";
                    }
                    type uint32 {
                      range "1 .. 2";
                    }
                  }
                }
                leaf type-7 {
                  description "Flood type 7 default LSA if no-summaries is configured";
                  type empty;
                }
              }
              leaf default-metric {
                description "Metric for the default route in this area";
                status deprecated;
                type union {
                  type string {
                    pattern "<.*>|$.*";
                  }
                  type uint32 {
                    range "1 .. 16777215";
                  }
                }
              }
              leaf metric-type {
                description "External metric type for the default type 7 LSA";
                status deprecated;
                type union {
                  type string {
                    pattern "<.*>|$.*";
                  }
                  type uint32 {
                    range "1 .. 2";
                  }
                }
              }
              choice summaries-choice {
                leaf summaries {
                  description "Flood summary LSAs into this NSSA area";
                  type empty;
                }
                leaf no-summaries {
                  description "Don't flood summary LSAs into this NSSA area";
                  type empty;
                }
              }
              list area-range {
                key name;
                ordered-by user;
                description "Configure NSSA area ranges";
                leaf name {
                  description "Range to summarize NSSA routes in this area";
                  type jt:ipprefix;
                }
                leaf restrict {
                  description "Restrict advertisement of this area range";
                  type empty;
                }
                leaf exact {
                  description "Enforce exact match for advertisement of this area range";
                  type empty;
                }
                container override-metric {
                  presence "enable override-metric";
                  description "Override the dynamic metric for this area-range";
                  leaf metric {
                    description "Metric value";
                    type union {
                      type string {
                        pattern "<.*>|$.*";
                      }
                      type uint32 {
                        range "1 .. 16777215";
                      }
                    }
                  }
                  leaf metric-type {
                    description "Set the metric type for the override metric";
                    default "1";
                    type union {
                      type string {
                        pattern "<.*>|$.*";
                      }
                      type uint32 {
                        range "1 .. 2";
                      }
                    }
                  }
                }
              }
            }
          }
        }
        list area-range {
          key name;
          ordered-by user;
          description "Configure area ranges";
          leaf name {
            description "Range to summarize routes in this area";
            type jt:ipprefix;
          }
          leaf restrict {
            description "Restrict advertisement of this area range";
            type empty;
          }
          leaf exact {
            description "Enforce exact match for advertisement of this area range";
            type empty;
          }
          leaf override-metric {
            description "Override the dynamic metric for this area-range";
            type union {
              type string {
                pattern "<.*>|$.*";
              }
              type uint32 {
                range "1 .. 16777215";
              }
            }
          }
        }
        leaf-list network-summary-export {
          ordered-by user;
          description "Export policy for Type 3 Summary LSAs";
          type jt:policy-algebra;
        }
        leaf-list network-summary-import {
          ordered-by user;
          description "Import policy for Type 3 Summary LSAs";
          type jt:policy-algebra;
        }
        leaf-list inter-area-prefix-export {
          ordered-by user;
          description "Export policy for Inter Area Prefix LSAs";
          type jt:policy-algebra;
        }
        leaf-list inter-area-prefix-import {
          ordered-by user;
          description "Import policy for Inter Area Prefix LSAs";
          type jt:policy-algebra;
        }
        leaf authentication-type {
          description "Authentication type";
          status deprecated;
          type enumeration {
            enum none {
              description "No authentication";
              status deprecated;
            }
            enum simple {
              description "Simple password authentication";
              status deprecated;
            }
            enum md5 {
              description "MD5 authentication";
              status deprecated;
            }
          }
        }
        list virtual-link {
          key "neighbor-id transit-area";
          ordered-by user;
          description "Configure virtual links";
          leaf neighbor-id {
            description "Router ID of a virtual neighbor";
            type jt:ipv4addr;
          }
          leaf transit-area {
            description "Transit area in common with virtual neighbor";
            type jt:areaid;
          }
          choice enable-disable {
            case case_1 {
              leaf disable {
                description "Disable this virtual link";
                type empty;
              }
            }
          }
          leaf retransmit-interval {
            description "Retransmission interval (seconds)";
            type union {
              type string {
                pattern "<.*>|$.*";
              }
              type uint32 {
                range "1 .. 65535";
              }
            }
          }
          leaf transit-delay {
            description "Transit delay (seconds)";
            type union {
              type string {
                pattern "<.*>|$.*";
              }
              type uint32 {
                range "1 .. 65535";
              }
            }
          }
          leaf hello-interval {
            description "Hello interval (seconds)";
            type union {
              type string {
                pattern "<.*>|$.*";
              }
              type uint32 {
                range "1 .. 255";
              }
            }
          }
          leaf dead-interval {
            description "Dead interval (seconds)";
            type union {
              type string {
                pattern "<.*>|$.*";
              }
              type uint32 {
                range "1 .. 65535";
              }
            }
          }
          leaf mtu {
            description "Maximum OSPF packet size";
            type union {
              type string {
                pattern "<.*>|$.*";
              }
              type uint32 {
                range "128 .. 65535";
              }
            }
          }
          choice auth {
            case case_1 {
              container authentication {
                uses juniper-ospf-authentication;
              }
            }
            case case_2 {
              container authentication-key {
                description "Authentication key";
                status deprecated;
                leaf keyname {
                  description "Authentication key value";
                  type jt:unreadable;
                }
                leaf key-id {
                  description "Key ID for MD5 authentication";
                  type union {
                    type string {
                      pattern "<.*>|$.*";
                    }
                    type uint32 {
                      range "0 .. 255";
                    }
                  }
                }
              }
            }
          }
          leaf demand-circuit {
            description "Interface functions as a demand circuit";
            type empty;
          }
          leaf flood-reduction {
            description "Enable flood reduction";
            type empty;
          }
          leaf no-neighbor-down-notification {
            description "Don't inform other protocols about neighbor down events";
            type empty;
          }
          leaf ipsec-sa {
            description "IPSec security association name";
            type string {
              length "1 .. 32";
            }
          }
          list topology {
            key name;
            ordered-by user;
            description "Topology specific attributes";
            leaf name {
              description "Topology name";
              type string;
            }
            leaf disable {
              description "Disable this topology";
              type empty;
            }
            leaf metric {
              description "Topology metric";
              type union {
                type string {
                  pattern "<.*>|$.*";
                }
                type uint16 {
                  range "1 .. 65535";
                }
              }
            }
            container bandwidth-based-metrics {
              description "Configure bandwidth based metrics";
              list bandwidth {
                key name;
                description "Bandwidth threshold";
                leaf name {
                  type string;
                }
                leaf metric {
                  description "Metric associated with specified bandwidth";
                  type union {
                    type string {
                      pattern "<.*>|$.*";
                    }
                    type uint16 {
                      range "1 .. 65535";
                    }
                  }
                }
              }
            }
          }
        }
        list sham-link-remote {
          key name;
          ordered-by user;
          description "Configure parameters for remote sham link endpoint";
          leaf name {
            description "Remote sham link endpoint address";
            type jt:ipaddr;
          }
          leaf metric {
            description "Sham link metric";
            type union {
              type string {
                pattern "<.*>|$.*";
              }
              type uint16 {
                range "1 .. 65535";
              }
            }
          }
          leaf ipsec-sa {
            description "IPSec security association name";
            type string {
              length "1 .. 32";
            }
          }
          leaf demand-circuit {
            description "Interface functions as a demand circuit";
            type empty;
          }
          leaf flood-reduction {
            description "Enable flood reduction";
            type empty;
          }
          list topology {
            key name;
            ordered-by user;
            description "Topology specific attributes";
            leaf name {
              description "Topology name";
              type string;
            }
            leaf disable {
              description "Disable this topology";
              type empty;
            }
            leaf metric {
              description "Topology metric";
              type union {
                type string {
                  pattern "<.*>|$.*";
                }
                type uint16 {
                  range "1 .. 65535";
                }
              }
            }
            container bandwidth-based-metrics {
              description "Configure bandwidth based metrics";
              list bandwidth {
                key name;
                description "Bandwidth threshold";
                leaf name {
                  type string;
                }
                leaf metric {
                  description "Metric associated with specified bandwidth";
                  type union {
                    type string {
                      pattern "<.*>|$.*";
                    }
                    type uint16 {
                      range "1 .. 65535";
                    }
                  }
                }
              }
            }
          }
        }
        list interface {
          key name;
          ordered-by user;
          description "Include an interface in this area";
          leaf name {
            description "Interface name";
            type union {
              type jt:ipv4addr-or-interface;
              type string {
                pattern "<.*>|$.*";
              }
            }
          }
          choice enable-disable {
            case case_1 {
              leaf disable {
                description "Disable OSPF on this interface";
                type empty;
              }
            }
          }
          leaf interface-type {
            description "Type of interface";
            type enumeration {
              enum nbma {
                description "Nonbroadcast multiaccess";
              }
              enum p2mp {
                description "Point-to-multipoint NBMA";
              }
              enum p2p {
                description "Point-to-point";
              }
              enum p2mp-over-lan {
                description "Point-to-multipoint over LAN mode";
              }
            }
          }
          choice protection-type {
            case case_1 {
              leaf link-protection {
                description "Protect interface from link faults only";
                type empty;
              }
            }
            case case_2 {
              leaf node-link-protection {
                description "Protect interface from both link and node faults";
                type empty;
              }
            }
          }
          leaf no-eligible-backup {
            description "Not eligible to backup traffic from protected interfaces";
            type empty;
          }
          leaf no-eligible-remote-backup {
            description "Not eligible for Remote-LFA backup traffic from protected interfaces";
            type empty;
          }
          container passive {
            presence "enable passive";
            description "Do not run OSPF, but advertise it";
            container traffic-engineering {
              description "Advertise TE link information";
              leaf remote-node-id {
                description "Remote address of the link";
                type jt:ipaddr;
              }
              leaf remote-node-router-id {
                description "TE Router-ID of the remote node";
                type jt:ipv4addr;
              }
            }
          }
          leaf secondary {
            description "Treat interface as secondary";
            type empty;
          }
          leaf own-router-lsa {
            description "Generate a separate router LSA for this interface";
            type empty;
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
          leaf metric {
            description "Interface metric";
            type union {
              type string {
                pattern "<.*>|$.*";
              }
              type uint16 {
                range "1 .. 65535";
              }
            }
          }
          leaf priority {
            description "Designated router priority";
            type union {
              type string {
                pattern "<.*>|$.*";
              }
              type uint32 {
                range "0 .. 255";
              }
            }
          }
          leaf retransmit-interval {
            description "Retransmission interval (seconds)";
            type union {
              type string {
                pattern "<.*>|$.*";
              }
              type uint32 {
                range "1 .. 65535";
              }
            }
          }
          leaf transit-delay {
            description "Transit delay (seconds)";
            type union {
              type string {
                pattern "<.*>|$.*";
              }
              type uint32 {
                range "1 .. 65535";
              }
            }
          }
          leaf hello-interval {
            description "Hello interval (seconds)";
            type union {
              type string {
                pattern "<.*>|$.*";
              }
              type uint32 {
                range "1 .. 255";
              }
            }
          }
          leaf dead-interval {
            description "Dead interval (seconds)";
            type union {
              type string {
                pattern "<.*>|$.*";
              }
              type uint32 {
                range "1 .. 65535";
              }
            }
          }
          leaf mtu {
            description "Maximum OSPF packet size";
            type union {
              type string {
                pattern "<.*>|$.*";
              }
              type uint32 {
                range "128 .. 65535";
              }
            }
          }
          choice auth {
            case case_1 {
              container authentication {
                uses juniper-ospf-authentication;
              }
            }
            case case_2 {
              container authentication-key {
                description "Authentication key";
                status deprecated;
                leaf keyname {
                  description "Authentication key value";
                  type jt:unreadable;
                }
                leaf key-id {
                  description "Key ID for MD5 authentication";
                  type union {
                    type string {
                      pattern "<.*>|$.*";
                    }
                    type uint32 {
                      range "0 .. 255";
                    }
                  }
                }
              }
            }
          }
          leaf demand-circuit {
            description "Interface functions as a demand circuit";
            type empty;
          }
          leaf flood-reduction {
            description "Enable flood reduction";
            type empty;
          }
          leaf no-neighbor-down-notification {
            description "Don't inform other protocols about neighbor down events";
            type empty;
          }
          leaf ipsec-sa {
            description "IPSec security association name";
            type string {
              length "1 .. 32";
            }
          }
          list topology {
            key name;
            ordered-by user;
            description "Topology specific attributes";
            leaf name {
              description "Topology name";
              type string;
            }
            leaf disable {
              description "Disable this topology";
              type empty;
            }
            leaf metric {
              description "Topology metric";
              type union {
                type string {
                  pattern "<.*>|$.*";
                }
                type uint16 {
                  range "1 .. 65535";
                }
              }
            }
            container bandwidth-based-metrics {
              description "Configure bandwidth based metrics";
              list bandwidth {
                key name;
                description "Bandwidth threshold";
                leaf name {
                  type string;
                }
                leaf metric {
                  description "Metric associated with specified bandwidth";
                  type union {
                    type string {
                      pattern "<.*>|$.*";
                    }
                    type uint16 {
                      range "1 .. 65535";
                    }
                  }
                }
              }
            }
          }
          leaf transmit-interval {
            description "OSPF packet transmit interval (milliseconds)";
            status deprecated;
            type union {
              type string {
                pattern "<.*>|$.*";
              }
              type uint32 {
                range "1 .. 4294967295";
              }
            }
          }
          container bfd-liveness-detection {
            description "Bidirectional Forwarding Detection options";
            leaf version {
              description "BFD protocol version number";
              default "automatic";
              type enumeration {
                enum 0 {
                  description "BFD version 0 (deprecated)";
                }
                enum 1 {
                  description "BFD version 1";
                }
                enum automatic {
                  description "Choose BFD version automatically";
                }
              }
            }
            leaf minimum-interval {
              description "Minimum transmit and receive interval";
              units milliseconds;
              type union {
                type string {
                  pattern "<.*>|$.*";
                }
                type uint32 {
                  range "1 .. 255000";
                }
              }
            }
            leaf minimum-transmit-interval {
              description "Minimum transmit interval";
              status deprecated;
              units milliseconds;
              type union {
                type string {
                  pattern "<.*>|$.*";
                }
                type uint32 {
                  range "1 .. 255000";
                }
              }
            }
            leaf minimum-receive-interval {
              description "Minimum receive interval";
              units milliseconds;
              type union {
                type string {
                  pattern "<.*>|$.*";
                }
                type uint32 {
                  range "1 .. 255000";
                }
              }
            }
            leaf multiplier {
              description "Detection time multiplier";
              default "3";
              type union {
                type string {
                  pattern "<.*>|$.*";
                }
                type uint32 {
                  range "1 .. 255";
                }
              }
            }
            leaf inline-disable {
              description "Disable inline mode for this BFD session";
              type empty;
            }
            leaf pdu-size {
              description "BFD transport protocol payload size";
              default "24";
              type union {
                type string {
                  pattern "<.*>|$.*";
                }
                type uint32 {
                  range "24 .. 9000";
                }
              }
            }
            choice adaptation-choice {
              case case_1 {
                leaf no-adaptation {
                  description "Disable adaptation";
                  type empty;
                }
              }
            }
            container transmit-interval {
              description "Transmit-interval options";
              leaf minimum-interval {
                description "Minimum transmit interval";
                units milliseconds;
                type union {
                  type string {
                    pattern "<.*>|$.*";
                  }
                  type uint32 {
                    range "1 .. 255000";
                  }
                }
              }
              leaf threshold {
                description "High transmit interval triggering a trap";
                units milliseconds;
                type union {
                  type uint32;
                  type string {
                    pattern "<.*>|$.*";
                  }
                }
              }
            }
            container detection-time {
              description "Detection-time options";
              leaf threshold {
                description "High detection-time triggering a trap";
                units milliseconds;
                type union {
                  type uint32;
                  type string {
                    pattern "<.*>|$.*";
                  }
                }
              }
            }
            container authentication {
              description "Authentication options";
              leaf key-chain {
                description "Key chain name";
                type string;
              }
              leaf algorithm {
                description "Algorithm name";
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
              }
              leaf loose-check {
                description "Verify authentication only if authentication is negotiated";
                type empty;
              }
            }
            container echo {
              description "Echo mode parameters";
              leaf minimum-interval {
                description "Minimum transmit and receive interval";
                units milliseconds;
                type union {
                  type string {
                    pattern "<.*>|$.*";
                  }
                  type uint32 {
                    range "100 .. 255000";
                  }
                }
              }
            }
            container echo-lite {
              description "Echo-lite more parameters";
              leaf minimum-interval {
                description "Minimum transmit and receive interval";
                units milliseconds;
                type union {
                  type string {
                    pattern "<.*>|$.*";
                  }
                  type uint32 {
                    range "100 .. 255000";
                  }
                }
              }
            }
            leaf full-neighbors-only {
              description "Setup BFD sessions only to Full neighbors";
              type empty;
            }
            leaf holddown-interval {
              description "Time to hold the session-UP notification to the client";
              units milliseconds;
              type union {
                type string {
                  pattern "<.*>|$.*";
                }
                type uint32 {
                  range "0 .. 255000";
                }
              }
            }
          }
          leaf dynamic-neighbors {
            description "Learn neighbors dynamically on a p2mp interface";
            type empty;
          }
          leaf no-advertise-adjacency-segment {
            description "Do not advertise an adjacency segment for this interface";
            type empty;
          }
          list neighbor {
            key name;
            ordered-by user;
            description "NBMA neighbor";
            leaf name {
              description "Address of neighbor";
              type jt:ipaddr;
            }
            leaf eligible {
              description "Eligible to be DR on an NBMA network";
              type empty;
            }
          }
          leaf poll-interval {
            description "Poll interval for NBMA interfaces";
            type union {
              type string {
                pattern "<.*>|$.*";
              }
              type uint32 {
                range "1 .. 65535";
              }
            }
          }
          leaf no-interface-state-traps {
            description "Do not send interface state change traps";
            type empty;
          }
          leaf strict-bfd {
            description "Enable strict bfd over this interface";
            type empty;
          }
          container post-convergence-lfa {
            presence "enable post-convergence-lfa";
            description "Protect interface using post-convergence backup path";
            container node-protection {
              presence "enable node-protection";
              description "Compute backup path assuming node failure";
              leaf cost {
                description "Cost for node protection";
                type union {
                  type string {
                    pattern "<.*>|$.*";
                  }
                  type uint16 {
                    range "1 .. 65535";
                  }
                }
              }
            }
            leaf srlg-protection {
              description "Compute backup path assuming SRLG failure";
              type empty;
            }
            leaf fate-sharing-protection {
              description "Compute backup path assuming fate-sharing group failure";
              type empty;
            }
          }
          leaf te-metric {
            description "Traffic engineering metric";
            type union {
              type string {
                pattern "<.*>|$.*";
              }
              type uint32 {
                range "1 .. 4294967295";
              }
            }
          }
          container ldp-synchronization {
            description "Advertise maximum metric until LDP is operational";
            presence "enable ldp-synchronization";
            uses ldp-sync-obj;
          }
          container ipv4-adjacency-segment {
            description "Configure ipv4 adjacency segment";
            container protected {
              description "Adjacency SID is eligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
            container unprotected {
              description "Adjacency SID uneligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
          }
          list lan-neighbor {
            key name;
            ordered-by user;
            description "Configuration specific to a LAN neighbor";
            leaf name {
              description "Address of neighbor";
              type jt:ipaddr;
            }
            container ipv4-adjacency-segment {
              description "Configure ipv4 adjacency segment";
              container protected {
                description "Adjacency SID is eligible for protection";
                choice adjsid-type {
                  case case_1 {
                    container index {
                      description "Adjacency SID indexed from SRGB";
                      leaf index-number {
                        type union {
                          type string {
                            pattern "<.*>|$.*";
                          }
                          type uint32 {
                            range "0 .. 199999";
                          }
                        }
                      }
                    }
                  }
                  case case_2 {
                    leaf label {
                      description "Adjacency SID from static label pool";
                      type union {
                        type string {
                          pattern "<.*>|$.*";
                        }
                        type uint32 {
                          range "16 .. 1048575";
                        }
                      }
                    }
                  }
                  case case_3 {
                    leaf dynamic {
                      description "Dynamically allocate an adjacency segment";
                      type empty;
                    }
                  }
                }
              }
              container unprotected {
                description "Adjacency SID uneligible for protection";
                choice adjsid-type {
                  case case_1 {
                    container index {
                      description "Adjacency SID indexed from SRGB";
                      leaf index-number {
                        type union {
                          type string {
                            pattern "<.*>|$.*";
                          }
                          type uint32 {
                            range "0 .. 199999";
                          }
                        }
                      }
                    }
                  }
                  case case_2 {
                    leaf label {
                      description "Adjacency SID from static label pool";
                      type union {
                        type string {
                          pattern "<.*>|$.*";
                        }
                        type uint32 {
                          range "16 .. 1048575";
                        }
                      }
                    }
                  }
                  case case_3 {
                    leaf dynamic {
                      description "Dynamically allocate an adjacency segment";
                      type empty;
                    }
                  }
                }
              }
            }
          }
          leaf delay-metric {
            description "Delay metric";
            units microseconds;
            type union {
              type string {
                pattern "<.*>|$.*";
              }
              type uint32 {
                range "0 .. 16777215";
              }
            }
          }
          container delay-measurement {
            presence "enable delay-measurement";
            description "Enable delay measurement";
            leaf probe-interval {
              description "Probe interval";
              units seconds;
              type union {
                type string {
                  pattern "<.*>|$.*";
                }
                type uint32 {
                  range "1 .. 255";
                }
              }
            }
            leaf probe-count {
              description "Probe count";
              type union {
                type string {
                  pattern "<.*>|$.*";
                }
                type uint32 {
                  range "1 .. 15";
                }
              }
            }
            container advertisement {
              description "Delay advertisement";
              container periodic {
                description "Periodic advertisement parameters";
                leaf threshold {
                  description "Threshold";
                  units percentage;
                  type union {
                    type string {
                      pattern "<.*>|$.*";
                    }
                    type uint32 {
                      range "0 .. 100";
                    }
                  }
                }
                leaf interval {
                  description "Interval";
                  units seconds;
                  type union {
                    type string {
                      pattern "<.*>|$.*";
                    }
                    type uint32 {
                      range "30 .. 3600";
                    }
                  }
                }
              }
              container accelerated {
                presence "enable accelerated";
                description "Accelerated advertisement parameters";
                leaf threshold {
                  description "Threshold";
                  units percentage;
                  type union {
                    type string {
                      pattern "<.*>|$.*";
                    }
                    type uint32 {
                      range "0 .. 100";
                    }
                  }
                }
              }
            }
          }
          container application-specific {
            description "Advertise application-specific TE attributes";
            list attribute-group {
              key name;
              ordered-by user;
              description "Link attribute group name";
              max-elements 1;
              leaf name {
                description "Link attribute group name";
                type string;
              }
              leaf te-metric {
                description "Traffic engineering metric for this attribute group";
                type union {
                  type string {
                    pattern "<.*>|$.*";
                  }
                  type uint32 {
                    range "1 .. 4294967295";
                  }
                }
              }
              leaf-list admin-group {
                ordered-by user;
                description "Administrative groups for this attribute-group";
                type string;
                max-elements 16;
              }
              leaf delay-metric {
                description "Delay metric for this attribute-group";
                units microseconds;
                type union {
                  type string {
                    pattern "<.*>|$.*";
                  }
                  type uint32 {
                    range "0 .. 16777215";
                  }
                }
              }
              leaf advertise-interface-delay {
                description "Use interface specific static/dynamic delay values as applicable in ASLA Sub-TLVs";
                type empty;
              }
              container application {
                description "Standard Applications part of this attribute-group";
                leaf flex-algorithm {
                  description "Set X flag in standard application bit mask";
                  type empty;
                }
              }
            }
          }
        }
        leaf no-context-identifier-advertisement {
          description "Disable context identifier advertisments in this area";
          type empty;
        }
        list peer-interface {
          key name;
          ordered-by user;
          description "Configuration for peer interface";
          leaf name {
            description "Name of peer interface";
            type string;
          }
          choice enable-disable {
            case case_1 {
              leaf disable {
                description "Disable OSPF on this control peer";
                type empty;
              }
            }
          }
          leaf retransmit-interval {
            description "Retransmission interval (seconds)";
            type union {
              type string {
                pattern "<.*>|$.*";
              }
              type uint32 {
                range "1 .. 65535";
              }
            }
          }
          leaf transit-delay {
            description "Transit delay (seconds)";
            type union {
              type string {
                pattern "<.*>|$.*";
              }
              type uint32 {
                range "1 .. 65535";
              }
            }
          }
          leaf hello-interval {
            description "Hello interval (seconds)";
            type union {
              type string {
                pattern "<.*>|$.*";
              }
              type uint32 {
                range "1 .. 255";
              }
            }
          }
          leaf dead-interval {
            description "Dead interval (seconds)";
            type union {
              type string {
                pattern "<.*>|$.*";
              }
              type uint32 {
                range "1 .. 65535";
              }
            }
          }
          leaf mtu {
            description "Maximum OSPF packet size";
            type union {
              type string {
                pattern "<.*>|$.*";
              }
              type uint32 {
                range "128 .. 65535";
              }
            }
          }
          choice auth {
            case case_1 {
              container authentication {
                uses juniper-ospf-authentication;
              }
            }
            case case_2 {
              container authentication-key {
                description "Authentication key";
                status deprecated;
                leaf keyname {
                  description "Authentication key value";
                  type jt:unreadable;
                }
                leaf key-id {
                  description "Key ID for MD5 authentication";
                  type union {
                    type string {
                      pattern "<.*>|$.*";
                    }
                    type uint32 {
                      range "0 .. 255";
                    }
                  }
                }
              }
            }
          }
          leaf demand-circuit {
            description "Interface functions as a demand circuit";
            type empty;
          }
          leaf flood-reduction {
            description "Enable flood reduction";
            type empty;
          }
          leaf no-neighbor-down-notification {
            description "Don't inform other protocols about neighbor down events";
            type empty;
          }
        }
        leaf no-source-packet-routing {
          description "Disable SPRING in this area";
          type empty;
        }
        list context-identifier {
          key name;
          ordered-by user;
          description "Configure context identifier in support of edge protection";
          leaf name {
            description "Context identifier";
            type jt:ipv4addr;
          }
        }
        list label-switched-path {
          key name;
          ordered-by user;
          description "Configuration for advertisement of a label-switched path";
          leaf name {
            description "Name of label-switched path to be advertised";
            type string {
              length "1 .. 64";
            }
          }
          choice enable-disable {
            case case_1 {
              leaf disable {
                description "Disable OSPF on this label-switched path";
                type empty;
              }
            }
          }
          leaf metric {
            description "Interface metric";
            type union {
              type string {
                pattern "<.*>|$.*";
              }
              type uint16 {
                range "1 .. 65535";
              }
            }
          }
          list topology {
            key name;
            ordered-by user;
            description "Topology specific attributes";
            leaf name {
              description "Topology name";
              type string;
            }
            leaf disable {
              description "Disable this topology";
              type empty;
            }
            leaf metric {
              description "Topology metric";
              type union {
                type string {
                  pattern "<.*>|$.*";
                }
                type uint16 {
                  range "1 .. 65535";
                }
              }
            }
            container bandwidth-based-metrics {
              description "Configure bandwidth based metrics";
              list bandwidth {
                key name;
                description "Bandwidth threshold";
                leaf name {
                  type string;
                }
                leaf metric {
                  description "Metric associated with specified bandwidth";
                  type union {
                    type string {
                      pattern "<.*>|$.*";
                    }
                    type uint16 {
                      range "1 .. 65535";
                    }
                  }
                }
              }
            }
          }
        }
      }
      choice enable-disable {
        case case_1 {
          leaf disable {
            description "Disable OSPF";
            type empty;
          }
        }
      }
      container traceoptions {
        description "Trace options for OSPF";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum spf {
                description "Trace SPF calculations";
              }
              enum error {
                description "Trace errored packets";
              }
              enum event {
                description "Trace OSPF state machine events";
              }
              enum packet-dump {
                description "Dump the contents of selected packet types";
              }
              enum flooding {
                description "Trace LSA flooding";
              }
              enum lsa-analysis {
                description "Trace LSA analysis";
              }
              enum packets {
                description "Trace all OSPF packets";
              }
              enum hello {
                description "Trace hello packets";
              }
              enum database-description {
                description "Trace database description packets";
              }
              enum lsa-request {
                description "Trace LSA request packets";
              }
              enum lsa-update {
                description "Trace LSA update packets";
              }
              enum lsa-ack {
                description "Trace LSA acknowledgment packets";
              }
              enum ldp-synchronization {
                description "Trace synchronization between OSPF and LDP";
              }
              enum on-demand {
                description "Trace demand circuit extensions";
              }
              enum nsr-synchronization {
                description "Trace NSR synchronization events";
              }
              enum graceful-restart {
                description "Trace graceful restart";
              }
              enum restart-signaling {
                description "Trace restart signaling";
              }
              enum traffic-statistics {
                description "Trace Segment Routing Traffic Statistics";
              }
              enum backup-spf {
                description "Trace backup SPF (LFA) specific events";
              }
              enum source-packet-routing {
                description "Trace source packet routing (SPRING) events";
              }
              enum post-convergence-lfa {
                description "Trace post-convergence-lfa related events";
              }
              enum flex-algorithm {
                description "Trace flex-algorithm related events";
              }
              enum rmopd {
                description "Trace rmopd interactions";
              }
              enum route {
                description "Trace routing information";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
      leaf prefix-export-limit {
        description "Maximum number of prefixes that can be exported";
        type union {
          type string {
            pattern "<.*>|$.*";
          }
          type uint32 {
            range "0 .. 4294967295";
          }
        }
      }
      container rib-groups {
        description "Routing table groups for importing OSPF routes";
        leaf inet {
          description "Name of the IPv4/v6 routing table group";
          type string;
        }
        leaf inet3 {
          description "Name of the IPv4/v6 inet.3 routing table group";
          type string;
        }
      }
      leaf job-stats {
        description "Collect job statistics";
        type empty;
      }
      container overload {
        presence "enable overload";
        description "Set the overload mode (repel transit traffic)";
        leaf timeout {
          description "Time after which overload mode is reset";
          units seconds;
          type union {
            type string {
              pattern "<.*>|$.*";
            }
            type uint32 {
              range "60 .. 3600";
            }
          }
        }
        leaf allow-route-leaking {
          description "Allow routes to be leaked when overload is configured";
          type empty;
        }
        leaf stub-network {
          description "Advertise Stub Network with maximum metric";
          type empty;
        }
        leaf intra-area-prefix {
          description "Advertise Intra Area Prefix with maximum metric";
          type empty;
        }
        leaf as-external {
          description "Advertise As External with maximum usable metric";
          type empty;
        }
      }
      container database-protection {
        presence "enable database-protection";
        description "Configure database protection attributes";
        leaf maximum-lsa {
          description "Maximum allowed non self-generated LSAs";
          type union {
            type string {
              pattern "<.*>|$.*";
            }
            type uint32 {
              range "1 .. 1000000";
            }
          }
        }
        leaf warning-only {
          description "Emit only a warning when LSA maximum limit is exceeded";
          type empty;
        }
        leaf warning-threshold {
          description "Percentage of LSA maximum above which to trigger warning";
          units percent;
          type union {
            type string {
              pattern "<.*>|$.*";
            }
            type uint8 {
              range "30 .. 100";
            }
          }
        }
        leaf ignore-count {
          description "Maximum number of times to go into ignore state";
          type union {
            type string {
              pattern "<.*>|$.*";
            }
            type uint8 {
              range "1 .. 32";
            }
          }
        }
        leaf ignore-time {
          description "Time to stay in ignore state and ignore all neighbors";
          units seconds;
          type union {
            type string {
              pattern "<.*>|$.*";
            }
            type uint16 {
              range "30 .. 3600";
            }
          }
        }
        leaf reset-time {
          description "Time after which the ignore count gets reset to zero";
          units seconds;
          type union {
            type string {
              pattern "<.*>|$.*";
            }
            type uint32 {
              range "60 .. 86400";
            }
          }
        }
      }
      container graceful-restart {
        description "Configure graceful restart attributes";
        choice enable-disable {
          case case_1 {
            leaf disable {
              description "Disable OSPF graceful restart capability";
              type empty;
            }
          }
        }
        leaf restart-duration {
          description "Time for all neighbors to become full";
          units seconds;
          type union {
            type string {
              pattern "<.*>|$.*";
            }
            type uint32 {
              range "1 .. 3600";
            }
          }
        }
        leaf notify-duration {
          description "Time to send all max-aged grace LSAs";
          units seconds;
          type union {
            type string {
              pattern "<.*>|$.*";
            }
            type uint32 {
              range "1 .. 3600";
            }
          }
        }
        container helper-disable {
          presence "enable helper-disable";
          description "Disable graceful restart helper capability";
          choice disable-choices {
            case case_1 {
              leaf standard {
                description "Disable helper-mode for rfc3623 based GR";
                type empty;
              }
            }
            case case_2 {
              leaf restart-signaling {
                description "Disable helper mode for restart-signaling ";
                type empty;
              }
            }
            case case_3 {
              leaf both {
                description "Disable helper mode for both the types of GR";
                type empty;
              }
            }
          }
        }
        leaf no-strict-lsa-checking {
          description "Do not abort graceful helper mode upon LSA changes";
          type empty;
        }
      }
      leaf route-type-community {
        description "Specify BGP extended community value to encode OSPF route type";
        type enumeration {
          enum iana {
            description "BGP extended community value used is 0x0306";
          }
          enum vendor {
            description "Vendor BGP extended community value used is 0x8000";
          }
        }
      }
      container domain-id {
        description "Configure domain ID";
        choice domain_id_or_disable {
          case case_1 {
            leaf domain-id {
              description "Domain ID";
              type string;
            }
          }
          case case_2 {
            leaf disable {
              description "Disable domain ID";
              type empty;
            }
          }
        }
      }
      choice domain_vpn_tag_or_disable {
        case case_1 {
          leaf domain-vpn-tag {
            description "Domain VPN tag for external LSA";
            type union {
              type string {
                pattern "<.*>|$.*";
              }
              type uint32 {
                range "0 .. 4294967295";
              }
            }
          }
        }
        case case_2 {
          leaf no-domain-vpn-tag {
            description "Disable domain VPN tag";
            type empty;
          }
        }
      }
      leaf preference {
        description "Preference of internal routes";
        type union {
          type uint32;
          type string {
            pattern "<.*>|$.*";
          }
        }
      }
      leaf external-preference {
        description "Preference of external routes";
        type union {
          type uint32;
          type string {
            pattern "<.*>|$.*";
          }
        }
      }
      leaf labeled-preference {
        description "Preference of labeled routes";
        type union {
          type uint32;
          type string {
            pattern "<.*>|$.*";
          }
        }
      }
      leaf-list export {
        ordered-by user;
        description "Export policy";
        type jt:policy-algebra;
      }
      leaf-list import {
        ordered-by user;
        description "Import policy (for external routes or setting priority)";
        type jt:policy-algebra;
      }
      leaf reference-bandwidth {
        description "Bandwidth for calculating metric defaults";
        type string;
      }
      leaf lsa-refresh-interval {
        description "LSA refresh interval (minutes)";
        default "50";
        type union {
          type string {
            pattern "<.*>|$.*";
          }
          type uint32 {
            range "25 .. 50";
          }
        }
      }
      leaf spf-delay {
        description "Time to wait before running an SPF";
        status deprecated;
        units milliseconds;
        type union {
          type string {
            pattern "<.*>|$.*";
          }
          type uint32 {
            range "50 .. 8000";
          }
        }
      }
      leaf no-rfc-1583 {
        description "Disable RFC1583 compatibility";
        type empty;
      }
      leaf forwarding-address-to-broadcast {
        description "Set forwarding address in Type 5 LSA in broadcast network";
        type empty;
      }
      choice nssa-abr-option {
        case case_1 {
          leaf no-nssa-abr {
            description "Disable full NSSA functionality at ABR";
            type empty;
          }
        }
      }
      container sham-link {
        presence "enable sham-link";
        description "Configure parameters for sham links";
        leaf local {
          description "Local sham link endpoint address";
          type jt:ipaddr;
        }
        leaf no-advertise-local {
          description "Don't advertise local sham link endpoint as stub in router LSA";
          status deprecated;
          type empty;
        }
      }
    }
    list topology {
      key name;
      ordered-by user;
      description "Topology parameters";
      leaf name {
        description "Topology name";
        type string;
      }
      leaf disable {
        description "Disable this topology";
        type empty;
      }
      leaf topology-id {
        description "Topology identifier";
        type union {
          type string {
            pattern "<.*>|$.*";
          }
          type uint8 {
            range "32 .. 127";
          }
        }
      }
      leaf overload {
        description "Set the overload mode (repel transit traffic)";
        type empty;
      }
      leaf rib-group {
        description "Routing table group for importing routes";
        type string;
      }
      container spf-options {
        description "Configure options for SPF";
        container microloop-avoidance {
          description "Configure microloop avoidance mechanism";
          container post-convergence-path {
            presence "enable post-convergence-path";
            description "Temporarily install post-convergence path for routes potentially affected by microloops";
            leaf delay {
              description "Time after which temporary post-convergence paths are removed";
              units milliseconds;
              type union {
                type string {
                  pattern "<.*>|$.*";
                }
                type uint32 {
                  range "500 .. 60000";
                }
              }
            }
            leaf maximum-labels {
              description "Maximum number of labels installed for post-convergence paths";
              type union {
                type string {
                  pattern "<.*>|$.*";
                }
                type uint32 {
                  range "2 .. 8";
                }
              }
            }
          }
        }
        leaf delay {
          description "Time to wait before running an SPF";
          units milliseconds;
          type union {
            type string {
              pattern "<.*>|$.*";
            }
            type uint32 {
              range "50 .. 8000";
            }
          }
        }
        leaf holddown {
          description "Time to hold down before running an SPF";
          units milliseconds;
          type union {
            type string {
              pattern "<.*>|$.*";
            }
            type uint32 {
              range "2000 .. 20000";
            }
          }
        }
        leaf rapid-runs {
          description "Number of maximum rapid SPF runs before holddown";
          type union {
            type string {
              pattern "<.*>|$.*";
            }
            type uint32 {
              range "1 .. 10";
            }
          }
        }
        leaf no-ignore-our-externals {
          description "Do not ignore self-generated external and NSSA LSAs";
          type empty;
        }
      }
      container backup-spf-options {
        description "Configure options for backup SPF";
        container remote-backup-calculation {
          presence "enable remote-backup-calculation";
          description "Calculate Remote LFA backup nexthops";
          container pq-nodes-nearest-to-source {
            description "PQ nodes selection based upon nearest to source";
            leaf percent {
              description "Selection percentage for nearest to source";
              type union {
                type string {
                  pattern "<.*>|$.*";
                }
                type uint32 {
                  range "10 .. 100";
                }
              }
            }
          }
        }
        container use-post-convergence-lfa {
          presence "enable use-post-convergence-lfa";
          description "Calculate post-convergence backup paths";
          leaf maximum-labels {
            description "Maximum number of labels installed for post-convergence paths";
            type union {
              type string {
                pattern "<.*>|$.*";
              }
              type uint32 {
                range "2 .. 8";
              }
            }
          }
          leaf maximum-backup-paths {
            description "Maximum number of equal-cost post-convergence paths installed";
            type union {
              type string {
                pattern "<.*>|$.*";
              }
              type uint32 {
                range "1 .. 8";
              }
            }
          }
        }
        leaf use-source-packet-routing {
          description "Use spring backup paths for inet.0 routes";
          type empty;
        }
        leaf disable {
          description "Do not run backup SPF";
          type empty;
        }
        leaf no-install {
          description "Do not install backup nexthops into the RIB";
          type empty;
        }
        leaf downstream-paths-only {
          description "Use only downstream backup paths";
          type empty;
        }
        container per-prefix-calculation {
          description "Calculate backup nexthops for non-best prefix originators";
          leaf stubs {
            description "Per prefix calculation for stubs only";
            type empty;
          }
          leaf summary {
            description "Per prefix calculation for summary originators only";
            type empty;
          }
          leaf externals {
            description "Per prefix calculation for externals";
            type empty;
          }
          leaf all {
            description "Per prefix calculation for all";
            type empty;
          }
        }
        leaf node-link-degradation {
          description "Degrade to link protection when nodelink protection not available";
          type empty;
        }
      }
      leaf prefix-export-limit {
        description "Maximum number of prefixes that can be exported";
        type union {
          type string {
            pattern "<.*>|$.*";
          }
          type uint32 {
            range "0 .. 4294967295";
          }
        }
      }
    }
    container spf-options {
      description "Configure options for SPF";
      container microloop-avoidance {
        description "Configure microloop avoidance mechanism";
        container post-convergence-path {
          presence "enable post-convergence-path";
          description "Temporarily install post-convergence path for routes potentially affected by microloops";
          leaf delay {
            description "Time after which temporary post-convergence paths are removed";
            units milliseconds;
            type union {
              type string {
                pattern "<.*>|$.*";
              }
              type uint32 {
                range "500 .. 60000";
              }
            }
          }
          leaf maximum-labels {
            description "Maximum number of labels installed for post-convergence paths";
            type union {
              type string {
                pattern "<.*>|$.*";
              }
              type uint32 {
                range "2 .. 8";
              }
            }
          }
        }
      }
      leaf delay {
        description "Time to wait before running an SPF";
        units milliseconds;
        type union {
          type string {
            pattern "<.*>|$.*";
          }
          type uint32 {
            range "50 .. 8000";
          }
        }
      }
      leaf holddown {
        description "Time to hold down before running an SPF";
        units milliseconds;
        type union {
          type string {
            pattern "<.*>|$.*";
          }
          type uint32 {
            range "2000 .. 20000";
          }
        }
      }
      leaf rapid-runs {
        description "Number of maximum rapid SPF runs before holddown";
        type union {
          type string {
            pattern "<.*>|$.*";
          }
          type uint32 {
            range "1 .. 10";
          }
        }
      }
      leaf no-ignore-our-externals {
        description "Do not ignore self-generated external and NSSA LSAs";
        type empty;
      }
    }
    container backup-spf-options {
      description "Configure options for backup SPF";
      container remote-backup-calculation {
        presence "enable remote-backup-calculation";
        description "Calculate Remote LFA backup nexthops";
        container pq-nodes-nearest-to-source {
          description "PQ nodes selection based upon nearest to source";
          leaf percent {
            description "Selection percentage for nearest to source";
            type union {
              type string {
                pattern "<.*>|$.*";
              }
              type uint32 {
                range "10 .. 100";
              }
            }
          }
        }
      }
      container use-post-convergence-lfa {
        presence "enable use-post-convergence-lfa";
        description "Calculate post-convergence backup paths";
        leaf maximum-labels {
          description "Maximum number of labels installed for post-convergence paths";
          type union {
            type string {
              pattern "<.*>|$.*";
            }
            type uint32 {
              range "2 .. 8";
            }
          }
        }
        leaf maximum-backup-paths {
          description "Maximum number of equal-cost post-convergence paths installed";
          type union {
            type string {
              pattern "<.*>|$.*";
            }
            type uint32 {
              range "1 .. 8";
            }
          }
        }
      }
      leaf use-source-packet-routing {
        description "Use spring backup paths for inet.0 routes";
        type empty;
      }
      leaf disable {
        description "Do not run backup SPF";
        type empty;
      }
      leaf no-install {
        description "Do not install backup nexthops into the RIB";
        type empty;
      }
      leaf downstream-paths-only {
        description "Use only downstream backup paths";
        type empty;
      }
      container per-prefix-calculation {
        description "Calculate backup nexthops for non-best prefix originators";
        leaf stubs {
          description "Per prefix calculation for stubs only";
          type empty;
        }
        leaf summary {
          description "Per prefix calculation for summary originators only";
          type empty;
        }
        leaf externals {
          description "Per prefix calculation for externals";
          type empty;
        }
        leaf all {
          description "Per prefix calculation for all";
          type empty;
        }
      }
      leaf node-link-degradation {
        description "Degrade to link protection when nodelink protection not available";
        type empty;
      }
    }
    container traffic-engineering {
      presence "enable traffic-engineering";
      description "Configure traffic engineering attributes";
      leaf no-topology {
        description "Disable dissemination of TE link-state topology information";
        type empty;
      }
      leaf multicast-rpf-routes {
        description "Install routes for multicast RPF checks into inet.2";
        type empty;
      }
      leaf l3-unicast-topology {
        description "Download IGP topology into TED";
        type empty;
      }
      container ignore-lsp-metrics {
        presence "enable ignore-lsp-metrics";
        description "Ignore label-switched path metrics when doing shortcuts";
        leaf unconfigured-only {
          description "Ignore lsp metrics for unconfigured only";
          type empty;
        }
      }
      container shortcuts {
        presence "enable shortcuts";
        description "Use label-switched paths as next hops, if possible";
        leaf ignore-lsp-metrics {
          description "Ignore label-switched path metrics when doing shortcuts";
          status deprecated;
          type empty;
        }
        leaf lsp-metric-into-summary {
          description "Advertise LSP metric into summary LSAs";
          type empty;
        }
        list family {
          key name;
          ordered-by user;
          description "Address family specific traffic-engineering attributes";
          leaf name {
            type enumeration {
              enum inet {
                description "IPv4 family";
              }
              enum inet-mpls {
                description "IPv4-MPLS family";
              }
            }
          }
        }
      }
      leaf advertise-unnumbered-interfaces {
        description "Advertise unnumbered interfaces";
        type empty;
      }
      leaf credibility-protocol-preference {
        description "TED protocol credibility follows protocol preference";
        type empty;
      }
      container advertisement {
        description "Advertise TE parameters even if RSVP is not turned on";
        leaf always {
          description "Advertise TE parameters in TE LSAs";
          type empty;
        }
      }
      container tunnel-source-protocol {
        description "Protocols from which to pick label-switched paths";
        container rsvp {
          presence "enable rsvp";
          description "Pick label-switched paths from rsvp";
          leaf preference {
            description "Preference for label-switched paths from this protocol";
            type union {
              type string {
                pattern "<.*>|$.*";
              }
              type uint32 {
                range "1 .. 255";
              }
            }
          }
        }
        container spring-te {
          presence "enable spring-te";
          description "Pick label-switched paths from spring-te";
          leaf preference {
            description "Preference for label-switched paths from this protocol";
            type union {
              type string {
                pattern "<.*>|$.*";
              }
              type uint32 {
                range "1 .. 255";
              }
            }
          }
        }
      }
    }
    container source-packet-routing {
      presence "enable source-packet-routing";
      description "Enable source packet routing (SPRING)";
      container adjacency-segment {
        description "Attributes for adjacency segments in spring";
        leaf hold-time {
          description "Retain time of Adjacency segment after isolating from an interface";
          type union {
            type string {
              pattern "<.*>|$.*";
            }
            type uint32 {
              range "180000 .. 900000";
            }
          }
        }
      }
      leaf-list prefix-segment {
        ordered-by user;
        description "Prefix Segment policy";
        type jt:policy-algebra;
      }
      leaf explicit-null {
        description "Set E and P bits in all Prefix SID advertisements";
        type empty;
      }
      container node-segment {
        presence "enable node-segment";
        description "Enable support for Node segments in SPRING";
        leaf ipv4-index {
          description "Set ipv4 node segment index";
          type union {
            type string {
              pattern "<.*>|$.*";
            }
            type uint32 {
              range "0 .. 199999";
            }
          }
        }
        leaf index-range {
          description "Set range of node segment indices allowed";
          type union {
            type string {
              pattern "<.*>|$.*";
            }
            type uint32 {
              range "32 .. 16385";
            }
          }
        }
      }
      container srgb {
        description "Set the SRGB global block in SPRING";
        leaf start-label {
          description "Start range for SRGB label block";
          type union {
            type string {
              pattern "<.*>|$.*";
            }
            type uint32;
          }
        }
        leaf index-range {
          description "Index to the SRGB start label block";
          type union {
            type string {
              pattern "<.*>|$.*";
            }
            type uint32;
          }
        }
      }
      leaf mapping-server {
        description "Mapping server name";
        type string;
      }
      leaf install-prefix-sid-for-best-route {
        description "For best route install a exact prefix sid route";
        type empty;
      }
      leaf ldp-stitching {
        description "Enable SR to LDP stitching";
        type empty;
      }
      leaf-list flex-algorithm {
        description "Flex-algorithms we would like to participate in";
        type union {
          type string {
            pattern "<.*>|$.*";
          }
          type uint32 {
            range "128 .. 255";
          }
        }
        max-elements 16;
      }
      leaf strict-asla-based-flex-algorithm {
        description "Flex-Algorithm to ignore links not having ASLA sub-TLVs";
        type empty;
      }
      container sensor-based-stats {
        description "Configure sensor based stats in SPRING";
        container per-interface-per-member-link {
          description "Configure sensor based stats per nexthop";
          leaf ingress {
            description "Enable sensor based stats on ingress interface";
            type empty;
          }
          leaf egress {
            description "Enable sensor based stats on egress interface";
            type empty;
          }
        }
        container per-sid {
          description "Configure sensor based stats per spring route";
          leaf ingress {
            description "Enable sensor based stats for per-sid ingress accounting";
            type empty;
          }
          leaf egress {
            description "Enable sensor based stats for IP-MPLS egress accounting";
            type empty;
          }
        }
      }
    }
    list area {
      key name;
      ordered-by user;
      description "Configure an OSPF area";
      leaf name {
        description "Area ID";
        type jt:areaid;
      }
      choice stub-option {
        case case_1 {
          container stub {
            presence "enable stub";
            description "Configure a stub area";
            leaf default-metric {
              description "Metric for the default route in this stub area";
              type union {
                type string {
                  pattern "<.*>|$.*";
                }
                type uint32 {
                  range "1 .. 16777215";
                }
              }
            }
            choice summaries-choice {
              leaf summaries {
                description "Flood summary LSAs into this stub area";
                type empty;
              }
              leaf no-summaries {
                description "Don't flood summary LSAs into this stub area";
                type empty;
              }
            }
          }
        }
        case case_2 {
          container nssa {
            presence "enable nssa";
            description "Configure a not-so-stubby area";
            container default-lsa {
              presence "enable default-lsa";
              description "Configure a default LSA";
              leaf default-metric {
                description "Metric for the default route in this area";
                type union {
                  type string {
                    pattern "<.*>|$.*";
                  }
                  type uint32 {
                    range "1 .. 16777215";
                  }
                }
              }
              leaf metric-type {
                description "External metric type for the default type 7 LSA";
                type union {
                  type string {
                    pattern "<.*>|$.*";
                  }
                  type uint32 {
                    range "1 .. 2";
                  }
                }
              }
              leaf type-7 {
                description "Flood type 7 default LSA if no-summaries is configured";
                type empty;
              }
            }
            leaf default-metric {
              description "Metric for the default route in this area";
              status deprecated;
              type union {
                type string {
                  pattern "<.*>|$.*";
                }
                type uint32 {
                  range "1 .. 16777215";
                }
              }
            }
            leaf metric-type {
              description "External metric type for the default type 7 LSA";
              status deprecated;
              type union {
                type string {
                  pattern "<.*>|$.*";
                }
                type uint32 {
                  range "1 .. 2";
                }
              }
            }
            choice summaries-choice {
              leaf summaries {
                description "Flood summary LSAs into this NSSA area";
                type empty;
              }
              leaf no-summaries {
                description "Don't flood summary LSAs into this NSSA area";
                type empty;
              }
            }
            list area-range {
              key name;
              ordered-by user;
              description "Configure NSSA area ranges";
              leaf name {
                description "Range to summarize NSSA routes in this area";
                type jt:ipprefix;
              }
              leaf restrict {
                description "Restrict advertisement of this area range";
                type empty;
              }
              leaf exact {
                description "Enforce exact match for advertisement of this area range";
                type empty;
              }
              container override-metric {
                presence "enable override-metric";
                description "Override the dynamic metric for this area-range";
                leaf metric {
                  description "Metric value";
                  type union {
                    type string {
                      pattern "<.*>|$.*";
                    }
                    type uint32 {
                      range "1 .. 16777215";
                    }
                  }
                }
                leaf metric-type {
                  description "Set the metric type for the override metric";
                  default "1";
                  type union {
                    type string {
                      pattern "<.*>|$.*";
                    }
                    type uint32 {
                      range "1 .. 2";
                    }
                  }
                }
              }
            }
          }
        }
      }
      list area-range {
        key name;
        ordered-by user;
        description "Configure area ranges";
        leaf name {
          description "Range to summarize routes in this area";
          type jt:ipprefix;
        }
        leaf restrict {
          description "Restrict advertisement of this area range";
          type empty;
        }
        leaf exact {
          description "Enforce exact match for advertisement of this area range";
          type empty;
        }
        leaf override-metric {
          description "Override the dynamic metric for this area-range";
          type union {
            type string {
              pattern "<.*>|$.*";
            }
            type uint32 {
              range "1 .. 16777215";
            }
          }
        }
      }
      leaf-list network-summary-export {
        ordered-by user;
        description "Export policy for Type 3 Summary LSAs";
        type jt:policy-algebra;
      }
      leaf-list network-summary-import {
        ordered-by user;
        description "Import policy for Type 3 Summary LSAs";
        type jt:policy-algebra;
      }
      leaf-list inter-area-prefix-export {
        ordered-by user;
        description "Export policy for Inter Area Prefix LSAs";
        type jt:policy-algebra;
      }
      leaf-list inter-area-prefix-import {
        ordered-by user;
        description "Import policy for Inter Area Prefix LSAs";
        type jt:policy-algebra;
      }
      leaf authentication-type {
        description "Authentication type";
        status deprecated;
        type enumeration {
          enum none {
            description "No authentication";
            status deprecated;
          }
          enum simple {
            description "Simple password authentication";
            status deprecated;
          }
          enum md5 {
            description "MD5 authentication";
            status deprecated;
          }
        }
      }
      list virtual-link {
        key "neighbor-id transit-area";
        ordered-by user;
        description "Configure virtual links";
        leaf neighbor-id {
          description "Router ID of a virtual neighbor";
          type jt:ipv4addr;
        }
        leaf transit-area {
          description "Transit area in common with virtual neighbor";
          type jt:areaid;
        }
        choice enable-disable {
          case case_1 {
            leaf disable {
              description "Disable this virtual link";
              type empty;
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
        leaf ipsec-sa {
          description "IPSec security association name";
          type string {
            length "1 .. 32";
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
      list sham-link-remote {
        key name;
        ordered-by user;
        description "Configure parameters for remote sham link endpoint";
        leaf name {
          description "Remote sham link endpoint address";
          type jt:ipaddr;
        }
        leaf metric {
          description "Sham link metric";
          type union {
            type string {
              pattern "<.*>|$.*";
            }
            type uint16 {
              range "1 .. 65535";
            }
          }
        }
        leaf ipsec-sa {
          description "IPSec security association name";
          type string {
            length "1 .. 32";
          }
        }
        leaf demand-circuit {
          description "Interface functions as a demand circuit";
          type empty;
        }
        leaf flood-reduction {
          description "Enable flood reduction";
          type empty;
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
      list interface {
        key name;
        ordered-by user;
        description "Include an interface in this area";
        leaf name {
          description "Interface name";
          type union {
            type jt:ipv4addr-or-interface;
            type string {
              pattern "<.*>|$.*";
            }
          }
        }
        choice enable-disable {
          case case_1 {
            leaf disable {
              description "Disable OSPF on this interface";
              type empty;
            }
          }
        }
        leaf interface-type {
          description "Type of interface";
          type enumeration {
            enum nbma {
              description "Nonbroadcast multiaccess";
            }
            enum p2mp {
              description "Point-to-multipoint NBMA";
            }
            enum p2p {
              description "Point-to-point";
            }
            enum p2mp-over-lan {
              description "Point-to-multipoint over LAN mode";
            }
          }
        }
        choice protection-type {
          case case_1 {
            leaf link-protection {
              description "Protect interface from link faults only";
              type empty;
            }
          }
          case case_2 {
            leaf node-link-protection {
              description "Protect interface from both link and node faults";
              type empty;
            }
          }
        }
        leaf no-eligible-backup {
          description "Not eligible to backup traffic from protected interfaces";
          type empty;
        }
        leaf no-eligible-remote-backup {
          description "Not eligible for Remote-LFA backup traffic from protected interfaces";
          type empty;
        }
        container passive {
          presence "enable passive";
          description "Do not run OSPF, but advertise it";
          container traffic-engineering {
            description "Advertise TE link information";
            leaf remote-node-id {
              description "Remote address of the link";
              type jt:ipaddr;
            }
            leaf remote-node-router-id {
              description "TE Router-ID of the remote node";
              type jt:ipv4addr;
            }
          }
        }
        leaf secondary {
          description "Treat interface as secondary";
          type empty;
        }
        leaf own-router-lsa {
          description "Generate a separate router LSA for this interface";
          type empty;
        }
        container bandwidth-based-metrics {
          description "Configure bandwidth based metrics";
          list bandwidth {
            key name;
            description "Bandwidth threshold";
            leaf name {
              type string;
            }
            leaf metric {
              description "Metric associated with specified bandwidth";
              type union {
                type string {
                  pattern "<.*>|$.*";
                }
                type uint16 {
                  range "1 .. 65535";
                }
              }
            }
          }
        }
        leaf metric {
          description "Interface metric";
          type union {
            type string {
              pattern "<.*>|$.*";
            }
            type uint16 {
              range "1 .. 65535";
            }
          }
        }
        leaf priority {
          description "Designated router priority";
          type union {
            type string {
              pattern "<.*>|$.*";
            }
            type uint32 {
              range "0 .. 255";
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
        leaf ipsec-sa {
          description "IPSec security association name";
          type string {
            length "1 .. 32";
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
        leaf transmit-interval {
          description "OSPF packet transmit interval (milliseconds)";
          status deprecated;
          type union {
            type string {
              pattern "<.*>|$.*";
            }
            type uint32 {
              range "1 .. 4294967295";
            }
          }
        }
        container bfd-liveness-detection {
          description "Bidirectional Forwarding Detection options";
          leaf version {
            description "BFD protocol version number";
            default "automatic";
            type enumeration {
              enum 0 {
                description "BFD version 0 (deprecated)";
              }
              enum 1 {
                description "BFD version 1";
              }
              enum automatic {
                description "Choose BFD version automatically";
              }
            }
          }
          leaf minimum-interval {
            description "Minimum transmit and receive interval";
            units milliseconds;
            type union {
              type string {
                pattern "<.*>|$.*";
              }
              type uint32 {
                range "1 .. 255000";
              }
            }
          }
          leaf minimum-transmit-interval {
            description "Minimum transmit interval";
            status deprecated;
            units milliseconds;
            type union {
              type string {
                pattern "<.*>|$.*";
              }
              type uint32 {
                range "1 .. 255000";
              }
            }
          }
          leaf minimum-receive-interval {
            description "Minimum receive interval";
            units milliseconds;
            type union {
              type string {
                pattern "<.*>|$.*";
              }
              type uint32 {
                range "1 .. 255000";
              }
            }
          }
          leaf multiplier {
            description "Detection time multiplier";
            default "3";
            type union {
              type string {
                pattern "<.*>|$.*";
              }
              type uint32 {
                range "1 .. 255";
              }
            }
          }
          leaf inline-disable {
            description "Disable inline mode for this BFD session";
            type empty;
          }
          leaf pdu-size {
            description "BFD transport protocol payload size";
            default "24";
            type union {
              type string {
                pattern "<.*>|$.*";
              }
              type uint32 {
                range "24 .. 9000";
              }
            }
          }
          choice adaptation-choice {
            case case_1 {
              leaf no-adaptation {
                description "Disable adaptation";
                type empty;
              }
            }
          }
          container transmit-interval {
            description "Transmit-interval options";
            leaf minimum-interval {
              description "Minimum transmit interval";
              units milliseconds;
              type union {
                type string {
                  pattern "<.*>|$.*";
                }
                type uint32 {
                  range "1 .. 255000";
                }
              }
            }
            leaf threshold {
              description "High transmit interval triggering a trap";
              units milliseconds;
              type union {
                type uint32;
                type string {
                  pattern "<.*>|$.*";
                }
              }
            }
          }
          container detection-time {
            description "Detection-time options";
            leaf threshold {
              description "High detection-time triggering a trap";
              units milliseconds;
              type union {
                type uint32;
                type string {
                  pattern "<.*>|$.*";
                }
              }
            }
          }
          container authentication {
            description "Authentication options";
            leaf key-chain {
              description "Key chain name";
              type string;
            }
            leaf algorithm {
              description "Algorithm name";
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
            }
            leaf loose-check {
              description "Verify authentication only if authentication is negotiated";
              type empty;
            }
          }
          container echo {
            description "Echo mode parameters";
            leaf minimum-interval {
              description "Minimum transmit and receive interval";
              units milliseconds;
              type union {
                type string {
                  pattern "<.*>|$.*";
                }
                type uint32 {
                  range "100 .. 255000";
                }
              }
            }
          }
          container echo-lite {
            description "Echo-lite more parameters";
            leaf minimum-interval {
              description "Minimum transmit and receive interval";
              units milliseconds;
              type union {
                type string {
                  pattern "<.*>|$.*";
                }
                type uint32 {
                  range "100 .. 255000";
                }
              }
            }
          }
          leaf full-neighbors-only {
            description "Setup BFD sessions only to Full neighbors";
            type empty;
          }
          leaf holddown-interval {
            description "Time to hold the session-UP notification to the client";
            units milliseconds;
            type union {
              type string {
                pattern "<.*>|$.*";
              }
              type uint32 {
                range "0 .. 255000";
              }
            }
          }
        }
        leaf dynamic-neighbors {
          description "Learn neighbors dynamically on a p2mp interface";
          type empty;
        }
        leaf no-advertise-adjacency-segment {
          description "Do not advertise an adjacency segment for this interface";
          type empty;
        }
        list neighbor {
          key name;
          ordered-by user;
          description "NBMA neighbor";
          leaf name {
            description "Address of neighbor";
            type jt:ipaddr;
          }
          leaf eligible {
            description "Eligible to be DR on an NBMA network";
            type empty;
          }
        }
        leaf poll-interval {
          description "Poll interval for NBMA interfaces";
          type union {
            type string {
              pattern "<.*>|$.*";
            }
            type uint32 {
              range "1 .. 65535";
            }
          }
        }
        leaf no-interface-state-traps {
          description "Do not send interface state change traps";
          type empty;
        }
        leaf strict-bfd {
          description "Enable strict bfd over this interface";
          type empty;
        }
        container post-convergence-lfa {
          presence "enable post-convergence-lfa";
          description "Protect interface using post-convergence backup path";
          container node-protection {
            presence "enable node-protection";
            description "Compute backup path assuming node failure";
            leaf cost {
              description "Cost for node protection";
              type union {
                type string {
                  pattern "<.*>|$.*";
                }
                type uint16 {
                  range "1 .. 65535";
                }
              }
            }
          }
          leaf srlg-protection {
            description "Compute backup path assuming SRLG failure";
            type empty;
          }
          leaf fate-sharing-protection {
            description "Compute backup path assuming fate-sharing group failure";
            type empty;
          }
        }
        leaf te-metric {
          description "Traffic engineering metric";
          type union {
            type string {
              pattern "<.*>|$.*";
            }
            type uint32 {
              range "1 .. 4294967295";
            }
          }
        }
        container ldp-synchronization {
          description "Advertise maximum metric until LDP is operational";
          presence "enable ldp-synchronization";
          uses ldp-sync-obj;
        }
        container ipv4-adjacency-segment {
          description "Configure ipv4 adjacency segment";
          container protected {
            description "Adjacency SID is eligible for protection";
            choice adjsid-type {
              case case_1 {
                container index {
                  description "Adjacency SID indexed from SRGB";
                  leaf index-number {
                    type union {
                      type string {
                        pattern "<.*>|$.*";
                      }
                      type uint32 {
                        range "0 .. 199999";
                      }
                    }
                  }
                }
              }
              case case_2 {
                leaf label {
                  description "Adjacency SID from static label pool";
                  type union {
                    type string {
                      pattern "<.*>|$.*";
                    }
                    type uint32 {
                      range "16 .. 1048575";
                    }
                  }
                }
              }
              case case_3 {
                leaf dynamic {
                  description "Dynamically allocate an adjacency segment";
                  type empty;
                }
              }
            }
          }
          container unprotected {
            description "Adjacency SID uneligible for protection";
            choice adjsid-type {
              case case_1 {
                container index {
                  description "Adjacency SID indexed from SRGB";
                  leaf index-number {
                    type union {
                      type string {
                        pattern "<.*>|$.*";
                      }
                      type uint32 {
                        range "0 .. 199999";
                      }
                    }
                  }
                }
              }
              case case_2 {
                leaf label {
                  description "Adjacency SID from static label pool";
                  type union {
                    type string {
                      pattern "<.*>|$.*";
                    }
                    type uint32 {
                      range "16 .. 1048575";
                    }
                  }
                }
              }
              case case_3 {
                leaf dynamic {
                  description "Dynamically allocate an adjacency segment";
                  type empty;
                }
              }
            }
          }
        }
        list lan-neighbor {
          key name;
          ordered-by user;
          description "Configuration specific to a LAN neighbor";
          leaf name {
            description "Address of neighbor";
            type jt:ipaddr;
          }
          container ipv4-adjacency-segment {
            description "Configure ipv4 adjacency segment";
            container protected {
              description "Adjacency SID is eligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
            container unprotected {
              description "Adjacency SID uneligible for protection";
              choice adjsid-type {
                case case_1 {
                  container index {
                    description "Adjacency SID indexed from SRGB";
                    leaf index-number {
                      type union {
                        type string {
                          pattern "<.*>|$.*";
                        }
                        type uint32 {
                          range "0 .. 199999";
                        }
                      }
                    }
                  }
                }
                case case_2 {
                  leaf label {
                    description "Adjacency SID from static label pool";
                    type union {
                      type string {
                        pattern "<.*>|$.*";
                      }
                      type uint32 {
                        range "16 .. 1048575";
                      }
                    }
                  }
                }
                case case_3 {
                  leaf dynamic {
                    description "Dynamically allocate an adjacency segment";
                    type empty;
                  }
                }
              }
            }
          }
        }
        leaf delay-metric {
          description "Delay metric";
          units microseconds;
          type union {
            type string {
              pattern "<.*>|$.*";
            }
            type uint32 {
              range "0 .. 16777215";
            }
          }
        }
        container delay-measurement {
          presence "enable delay-measurement";
          description "Enable delay measurement";
          leaf probe-interval {
            description "Probe interval";
            units seconds;
            type union {
              type string {
                pattern "<.*>|$.*";
              }
              type uint32 {
                range "1 .. 255";
              }
            }
          }
          leaf probe-count {
            description "Probe count";
            type union {
              type string {
                pattern "<.*>|$.*";
              }
              type uint32 {
                range "1 .. 15";
              }
            }
          }
          container advertisement {
            description "Delay advertisement";
            container periodic {
              description "Periodic advertisement parameters";
              leaf threshold {
                description "Threshold";
                units percentage;
                type union {
                  type string {
                    pattern "<.*>|$.*";
                  }
                  type uint32 {
                    range "0 .. 100";
                  }
                }
              }
              leaf interval {
                description "Interval";
                units seconds;
                type union {
                  type string {
                    pattern "<.*>|$.*";
                  }
                  type uint32 {
                    range "30 .. 3600";
                  }
                }
              }
            }
            container accelerated {
              presence "enable accelerated";
              description "Accelerated advertisement parameters";
              leaf threshold {
                description "Threshold";
                units percentage;
                type union {
                  type string {
                    pattern "<.*>|$.*";
                  }
                  type uint32 {
                    range "0 .. 100";
                  }
                }
              }
            }
          }
        }
        container application-specific {
          description "Advertise application-specific TE attributes";
          list attribute-group {
            key name;
            ordered-by user;
            description "Link attribute group name";
            max-elements 1;
            leaf name {
              description "Link attribute group name";
              type string;
            }
            leaf te-metric {
              description "Traffic engineering metric for this attribute group";
              type union {
                type string {
                  pattern "<.*>|$.*";
                }
                type uint32 {
                  range "1 .. 4294967295";
                }
              }
            }
            leaf-list admin-group {
              ordered-by user;
              description "Administrative groups for this attribute-group";
              type string;
              max-elements 16;
            }
            leaf delay-metric {
              description "Delay metric for this attribute-group";
              units microseconds;
              type union {
                type string {
                  pattern "<.*>|$.*";
                }
                type uint32 {
                  range "0 .. 16777215";
                }
              }
            }
            leaf advertise-interface-delay {
              description "Use interface specific static/dynamic delay values as applicable in ASLA Sub-TLVs";
              type empty;
            }
            container application {
              description "Standard Applications part of this attribute-group";
              leaf flex-algorithm {
                description "Set X flag in standard application bit mask";
                type empty;
              }
            }
          }
        }
      }
      leaf no-context-identifier-advertisement {
        description "Disable context identifier advertisments in this area";
        type empty;
      }
      list peer-interface {
        key name;
        ordered-by user;
        description "Configuration for peer interface";
        leaf name {
          description "Name of peer interface";
          type string;
        }
        choice enable-disable {
          case case_1 {
            leaf disable {
              description "Disable OSPF on this control peer";
              type empty;
            }
          }
        }
        leaf retransmit-interval {
          description "Retransmission interval (seconds)";
          type union {
            type string {
              pattern "<.*>|$.*";
            }
            type uint32 {
              range "1 .. 65535";
            }
          }
        }
        leaf transit-delay {
          description "Transit delay (seconds)";
          type union {
            type string {
              pattern "<.*>|$.*";
            }
            type uint32 {
              range "1 .. 65535";
            }
          }
        }
        leaf hello-interval {
          description "Hello interval (seconds)";
          type union {
            type string {
              pattern "<.*>|$.*";
            }
            type uint32 {
              range "1 .. 255";
            }
          }
        }
        leaf dead-interval {
          description "Dead interval (seconds)";
          type union {
            type string {
              pattern "<.*>|$.*";
            }
            type uint32 {
              range "1 .. 65535";
            }
          }
        }
        leaf mtu {
          description "Maximum OSPF packet size";
          type union {
            type string {
              pattern "<.*>|$.*";
            }
            type uint32 {
              range "128 .. 65535";
            }
          }
        }
        choice auth {
          case case_1 {
            container authentication {
              uses juniper-ospf-authentication;
            }
          }
          case case_2 {
            container authentication-key {
              description "Authentication key";
              status deprecated;
              leaf keyname {
                description "Authentication key value";
                type jt:unreadable;
              }
              leaf key-id {
                description "Key ID for MD5 authentication";
                type union {
                  type string {
                    pattern "<.*>|$.*";
                  }
                  type uint32 {
                    range "0 .. 255";
                  }
                }
              }
            }
          }
        }
        leaf demand-circuit {
          description "Interface functions as a demand circuit";
          type empty;
        }
        leaf flood-reduction {
          description "Enable flood reduction";
          type empty;
        }
        leaf no-neighbor-down-notification {
          description "Don't inform other protocols about neighbor down events";
          type empty;
        }
      }
      leaf no-source-packet-routing {
        description "Disable SPRING in this area";
        type empty;
      }
      list context-identifier {
        key name;
        ordered-by user;
        description "Configure context identifier in support of edge protection";
        leaf name {
          description "Context identifier";
          type jt:ipv4addr;
        }
      }
      list label-switched-path {
        key name;
        ordered-by user;
        description "Configuration for advertisement of a label-switched path";
        leaf name {
          description "Name of label-switched path to be advertised";
          type string {
            length "1 .. 64";
          }
        }
        choice enable-disable {
          case case_1 {
            leaf disable {
              description "Disable OSPF on this label-switched path";
              type empty;
            }
          }
        }
        leaf metric {
          description "Interface metric";
          type union {
            type string {
              pattern "<.*>|$.*";
            }
            type uint16 {
              range "1 .. 65535";
            }
          }
        }
        list topology {
          key name;
          ordered-by user;
          description "Topology specific attributes";
          leaf name {
            description "Topology name";
            type string;
          }
          leaf disable {
            description "Disable this topology";
            type empty;
          }
          leaf metric {
            description "Topology metric";
            type union {
              type string {
                pattern "<.*>|$.*";
              }
              type uint16 {
                range "1 .. 65535";
              }
            }
          }
          container bandwidth-based-metrics {
            description "Configure bandwidth based metrics";
            list bandwidth {
              key name;
              description "Bandwidth threshold";
              leaf name {
                type string;
              }
              leaf metric {
                description "Metric associated with specified bandwidth";
                type union {
                  type string {
                    pattern "<.*>|$.*";
                  }
                  type uint16 {
                    range "1 .. 65535";
                  }
                }
              }
            }
          }
        }
      }
    }
    choice enable-disable {
      case case_1 {
        leaf disable {
          description "Disable OSPF";
          type empty;
        }
      }
    }
    container traceoptions {
      description "Trace options for OSPF";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum spf {
              description "Trace SPF calculations";
            }
            enum error {
              description "Trace errored packets";
            }
            enum event {
              description "Trace OSPF state machine events";
            }
            enum packet-dump {
              description "Dump the contents of selected packet types";
            }
            enum flooding {
              description "Trace LSA flooding";
            }
            enum lsa-analysis {
              description "Trace LSA analysis";
            }
            enum packets {
              description "Trace all OSPF packets";
            }
            enum hello {
              description "Trace hello packets";
            }
            enum database-description {
              description "Trace database description packets";
            }
            enum lsa-request {
              description "Trace LSA request packets";
            }
            enum lsa-update {
              description "Trace LSA update packets";
            }
            enum lsa-ack {
              description "Trace LSA acknowledgment packets";
            }
            enum ldp-synchronization {
              description "Trace synchronization between OSPF and LDP";
            }
            enum on-demand {
              description "Trace demand circuit extensions";
            }
            enum nsr-synchronization {
              description "Trace NSR synchronization events";
            }
            enum graceful-restart {
              description "Trace graceful restart";
            }
            enum restart-signaling {
              description "Trace restart signaling";
            }
            enum traffic-statistics {
              description "Trace Segment Routing Traffic Statistics";
            }
            enum backup-spf {
              description "Trace backup SPF (LFA) specific events";
            }
            enum source-packet-routing {
              description "Trace source packet routing (SPRING) events";
            }
            enum post-convergence-lfa {
              description "Trace post-convergence-lfa related events";
            }
            enum flex-algorithm {
              description "Trace flex-algorithm related events";
            }
            enum rmopd {
              description "Trace rmopd interactions";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf prefix-export-limit {
      description "Maximum number of prefixes that can be exported";
      type union {
        type string {
          pattern "<.*>|$.*";
        }
        type uint32 {
          range "0 .. 4294967295";
        }
      }
    }
    container rib-groups {
      description "Routing table groups for importing OSPF routes";
      leaf inet {
        description "Name of the IPv4/v6 routing table group";
        type string;
      }
      leaf inet3 {
        description "Name of the IPv4/v6 inet.3 routing table group";
        type string;
      }
    }
    leaf job-stats {
      description "Collect job statistics";
      type empty;
    }
    container overload {
      presence "enable overload";
      description "Set the overload mode (repel transit traffic)";
      leaf timeout {
        description "Time after which overload mode is reset";
        units seconds;
        type union {
          type string {
            pattern "<.*>|$.*";
          }
          type uint32 {
            range "60 .. 3600";
          }
        }
      }
      leaf allow-route-leaking {
        description "Allow routes to be leaked when overload is configured";
        type empty;
      }
      leaf stub-network {
        description "Advertise Stub Network with maximum metric";
        type empty;
      }
      leaf intra-area-prefix {
        description "Advertise Intra Area Prefix with maximum metric";
        type empty;
      }
      leaf as-external {
        description "Advertise As External with maximum usable metric";
        type empty;
      }
    }
    container database-protection {
      presence "enable database-protection";
      description "Configure database protection attributes";
      leaf maximum-lsa {
        description "Maximum allowed non self-generated LSAs";
        type union {
          type string {
            pattern "<.*>|$.*";
          }
          type uint32 {
            range "1 .. 1000000";
          }
        }
      }
      leaf warning-only {
        description "Emit only a warning when LSA maximum limit is exceeded";
        type empty;
      }
      leaf warning-threshold {
        description "Percentage of LSA maximum above which to trigger warning";
        units percent;
        type union {
          type string {
            pattern "<.*>|$.*";
          }
          type uint8 {
            range "30 .. 100";
          }
        }
      }
      leaf ignore-count {
        description "Maximum number of times to go into ignore state";
        type union {
          type string {
            pattern "<.*>|$.*";
          }
          type uint8 {
            range "1 .. 32";
          }
        }
      }
      leaf ignore-time {
        description "Time to stay in ignore state and ignore all neighbors";
        units seconds;
        type union {
          type string {
            pattern "<.*>|$.*";
          }
          type uint16 {
            range "30 .. 3600";
          }
        }
      }
      leaf reset-time {
        description "Time after which the ignore count gets reset to zero";
        units seconds;
        type union {
          type string {
            pattern "<.*>|$.*";
          }
          type uint32 {
            range "60 .. 86400";
          }
        }
      }
    }
    container graceful-restart {
      description "Configure graceful restart attributes";
      choice enable-disable {
        case case_1 {
          leaf disable {
            description "Disable OSPF graceful restart capability";
            type empty;
          }
        }
      }
      leaf restart-duration {
        description "Time for all neighbors to become full";
        units seconds;
        type union {
          type string {
            pattern "<.*>|$.*";
          }
          type uint32 {
            range "1 .. 3600";
          }
        }
      }
      leaf notify-duration {
        description "Time to send all max-aged grace LSAs";
        units seconds;
        type union {
          type string {
            pattern "<.*>|$.*";
          }
          type uint32 {
            range "1 .. 3600";
          }
        }
      }
      container helper-disable {
        presence "enable helper-disable";
        description "Disable graceful restart helper capability";
        choice disable-choices {
          case case_1 {
            leaf standard {
              description "Disable helper-mode for rfc3623 based GR";
              type empty;
            }
          }
          case case_2 {
            leaf restart-signaling {
              description "Disable helper mode for restart-signaling ";
              type empty;
            }
          }
          case case_3 {
            leaf both {
              description "Disable helper mode for both the types of GR";
              type empty;
            }
          }
        }
      }
      leaf no-strict-lsa-checking {
        description "Do not abort graceful helper mode upon LSA changes";
        type empty;
      }
    }
    leaf route-type-community {
      description "Specify BGP extended community value to encode OSPF route type";
      type enumeration {
        enum iana {
          description "BGP extended community value used is 0x0306";
        }
        enum vendor {
          description "Vendor BGP extended community value used is 0x8000";
        }
      }
    }
    container domain-id {
      description "Configure domain ID";
      choice domain_id_or_disable {
        case case_1 {
          leaf domain-id {
            description "Domain ID";
            type string;
          }
        }
        case case_2 {
          leaf disable {
            description "Disable domain ID";
            type empty;
          }
        }
      }
    }
    choice domain_vpn_tag_or_disable {
      case case_1 {
        leaf domain-vpn-tag {
          description "Domain VPN tag for external LSA";
          type union {
            type string {
              pattern "<.*>|$.*";
            }
            type uint32 {
              range "0 .. 4294967295";
            }
          }
        }
      }
      case case_2 {
        leaf no-domain-vpn-tag {
          description "Disable domain VPN tag";
          type empty;
        }
      }
    }
    leaf preference {
      description "Preference of internal routes";
      type union {
        type uint32;
        type string {
          pattern "<.*>|$.*";
        }
      }
    }
    leaf external-preference {
      description "Preference of external routes";
      type union {
        type uint32;
        type string {
          pattern "<.*>|$.*";
        }
      }
    }
    leaf labeled-preference {
      description "Preference of labeled routes";
      type union {
        type uint32;
        type string {
          pattern "<.*>|$.*";
        }
      }
    }
    leaf-list export {
      ordered-by user;
      description "Export policy";
      type jt:policy-algebra;
    }
    leaf-list import {
      ordered-by user;
      description "Import policy (for external routes or setting priority)";
      type jt:policy-algebra;
    }
    leaf reference-bandwidth {
      description "Bandwidth for calculating metric defaults";
      type string;
    }
    leaf lsa-refresh-interval {
      description "LSA refresh interval (minutes)";
      default "50";
      type union {
        type string {
          pattern "<.*>|$.*";
        }
        type uint32 {
          range "25 .. 50";
        }
      }
    }
    leaf spf-delay {
      description "Time to wait before running an SPF";
      status deprecated;
      units milliseconds;
      type union {
        type string {
          pattern "<.*>|$.*";
        }
        type uint32 {
          range "50 .. 8000";
        }
      }
    }
    leaf no-rfc-1583 {
      description "Disable RFC1583 compatibility";
      type empty;
    }
    leaf forwarding-address-to-broadcast {
      description "Set forwarding address in Type 5 LSA in broadcast network";
      type empty;
    }
    choice nssa-abr-option {
      case case_1 {
        leaf no-nssa-abr {
          description "Disable full NSSA functionality at ABR";
          type empty;
        }
      }
    }
    container sham-link {
      presence "enable sham-link";
      description "Configure parameters for sham links";
      leaf local {
        description "Local sham link endpoint address";
        type jt:ipaddr;
      }
      leaf no-advertise-local {
        description "Don't advertise local sham link endpoint as stub in router LSA";
        status deprecated;
        type empty;
      }
    }
  }
  grouping juniper-protocols-pgm {
    container traceoptions {
      description "PGM trace options";
      list flag {
        key name;
        ordered-by user;
        description "Tracing parameters";
        leaf name {
          type enumeration {
            enum init {
              description "Trace initialization events";
            }
            enum show {
              description "Trace show command servicing";
            }
            enum route-socket {
              description "Trace route-socket events";
            }
            enum parse {
              description "Trace parser processing";
            }
            enum state {
              description "Trace state transitions";
            }
            enum packets {
              description "Trace packet processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
  }
  grouping juniper-protocols-pim {
    leaf protocol-instance-name {
      description "Name of protocol instance under routing instance";
      type string;
    }
    container family {
      description "Local address family";
      container any {
        presence "enable any";
        description "Default properties for all address families";
        leaf disable {
          description "Disable all families";
          type empty;
        }
      }
      container inet {
        presence "enable inet";
        description "IPv4 specific properties";
        choice enable-disable {
          case case_1 {
            leaf disable {
              description "Disable PIMv4 on all interfaces";
              type empty;
            }
          }
        }
      }
      container inet6 {
        presence "enable inet6";
        description "IPv6 specific properties";
        choice enable-disable {
          case case_1 {
            leaf disable {
              description "Disable PIMv6 on all interfaces";
              type empty;
            }
          }
        }
      }
    }
    choice enable-disable {
      case case_1 {
        leaf disable {
          description "Disable PIM";
          type empty;
        }
      }
    }
    container nonstop-routing {
      description "Configure PIM nonstop-routing attributes";
      choice enable-disable {
        case case_1 {
          leaf disable {
            description "Disable non-stop routing for PIM";
            type empty;
          }
        }
      }
    }
    container traceoptions {
      description "Trace options for PIM";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum route {
              description "Trace routing information";
            }
            enum packets {
              description "Trace all PIM packets";
            }
            enum hello {
              description "Trace hello packets";
            }
            enum register {
              description "Trace register/register-stop messages";
            }
            enum join {
              description "Trace join/prune/graft/graft-ack messages";
            }
            enum prune {
              description "Trace join/prune/graft/graft-ack messages";
            }
            enum graft {
              description "Trace join/prune/graft/graft-ack messages";
            }
            enum bootstrap {
              description "Trace bootstrap/RP/auto-RP messages";
            }
            enum rp {
              description "Trace bootstrap/RP/auto-RP messages";
            }
            enum autorp {
              description "Trace bootstrap/RP/auto-RP messages";
            }
            enum assert {
              description "Trace assert messages";
            }
            enum mdt {
              description "Trace messages related to multicast data tunnels";
            }
            enum nsr-synchronization {
              description "Trace NSR synchronization events";
            }
            enum bidirectional-df-election {
              description "Trace bidirectional PIM DF election events";
            }
            enum mofrr {
              description "Trace Multicast only Fast Re-Route messages";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
        container filter {
          description "Filter to apply to this flag";
          presence "enable filter";
          uses pim_filter_obj;
        }
      }
    }
    container dense-groups {
      description "Dense mode groups for sparse-dense mode";
      leaf dynamic-reject {
        description "Reject dynamic autorp negative dense-mode prefixes learnt from network";
        type empty;
      }
      list pim-dense-group-type {
        key name;
        ordered-by user;
        leaf name {
          description "Group address or range to forward in dense mode";
          type jt:ipprefix;
        }
        choice dense-group-flags {
          case case_1 {
            leaf reject {
              description "Do not include prefix as dense mode; force sparse mode";
              type empty;
            }
          }
          case case_2 {
            leaf announce {
              description "Advertise as negative prefix in auto-RP announce messages";
              type empty;
            }
          }
        }
      }
    }
    leaf vpn-tunnel-source {
      description "Source address for the provider space mGRE tunnel";
      status deprecated;
      type jt:ipv4addr;
    }
    leaf vpn-group-address {
      description "Group address for the VPN in provider space";
      status deprecated;
      type jt:ipv4addr;
    }
    leaf-list tunnel-devices {
      ordered-by user;
      description "Tunnel devices to be used for creating mt interfaces";
      type union {
        type jt:interface-device;
        type string {
          pattern "<.*>|$.*";
        }
      }
    }
    container rpf-selection {
      description "Select RPF neighbor";
      list group {
        key name;
        ordered-by user;
        description "IP prefix of multicast group";
        leaf name {
          description "IP prefix of group";
          type jt:ipprefix;
        }
        container wildcard-source {
          presence "enable wildcard-source";
          description "Select RPF for (*,g) and unspecified (s,g) joins";
          leaf next-hop {
            description "Next-hop address";
            type jt:ipaddr;
          }
        }
        list source {
          key name;
          ordered-by user;
          description "IP prefix of one or more multicast sources";
          leaf name {
            description "IP prefix of source";
            type jt:ipprefix;
          }
          leaf next-hop {
            description "Next-hop address";
            type jt:ipaddr;
          }
        }
      }
      list prefix-list {
        key name;
        ordered-by user;
        description "Multicast group prefix list";
        leaf name {
          description "Name of prefix list to match against";
          type string;
        }
        container wildcard-source {
          presence "enable wildcard-source";
          description "Select RPF for (*,g) and unspecified (s,g) joins";
          leaf next-hop {
            description "Next-hop address";
            type jt:ipaddr;
          }
        }
        list source {
          key name;
          ordered-by user;
          description "IP prefix of one or more multicast sources";
          leaf name {
            description "IP prefix of source";
            type jt:ipprefix;
          }
          leaf next-hop {
            description "Next-hop address";
            type jt:ipaddr;
          }
        }
      }
    }
    container mvpn {
      presence "enable mvpn";
      description "PIM MVPN control-plane options";
      container autodiscovery {
        description "PE router autodiscovery options for SSM MDTs";
        status deprecated;
        leaf inet-mdt {
          description "MDT-SAFI PE autodiscovery for SSM MDTs";
          type empty;
        }
      }
      container family {
        description "PIM MVPN address family";
        container inet {
          description "IPv4 PIM MVPN specific properties";
          leaf rosen-mvpn {
            status deprecated;
            type empty;
          }
          leaf ngen-mvpn {
            status deprecated;
            type empty;
          }
          container autodiscovery {
            description "PE router autodiscovery options for SSM MDTs";
            leaf inet-mdt {
              description "MDT-SAFI PE autodiscovery for SSM MDTs";
              type empty;
            }
          }
          leaf disable {
            description "Disable family IPv4";
            type empty;
          }
        }
        container inet6 {
          description "IPv6 PIM MVPN specific properties";
          leaf rosen-mvpn {
            status deprecated;
            type empty;
          }
          leaf ngen-mvpn {
            status deprecated;
            type empty;
          }
          container autodiscovery {
            description "PE router autodiscovery options for SSM MDTs";
            leaf inet-mdt {
              description "MDT-SAFI PE autodiscovery for SSM MDTs";
              type empty;
            }
          }
          leaf disable {
            description "Disable family IPv6";
            type empty;
          }
        }
      }
    }
    container rib-group {
      description "Routing table group";
      uses rib_group_type;
    }
    leaf-list import {
      ordered-by user;
      description "PIM sparse import join policy";
      type jt:policy-algebra;
    }
    leaf-list export {
      ordered-by user;
      description "PIM sparse export join policy";
      type jt:policy-algebra;
    }
    container mldp-inband-signalling {
      presence "enable mldp-inband-signalling";
      leaf-list policy {
        ordered-by user;
        description "PIM MLDP join translation filter policy";
        type jt:policy-algebra;
      }
    }
    container rpf-vector {
      description "RPF vector TLV";
      leaf-list policy {
        ordered-by user;
        description "RPF vector TLV include policy";
        type jt:policy-algebra;
      }
    }
    leaf assert-timeout {
      description "Set assert timeout";
      default "180";
      type union {
        type string {
          pattern "<.*>|$.*";
        }
        type uint32 {
          range "5 .. 210";
        }
      }
    }
    leaf assert-robust-count {
      description "Number of assert messages an assert winner sends in one cycle";
      default "2";
      type union {
        type string {
          pattern "<.*>|$.*";
        }
        type uint32 {
          range "1 .. 5";
        }
      }
    }
    leaf join-prune-timeout {
      description "Set join/prune timeout";
      default "210";
      type union {
        type string {
          pattern "<.*>|$.*";
        }
        type uint32 {
          range "210 .. 420";
        }
      }
    }
    container spt-threshold {
      description "Set shortest-path-tree threshold policy";
      leaf-list infinity {
        ordered-by user;
        description "Apply policy to always remain on shared tree";
        type jt:policy-algebra;
      }
    }
    container sglimit {
      description "Set limit on number of (S,G) states ";
      list family {
        key name;
        ordered-by user;
        description "Protocol family";
        leaf name {
          type enumeration {
            enum inet {
              description "IPv4 family";
            }
            enum inet6 {
              description "IPv6 family";
            }
          }
        }
        leaf maximum {
          description "Maximum limit above which additional entries are not accepted";
          type union {
            type string {
              pattern "<.*>|$.*";
            }
            type uint32 {
              range "1 .. 65535";
            }
          }
        }
        leaf threshold {
          description "Percentage of maximum at which to start generating warnings";
          type union {
            type string {
              pattern "<.*>|$.*";
            }
            type uint32 {
              range "1 .. 100";
            }
          }
        }
        leaf log-interval {
          description "Time between successive log messages";
          type union {
            type string {
              pattern "<.*>|$.*";
            }
            type uint32 {
              range "1 .. 65535";
            }
          }
        }
      }
      leaf maximum {
        description "Maximum limit above which additional entries are not accepted";
        type union {
          type string {
            pattern "<.*>|$.*";
          }
          type uint32 {
            range "1 .. 65535";
          }
        }
      }
      leaf threshold {
        description "Percentage of maximum at which to start generating warnings";
        type union {
          type string {
            pattern "<.*>|$.*";
          }
          type uint32 {
            range "1 .. 100";
          }
        }
      }
      leaf log-interval {
        description "Time between successive log messages";
        type union {
          type string {
            pattern "<.*>|$.*";
          }
          type uint32 {
            range "1 .. 65535";
          }
        }
      }
    }
    container rp {
      description "Router's rendezvous point properties";
      leaf bootstrap-priority {
        description "Eligibility to be the bootstrap router (IPv4 only)";
        type union {
          type string {
            pattern "<.*>|$.*";
          }
          type uint32 {
            range "0 .. 255";
          }
        }
      }
      leaf-list bootstrap-import {
        ordered-by user;
        description "Bootstrap import policy (IPv4 only)";
        type jt:policy-algebra;
      }
      leaf-list bootstrap-export {
        ordered-by user;
        description "Bootstrap export policy (IPv4 only)";
        type jt:policy-algebra;
      }
      container bootstrap {
        description "Bootstrap properties";
        container family {
          description "Bootstrap address family";
          container inet {
            description "IPv4 bootstrap properties";
            uses pim_bootstrap_options_type;
          }
          container inet6 {
            description "IPv6 bootstrap properties";
            uses pim_bootstrap_options_type;
          }
        }
      }
      container register-limit {
        description "Set limit on incoming registers that create (S,G) state";
        list family {
          key name;
          ordered-by user;
          description "Protocol family";
          leaf name {
            type enumeration {
              enum inet {
                description "IPv4 family";
              }
              enum inet6 {
                description "IPv6 family";
              }
            }
          }
          leaf maximum {
            description "Maximum limit above which additional entries are not accepted";
            type union {
              type string {
                pattern "<.*>|$.*";
              }
              type uint32 {
                range "1 .. 65535";
              }
            }
          }
          leaf threshold {
            description "Percentage of maximum at which to start generating warnings";
            type union {
              type string {
                pattern "<.*>|$.*";
              }
              type uint32 {
                range "1 .. 100";
              }
            }
          }
          leaf log-interval {
            description "Time between successive log messages";
            type union {
              type string {
                pattern "<.*>|$.*";
              }
              type uint32 {
                range "1 .. 65535";
              }
            }
          }
        }
        leaf maximum {
          description "Maximum limit above which additional entries are not accepted";
          type union {
            type string {
              pattern "<.*>|$.*";
            }
            type uint32 {
              range "1 .. 65535";
            }
          }
        }
        leaf threshold {
          description "Percentage of maximum at which to start generating warnings";
          type union {
            type string {
              pattern "<.*>|$.*";
            }
            type uint32 {
              range "1 .. 100";
            }
          }
        }
        leaf log-interval {
          description "Time between successive log messages";
          type union {
            type string {
              pattern "<.*>|$.*";
            }
            type uint32 {
              range "1 .. 65535";
            }
          }
        }
      }
      container group-rp-mapping {
        description "Group-rp-mapping";
        list family {
          key name;
          ordered-by user;
          description "Protocol family";
          leaf name {
            type enumeration {
              enum inet {
                description "IPv4 family";
              }
              enum inet6 {
                description "IPv6 family";
              }
            }
          }
          leaf maximum {
            description "Maximum limit above which additional entries are not accepted";
            type union {
              type string {
                pattern "<.*>|$.*";
              }
              type uint32 {
                range "1 .. 65535";
              }
            }
          }
          leaf threshold {
            description "Percentage of maximum at which to start generating warnings";
            type union {
              type string {
                pattern "<.*>|$.*";
              }
              type uint32 {
                range "1 .. 100";
              }
            }
          }
          leaf log-interval {
            description "Time between successive log messages";
            type union {
              type string {
                pattern "<.*>|$.*";
              }
              type uint32 {
                range "1 .. 65535";
              }
            }
          }
        }
        leaf maximum {
          description "Maximum limit above which additional entries are not accepted";
          type union {
            type string {
              pattern "<.*>|$.*";
            }
            type uint32 {
              range "1 .. 65535";
            }
          }
        }
        leaf threshold {
          description "Percentage of maximum at which to start generating warnings";
          type union {
            type string {
              pattern "<.*>|$.*";
            }
            type uint32 {
              range "1 .. 100";
            }
          }
        }
        leaf log-interval {
          description "Time between successive log messages";
          type union {
            type string {
              pattern "<.*>|$.*";
            }
            type uint32 {
              range "1 .. 65535";
            }
          }
        }
      }
      leaf-list rp-register-policy {
        ordered-by user;
        description "RP policy applied to incoming register messages";
        type jt:policy-algebra;
      }
      leaf-list dr-register-policy {
        ordered-by user;
        description "DR policy applied to outgoing register messages";
        type jt:policy-algebra;
      }
      container local {
        description "Router's local RP properties";
        leaf address {
          description "Local RP address (IPv4 only)";
          type jt:ipv4addr;
        }
        choice enable-disable {
          case case_1 {
            leaf disable {
              description "Disable this RP (IPv4 only)";
              type empty;
            }
          }
        }
        leaf priority {
          description "Router's priority for becoming an RP (IPv4 only)";
          type union {
            type string {
              pattern "<.*>|$.*";
            }
            type uint32 {
              range "0 .. 255";
            }
          }
        }
        leaf hold-time {
          description "How long neighbor considers this router to be up, in seconds (IPv4 only)";
          type union {
            type string {
              pattern "<.*>|$.*";
            }
            type uint32 {
              range "1 .. 65535";
            }
          }
        }
        list group-ranges {
          key name;
          ordered-by user;
          description "Group address range for which this router can be an RP (IPv4 only)";
          leaf name {
            type jt:ipv4prefix;
          }
        }
        leaf override {
          description "Static RP mapping will take precedence over dynamic";
          type empty;
        }
        container family {
          description "Local RP address family";
          container inet {
            description "IPv4 local RP properties";
            leaf address {
              description "Local RP address";
              type jt:ipv4addr;
            }
            choice enable-disable {
              case case_1 {
                leaf disable {
                  description "Disable this RP";
                  type empty;
                }
              }
            }
            leaf priority {
              description "Router's priority for becoming an RP";
              type union {
                type string {
                  pattern "<.*>|$.*";
                }
                type uint32 {
                  range "0 .. 255";
                }
              }
            }
            leaf hold-time {
              description "How long neighbor considers this router to be up, in seconds";
              type union {
                type string {
                  pattern "<.*>|$.*";
                }
                type uint32 {
                  range "1 .. 65535";
                }
              }
            }
            list group-ranges {
              key name;
              ordered-by user;
              description "Group address range for which this router can be an RP";
              leaf name {
                type jt:ipv4prefix;
              }
            }
            leaf override {
              description "Static RP mapping will take precedence over dynamic";
              type empty;
            }
            container anycast-pim {
              description "Attributes for IPv4 anycast PIM";
              container rp-set {
                description "Rendezvous points belonging to anycast RP set";
                list address {
                  key name;
                  ordered-by user;
                  description "IPv4 address of one or more remote anycast RPs";
                  leaf name {
                    description "IPv4 address of remote anycast RP";
                    type jt:ipaddr;
                  }
                  leaf forward-msdp-sa {
                    description "Forward SAs learned from MSDP to this RP";
                    type empty;
                  }
                }
              }
              leaf local-address {
                description "Local address for replicating register messages to other RPs";
                type jt:ipaddr;
              }
            }
          }
          container inet6 {
            description "IPv6 local RP properties";
            leaf address {
              description "Local RP address";
              type jt:ipv6addr;
            }
            choice enable-disable {
              case case_1 {
                leaf disable {
                  description "Disable this RP";
                  type empty;
                }
              }
            }
            leaf priority {
              description "Router's priority for becoming an RP";
              type union {
                type string {
                  pattern "<.*>|$.*";
                }
                type uint32 {
                  range "0 .. 255";
                }
              }
            }
            leaf hold-time {
              description "How long neighbor considers this router to be up, in seconds";
              type union {
                type string {
                  pattern "<.*>|$.*";
                }
                type uint32 {
                  range "1 .. 65535";
                }
              }
            }
            list group-ranges {
              key name;
              ordered-by user;
              description "Group address range for which this router can be an RP";
              leaf name {
                type jt:ipv6prefix;
              }
            }
            leaf override {
              description "Static RP mapping will take precedence over dynamic";
              type empty;
            }
            container anycast-pim {
              description "Attributes for IPv6 anycast PIM";
              container rp-set {
                description "Rendezvous points belonging to anycast RP set";
                list address {
                  key name;
                  ordered-by user;
                  description "IPv6 address of one or more remote anycast RPs";
                  leaf name {
                    description "IPv6 address of remote anycast RP";
                    type jt:ipv6addr;
                  }
                }
              }
              leaf local-address {
                description "Local address for replicating register messages to other RPs";
                type jt:ipv6addr;
              }
            }
          }
        }
      }
      container embedded-rp {
        presence "enable embedded-rp";
        description "Set embedded-RP mode (IPv6 only)";
        list group-ranges {
          key name;
          ordered-by user;
          description "Group address range of RP";
          uses pim_rp_group_range_type;
        }
        leaf maximum-rps {
          description "Maximum number of embedded RPs";
          default "100";
          type union {
            type string {
              pattern "<.*>|$.*";
            }
            type uint32 {
              range "1 .. 500";
            }
          }
        }
      }
      container auto-rp {
        description "Set auto-RP mode (IPv4 only)";
        choice autorp-mode {
          case case_1 {
            leaf discovery {
              description "Listen for auto-RP discovery messages";
              type empty;
            }
          }
          case case_2 {
            leaf announce {
              description "Transmit auto-RP announcement messages";
              type empty;
            }
          }
          case case_3 {
            leaf mapping {
              description "Transmit auto-RP mapping messages";
              type empty;
            }
          }
        }
        choice mapping-agent-election-choice {
          leaf mapping-agent-election {
            description "Consider higher-addressed mapping agents as authoritative";
            type empty;
          }
          leaf no-mapping-agent-election {
            description "Don't consider higher-addressed mapping agents as authoritative";
            type empty;
          }
        }
      }
      container static {
        description "Configure static PIM RPs";
        list address {
          key name;
          ordered-by user;
          description "RP address";
          leaf name {
            description "IP address of RP";
            type jt:ipaddr;
          }
          leaf version {
            description "PIM version of RP";
            status deprecated;
            type union {
              type string {
                pattern "<.*>|$.*";
              }
              type uint32 {
                range "1 .. 2";
              }
            }
          }
          list group-ranges {
            key name;
            ordered-by user;
            description "Group address range of RP";
            uses pim_rp_group_range_type;
          }
          leaf override {
            description "Static RP mapping will take precedence over dynamic";
            type empty;
          }
        }
      }
      container bidirectional {
        description "Configure PIM bidirectional-mode RPs";
        list address {
          key name;
          ordered-by user;
          description "RP address";
          leaf name {
            description "IP address of RP";
            type jt:ipaddr;
          }
          leaf priority {
            description "Router's priority for becoming an RP";
            type union {
              type string {
                pattern "<.*>|$.*";
              }
              type uint32 {
                range "0 .. 255";
              }
            }
          }
          leaf hold-time {
            description "How long neighbor considers this router to be up";
            units seconds;
            type union {
              type string {
                pattern "<.*>|$.*";
              }
              type uint32 {
                range "1 .. 65535";
              }
            }
          }
          list group-ranges {
            key name;
            ordered-by user;
            description "Group address range of RP";
            uses pim_rp_group_range_type;
          }
        }
      }
    }
    leaf passive {
      description "Configure PIM protocol in passive mode";
      type empty;
    }
    list interface {
      key name;
      ordered-by user;
      description "PIM interface options";
      leaf name {
        description "Interface name";
        type string;
      }
      container family {
        description "Local address family";
        container any {
          presence "enable any";
          description "Default properties for all families";
          leaf disable {
            description "Disable all families";
            type empty;
          }
        }
        container inet {
          presence "enable inet";
          description "IPv4 specific properties";
          container bfd-liveness-detection {
            description "Bidirectional Forwarding Detection options";
            leaf version {
              description "BFD protocol version number";
              default "automatic";
              type enumeration {
                enum 0 {
                  description "BFD version 0 (deprecated)";
                }
                enum 1 {
                  description "BFD version 1";
                }
                enum automatic {
                  description "Choose BFD version automatically";
                }
              }
            }
            leaf minimum-interval {
              description "Minimum transmit and receive interval";
              units milliseconds;
              type union {
                type string {
                  pattern "<.*>|$.*";
                }
                type uint32 {
                  range "1 .. 255000";
                }
              }
            }
            leaf minimum-transmit-interval {
              description "Minimum transmit interval";
              status deprecated;
              units milliseconds;
              type union {
                type string {
                  pattern "<.*>|$.*";
                }
                type uint32 {
                  range "1 .. 255000";
                }
              }
            }
            leaf minimum-receive-interval {
              description "Minimum receive interval";
              units milliseconds;
              type union {
                type string {
                  pattern "<.*>|$.*";
                }
                type uint32 {
                  range "1 .. 255000";
                }
              }
            }
            leaf multiplier {
              description "Detection time multiplier";
              default "3";
              type union {
                type string {
                  pattern "<.*>|$.*";
                }
                type uint32 {
                  range "1 .. 255";
                }
              }
            }
            leaf inline-disable {
              description "Disable inline mode for this BFD session";
              type empty;
            }
            leaf pdu-size {
              description "BFD transport protocol payload size";
              default "24";
              type union {
                type string {
                  pattern "<.*>|$.*";
                }
                type uint32 {
                  range "24 .. 9000";
                }
              }
            }
            choice adaptation-choice {
              case case_1 {
                leaf no-adaptation {
                  description "Disable adaptation";
                  type empty;
                }
              }
            }
            container transmit-interval {
              description "Transmit-interval options";
              leaf minimum-interval {
                description "Minimum transmit interval";
                units milliseconds;
                type union {
                  type string {
                    pattern "<.*>|$.*";
                  }
                  type uint32 {
                    range "1 .. 255000";
                  }
                }
              }
              leaf threshold {
                description "High transmit interval triggering a trap";
                units milliseconds;
                type union {
                  type uint32;
                  type string {
                    pattern "<.*>|$.*";
                  }
                }
              }
            }
            container detection-time {
              description "Detection-time options";
              leaf threshold {
                description "High detection-time triggering a trap";
                units milliseconds;
                type union {
                  type uint32;
                  type string {
                    pattern "<.*>|$.*";
                  }
                }
              }
            }
            container authentication {
              description "Authentication options";
              leaf key-chain {
                description "Key chain name";
                type string;
              }
              leaf algorithm {
                description "Algorithm name";
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
              }
              leaf loose-check {
                description "Verify authentication only if authentication is negotiated";
                type empty;
              }
            }
          }
          leaf mcae-mac-synchronize {
            description "Mclag mac synchronization";
            type empty;
          }
          choice enable-disable {
            case case_1 {
              leaf disable {
                description "Disable PIMv4 on this interface";
                type empty;
              }
            }
          }
        }
        container inet6 {
          presence "enable inet6";
          description "IPv6 specific properties";
          container bfd-liveness-detection {
            description "Bidirectional Forwarding Detection options";
            leaf version {
              description "BFD protocol version number";
              default "automatic";
              type enumeration {
                enum 0 {
                  description "BFD version 0 (deprecated)";
                }
                enum 1 {
                  description "BFD version 1";
                }
                enum automatic {
                  description "Choose BFD version automatically";
                }
              }
            }
            leaf minimum-interval {
              description "Minimum transmit and receive interval";
              units milliseconds;
              type union {
                type string {
                  pattern "<.*>|$.*";
                }
                type uint32 {
                  range "1 .. 255000";
                }
              }
            }
            leaf minimum-transmit-interval {
              description "Minimum transmit interval";
              status deprecated;
              units milliseconds;
              type union {
                type string {
                  pattern "<.*>|$.*";
                }
                type uint32 {
                  range "1 .. 255000";
                }
              }
            }
            leaf minimum-receive-interval {
              description "Minimum receive interval";
              units milliseconds;
              type union {
                type string {
                  pattern "<.*>|$.*";
                }
                type uint32 {
                  range "1 .. 255000";
                }
              }
            }
            leaf multiplier {
              description "Detection time multiplier";
              default "3";
              type union {
                type string {
                  pattern "<.*>|$.*";
                }
                type uint32 {
                  range "1 .. 255";
                }
              }
            }
            leaf inline-disable {
              description "Disable inline mode for this BFD session";
              type empty;
            }
            leaf pdu-size {
              description "BFD transport protocol payload size";
              default "24";
              type union {
                type string {
                  pattern "<.*>|$.*";
                }
                type uint32 {
                  range "24 .. 9000";
                }
              }
            }
            choice adaptation-choice {
              case case_1 {
                leaf no-adaptation {
                  description "Disable adaptation";
                  type empty;
                }
              }
            }
            container transmit-interval {
              description "Transmit-interval options";
              leaf minimum-interval {
                description "Minimum transmit interval";
                units milliseconds;
                type union {
                  type string {
                    pattern "<.*>|$.*";
                  }
                  type uint32 {
                    range "1 .. 255000";
                  }
                }
              }
              leaf threshold {
                description "High transmit interval triggering a trap";
                units milliseconds;
                type union {
                  type uint32;
                  type string {
                    pattern "<.*>|$.*";
                  }
                }
              }
            }
            container detection-time {
              description "Detection-time options";
              leaf threshold {
                description "High detection-time triggering a trap";
                units milliseconds;
                type union {
                  type uint32;
                  type string {
                    pattern "<.*>|$.*";
                  }
                }
              }
            }
            container authentication {
              description "Authentication options";
              leaf key-chain {
                description "Key chain name";
                type string;
              }
              leaf algorithm {
                description "Algorithm name";
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
              }
              leaf loose-check {
                description "Verify authentication only if authentication is negotiated";
                type empty;
              }
            }
          }
          choice enable-disable {
            case case_1 {
              leaf disable {
                description "Disable PIMv6 on this interface";
                type empty;
              }
            }
          }
        }
      }
      choice enable-disable {
        case case_1 {
          leaf disable {
            description "Disable PIM on this interface";
            type empty;
          }
        }
      }
      container bidirectional {
        description "PIM bidirectional mode properties";
        container df-election {
          description "Bidir designated forwarder properties";
          leaf robustness-count {
            description "Election robustness count";
            type union {
              type string {
                pattern "<.*>|$.*";
              }
              type uint32 {
                range "1 .. 10";
              }
            }
          }
          leaf offer-period {
            description "Election offer message period";
            units milliseconds;
            type union {
              type string {
                pattern "<.*>|$.*";
              }
              type uint32 {
                range "100 .. 10000";
              }
            }
          }
          leaf backoff-period {
            description "Election backoff period";
            units milliseconds;
            type union {
              type string {
                pattern "<.*>|$.*";
              }
              type uint32 {
                range "100 .. 65535";
              }
            }
          }
        }
      }
      leaf mode {
        description "Mode of interface";
        type enumeration {
          enum dense {
            description "Dense mode";
          }
          enum sparse {
            description "Sparse mode";
          }
          enum sparse-dense {
            description "Sparse-dense mode";
          }
          enum bidirectional-sparse {
            description "Bidirectional-sparse mode";
          }
          enum bidirectional-sparse-dense {
            description "Bidirectional-sparse-dense mode";
          }
        }
      }
      leaf priority {
        description "Hello option DR priority";
        type union {
          type string {
            pattern "<.*>|$.*";
          }
          type uint32 {
            range "0 .. 4294967295";
          }
        }
      }
      container stickydr {
        presence "enable stickydr";
        description "Make DR sticky";
      }
      container multiple-triggered-joins {
        presence "enable multiple-triggered-joins";
        description "Send multiple pim triggered joins in quick intervals";
        leaf count {
          description "Set number of triggered joins to be sent";
          default "2";
          type union {
            type string {
              pattern "<.*>|$.*";
            }
            type uint16 {
              range "2 .. 15";
            }
          }
        }
        leaf interval {
          description "Set interval between multiple triggered joins to be sent in milliseconds";
          default "100";
          type union {
            type string {
              pattern "<.*>|$.*";
            }
            type uint16 {
              range "100 .. 1000";
            }
          }
        }
      }
      leaf version {
        description "Force PIM version";
        status deprecated;
        type union {
          type string {
            pattern "<.*>|$.*";
          }
          type uint32 {
            range "1 .. 2";
          }
        }
      }
      leaf hello-interval {
        description "Hello interval";
        units seconds;
        type union {
          type string {
            pattern "<.*>|$.*";
          }
          type uint32 {
            range "0 .. 255";
          }
        }
      }
      leaf-list neighbor-policy {
        ordered-by user;
        description "PIM neighbor policy applied to incoming hello messages";
        type jt:policy-algebra;
      }
      leaf-list accept-join-always-from {
        ordered-by user;
        description "Accept pim join/prune messages based on the policy configured";
        type jt:policy-algebra;
      }
      leaf accept-remote-source {
        description "Accept traffic from remote source";
        type empty;
      }
      container dual-dr {
        presence "enable dual-dr";
        description "Configure PIM Dual DR";
        leaf enhanced {
          description "Enable enhanced PIM Dual DR";
          type empty;
        }
      }
      leaf distributed-dr {
        description "PIM Distributed DR";
        type empty;
      }
      leaf reset-tracking-bit {
        description "Clear tracking-bit in PIM Hello LAN Prune Delay Option";
        type empty;
      }
      leaf propagation-delay {
        description "Propagation delay value";
        default "500";
        units milliseconds;
        type union {
          type string {
            pattern "<.*>|$.*";
          }
          type uint32 {
            range "250 .. 2000";
          }
        }
      }
      leaf override-interval {
        description "Override interval value";
        default "2000";
        units milliseconds;
        type union {
          type string {
            pattern "<.*>|$.*";
          }
          type uint32 {
            range "500 .. 6000";
          }
        }
      }
      leaf disable-packet-register {
        description "Disable PIM packet registers on first hop router";
        type empty;
      }
      container bfd-liveness-detection {
        description "Bidirectional Forwarding Detection options (ipv4 only)";
        status deprecated;
        leaf version {
          description "BFD protocol version number";
          default "automatic";
          type enumeration {
            enum 0 {
              description "BFD version 0 (deprecated)";
            }
            enum 1 {
              description "BFD version 1";
            }
            enum automatic {
              description "Choose BFD version automatically";
            }
          }
        }
        leaf minimum-interval {
          description "Minimum transmit and receive interval";
          units milliseconds;
          type union {
            type string {
              pattern "<.*>|$.*";
            }
            type uint32 {
              range "1 .. 255000";
            }
          }
        }
        leaf minimum-transmit-interval {
          description "Minimum transmit interval";
          status deprecated;
          units milliseconds;
          type union {
            type string {
              pattern "<.*>|$.*";
            }
            type uint32 {
              range "1 .. 255000";
            }
          }
        }
        leaf minimum-receive-interval {
          description "Minimum receive interval";
          units milliseconds;
          type union {
            type string {
              pattern "<.*>|$.*";
            }
            type uint32 {
              range "1 .. 255000";
            }
          }
        }
        leaf multiplier {
          description "Detection time multiplier";
          default "3";
          type union {
            type string {
              pattern "<.*>|$.*";
            }
            type uint32 {
              range "1 .. 255";
            }
          }
        }
        leaf inline-disable {
          description "Disable inline mode for this BFD session";
          type empty;
        }
        leaf pdu-size {
          description "BFD transport protocol payload size";
          default "24";
          type union {
            type string {
              pattern "<.*>|$.*";
            }
            type uint32 {
              range "24 .. 9000";
            }
          }
        }
        choice adaptation-choice {
          case case_1 {
            leaf no-adaptation {
              description "Disable adaptation";
              type empty;
            }
          }
        }
        container transmit-interval {
          description "Transmit-interval options";
          leaf minimum-interval {
            description "Minimum transmit interval";
            units milliseconds;
            type union {
              type string {
                pattern "<.*>|$.*";
              }
              type uint32 {
                range "1 .. 255000";
              }
            }
          }
          leaf threshold {
            description "High transmit interval triggering a trap";
            units milliseconds;
            type union {
              type uint32;
              type string {
                pattern "<.*>|$.*";
              }
            }
          }
        }
        container detection-time {
          description "Detection-time options";
          leaf threshold {
            description "High detection-time triggering a trap";
            units milliseconds;
            type union {
              type uint32;
              type string {
                pattern "<.*>|$.*";
              }
            }
          }
        }
        container authentication {
          description "Authentication options";
          leaf key-chain {
            description "Key chain name";
            type string;
          }
          leaf algorithm {
            description "Algorithm name";
            type enumeration {
              enum simple-password {
                description "Simple password";
              }
              enum keyed-md5 {
                description "Keyed message Digest 5";
              }
              enum meticulous-keyed-md5 {
                description "Meticulous keyed message Digest 5";
              }
              enum keyed-sha-1 {
                description "Keyed secure hash algorithm (SHA1) ";
              }
              enum meticulous-keyed-sha-1 {
                description "Meticulous keyed secure hash algorithm (SHA1) ";
              }
            }
          }
          leaf loose-check {
            description "Verify authentication only if authentication is negotiated";
            type empty;
          }
        }
      }
    }
    container mdt {
      description "Configure multicast data tunnel parameters";
      status deprecated;
      container threshold {
        description "Threshold for creation of multicast tunnels";
        list group {
          key name;
          ordered-by user;
          description "IP prefix of multicast group";
          leaf name {
            description "IP prefix of group";
            type jt:ipprefix;
          }
          list source {
            key name;
            ordered-by user;
            description "IP prefix of one or more multicast sources ";
            leaf name {
              description "IP prefix of source";
              type jt:ipprefix;
            }
            leaf rate {
              description "Data threshold to create new tunnel";
              units kilobits;
              type union {
                type string {
                  pattern "<.*>|$.*";
                }
                type uint32 {
                  range "10 .. 1000000";
                }
              }
            }
          }
        }
      }
      leaf data-mdt-reuse {
        description "Allow multiple customer streams to be transmitted over one data tunnel ";
        type empty;
      }
      leaf tunnel-limit {
        description "Maximum multicast data tunnels";
        type union {
          type string {
            pattern "<.*>|$.*";
          }
          type uint32 {
            range "0 .. 8192";
          }
        }
      }
      leaf group-range {
        description "Group address range for multicast data tunnels";
        type jt:ipprefix;
      }
    }
    container graceful-restart {
      description "Configure graceful restart attributes";
      choice enable-disable {
        case case_1 {
          leaf disable {
            description "Disable PIM graceful restart capability";
            type empty;
          }
        }
      }
      leaf restart-duration {
        description "Maximum time for graceful restart to finish (seconds)";
        units seconds;
        type union {
          type string {
            pattern "<.*>|$.*";
          }
          type uint32 {
            range "30 .. 300";
          }
        }
      }
      leaf no-bidirectional-mode {
        description "Disable PIM graceful restart for bidirectional mode";
        type empty;
      }
      leaf restart-complete-duration {
        description "Maximum time for graceful restart to complete (seconds)";
        units seconds;
        type union {
          type string {
            pattern "<.*>|$.*";
          }
          type uint32 {
            range "5 .. 300";
          }
        }
      }
    }
    container join-load-balance {
      presence "enable join-load-balance";
      description "Configure PIM join load balancing";
      leaf automatic {
        description "Enable automatic PIM join load balancing";
        type empty;
      }
    }
    leaf standby-path-creation-delay {
      description "Amount of time to wait before creating standby path";
      units seconds;
      type union {
        type string {
          pattern "<.*>|$.*";
        }
        type uint32 {
          range "1 .. 300";
        }
      }
    }
    leaf idle-standby-path-switchover-delay {
      description "Amount of time to wait before switching over to idle standby path";
      units seconds;
      type union {
        type string {
          pattern "<.*>|$.*";
        }
        type uint32 {
          range "1 .. 300";
        }
      }
    }
    leaf dr-election-on-p2p {
      description "Enable DR election on Point-to-Point Interfaces";
      type empty;
    }
    leaf no-wildcard-register-stop {
      description "Disable sending of wildcard register stop message";
      type empty;
    }
    leaf nexthop-hold-time {
      description "Nexthop hold time in milliseconds";
      units milliseconds;
      type union {
        type string {
          pattern "<.*>|$.*";
        }
        type uint32 {
          range "1 .. 1000";
        }
      }
    }
    leaf mpls-internet-multicast {
      description "Enable support for Internet Multicast over MPLS";
      type empty;
    }
    container join-make-before-break {
      description "Enable PIM Join Make-Before-Break during RPF neighbor change";
      choice enable-disable {
        case case_1 {
          leaf disable {
            description "Disable Make-Before-Break for PIM RPF neighbor change";
            type empty;
          }
        }
      }
    }
    leaf reset-tracking-bit {
      description "Clear tracking-bit in PIM Hello LAN Prune Delay Option";
      type empty;
    }
    leaf propagation-delay {
      description "Propagation delay value";
      default "500";
      units milliseconds;
      type union {
        type string {
          pattern "<.*>|$.*";
        }
        type uint32 {
          range "250 .. 2000";
        }
      }
    }
    leaf override-interval {
      description "Override interval value";
      default "2000";
      units milliseconds;
      type union {
        type string {
          pattern "<.*>|$.*";
        }
        type uint32 {
          range "500 .. 6000";
        }
      }
    }
    leaf disable-packet-register {
      description "Disable PIM packet registers on first hop router";
      type empty;
    }
    container default-vpn-source {
      presence "enable default-vpn-source";
      description "Let all VRFs use master loopback address for mt interfaces";
      leaf interface-name {
        description "Master loopback interface name";
        type union {
          type jt:interface-unit;
          type string {
            pattern "<.*>|$.*";
          }
        }
      }
    }
  }
  grouping juniper-protocols-protection-group {
    container ethernet-aps {
      description "Ethernet APS configuration";
      uses juniper-protocols-protection-group-eaps;
    }
    container traceoptions {
      description "Tracing options for debugging protocol operation";
      uses erp-trace-options;
    }
    leaf restore-interval {
      description "Wait to restore interval";
      default "5";
      units minutes;
      type union {
        type string {
          pattern "<.*>|$.*";
        }
        type uint32 {
          range "1 .. 12";
        }
      }
    }
    leaf guard-interval {
      description "Guard timer interval in 10ms steps";
      default "500";
      units milliseconds;
      type union {
        type string {
          pattern "<.*>|$.*";
        }
        type uint32 {
          range "10 .. 2000";
        }
      }
    }
    leaf hold-interval {
      description "Hold off timer interval in 100ms steps";
      default "0";
      units milliseconds;
      type union {
        type string {
          pattern "<.*>|$.*";
        }
        type uint32 {
          range "0 .. 10000";
        }
      }
    }
    list ethernet-ring {
      key name;
      ordered-by user;
      description "Ethernet ring";
      uses juniper-protocols-protection-group-ethernet-ring;
    }
  }
  grouping erp-trace-options {
    description "Trace options for Ethernet Ring Protocol";
    list flag {
      key name;
      ordered-by user;
      description "Tracing parameters";
      leaf name {
        type enumeration {
          enum events {
            description "Trace events to the protocol state machine";
          }
          enum pdu {
            description "Trace R-APS PDU reception and transmission";
          }
          enum timers {
            description "Trace protocol timers";
          }
          enum state-machine {
            description "Trace R-APS state machine";
          }
          enum periodic-packet-management {
            description "Trace periodic packet management state and events";
          }
          enum config {
            description "Trace protocol configuration";
          }
          enum normal {
            description "Trace protocol general log messages";
          }
          enum debug {
            description "Trace protocol debug log messages";
          }
          enum all {
            description "Trace all";
          }
        }
      }
    }
    container file {
      description "Trace file options";
      leaf filename {
        description "Name of file in which to write trace information";
        type string {
          length "1 .. 1024";
        }
      }
      leaf replace {
        description "Replace trace file rather than appending to it";
        status deprecated;
        type empty;
      }
      leaf size {
        description "Maximum trace file size";
        type string;
      }
      leaf files {
        description "Maximum number of trace files";
        default "10";
        type union {
          type string {
            pattern "<.*>|$.*";
          }
          type uint32 {
            range "2 .. 1000";
          }
        }
      }
      leaf no-stamp {
        description "Do not timestamp trace file";
        status deprecated;
        type empty;
      }
      choice world-readable-choice {
        leaf world-readable {
          description "Allow any user to read the log file";
          type empty;
        }
        leaf no-world-readable {
          description "Don't allow any user to read the log file";
          type empty;
        }
      }
    }
  }
  grouping juniper-protocols-protection-group-eaps {
    list profile {
      key name;
      uses juniper-protocols-protection-group-eaps-profile;
    }
  }
  grouping juniper-protocols-protection-group-eaps-profile {
    description "Ethernet APS profile";
    leaf name {
      description "Profile name";
      type string {
        length "1 .. 32";
      }
    }
    leaf protocol {
      description "Protocol value";
      type enumeration {
        enum ccm {
          description "Use CCM packets for protection.";
        }
        enum G.8031 {
          description "Use G.8031 packets for protection.";
        }
      }
    }
    leaf revert-time {
      description "Reversion time in minutes, 0 would mean no reversion";
      default "4";
      units minutes;
      type union {
        type string {
          pattern "<.*>|$.*";
        }
        type uint32 {
          range "0 .. 15";
        }
      }
    }
    leaf hold-time {
      description "Hold time in seconds";
      default "0";
      units "milli seconds";
      type union {
        type string {
          pattern "<.*>|$.*";
        }
        type uint32 {
          range "0 .. 10000";
        }
      }
    }
    leaf local-request {
      description "Local APS request";
      type enumeration {
        enum lockout {
          description "Lockout protection";
        }
      }
    }
  }
  grouping juniper-protocols-protection-group-ethernet-ring {
    description "Ethernet Ring protection group configuration";
    leaf name {
      description "Name of Ethernet Ring protection group";
      type string {
        length "1 .. 32";
      }
    }
    leaf node-id {
      description "Node ID of the protection group, by default bridge's MAC";
      type jt:mac-unicast;
    }
    leaf ring-protection-link-owner {
      description "Ring protection link owner flag, one ring should have only one node as a ring protection link owner";
      type empty;
    }
    leaf level {
      description "MPG Level value for R-APS PDU";
      type union {
        type string {
          pattern "<.*>|$.*";
        }
        type uint32 {
          range "0 .. 7";
        }
      }
    }
    leaf restore-interval {
      description "Wait to restore interval";
      units minutes;
      type union {
        type string {
          pattern "<.*>|$.*";
        }
        type uint32 {
          range "1 .. 12";
        }
      }
    }
    leaf guard-interval {
      description "Guard timer interval in 10ms";
      units milliseconds;
      type union {
        type string {
          pattern "<.*>|$.*";
        }
        type uint32 {
          range "10 .. 2000";
        }
      }
    }
    leaf hold-interval {
      description "Hold off timer interval in 100ms steps";
      units milliseconds;
      type union {
        type string {
          pattern "<.*>|$.*";
        }
        type uint32 {
          range "0 .. 10000";
        }
      }
    }
    leaf non-revertive {
      description "Non-revertive mode of operation";
      type empty;
    }
    leaf wait-to-block-interval {
      description "Wait to block interval";
      default "5";
      units seconds;
      type union {
        type string {
          pattern "<.*>|$.*";
        }
        type uint32 {
          range "5 .. 10";
        }
      }
    }
    leaf major-ring-name {
      description "Name of major-ring to which this sub-ring node attached";
      type string {
        length "1 .. 32";
      }
    }
    leaf propagate-tc {
      description "Enable Topology Change Propagation to major-ring from the sub-ring";
      type empty;
    }
    leaf compatibility-version {
      description "G.8032 compatibility version";
      default "2";
      type union {
        type string {
          pattern "<.*>|$.*";
        }
        type uint32 {
          range "1 .. 2";
        }
      }
    }
    leaf ring-id {
      description "Ethernet Ring ID of protection group";
      default "1";
      type union {
        type string {
          pattern "<.*>|$.*";
        }
        type uint32 {
          range "1 .. 239";
        }
      }
    }
    leaf non-vc-mode {
      description "Node is operating in non virtual channel mode";
      type empty;
    }
    leaf dot1p-priority {
      description "IEEE 802.1p priority of transmitted R-APS";
      default "0";
      type union {
        type string {
          pattern "<.*>|$.*";
        }
        type uint32 {
          range "0 .. 7";
        }
      }
    }
    container east-interface {
      description "East interface configuration";
      presence "enable east-interface";
      uses erp-interface;
    }
    container west-interface {
      description "West interface configuration";
      presence "enable west-interface";
      uses erp-interface;
    }
    leaf control-vlan {
      description "Dedicated VLAN identifier - VLAN id or VLAN name";
      type string;
    }
    container data-channel {
      description "Ring instance data channel";
      presence "enable data-channel";
      uses erp-data-channel;
    }
  }
  grouping erp-data-channel {
    leaf-list vlan {
      ordered-by user;
      description "VLAN ID or VLAN ID range [1..4094]";
      type string;
    }
  }
  grouping erp-interface {
    container control-channel {
      presence "enable control-channel";
      description "Control channel of ring port";
      leaf vlan {
        description "Dedicated VLAN identifier";
        type union {
          type string {
            pattern "<.*>|$.*";
          }
          type uint16 {
            range "1 .. 4094";
          }
        }
      }
      leaf control-channel-name {
        type union {
          type jt:interface-name;
          type string {
            pattern "<.*>|$.*";
          }
        }
      }
    }
    leaf ring-protection-link-end {
      description "Port is connecting to ring protection link";
      type empty;
    }
    leaf interface-none {
      description "Port is not used";
      type empty;
    }
  }
  grouping juniper-protocols-rip {
    container traceoptions {
      description "Trace options for RIP";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum auth {
              description "Trace RIP authentication";
            }
            enum error {
              description "Trace RIP errors";
            }
            enum expiration {
              description "Trace RIP route expiration processing";
            }
            enum holddown {
              description "Trace RIP hold-down processing";
            }
            enum packets {
              description "Trace all RIP packets";
            }
            enum request {
              description "Trace RIP information packets";
            }
            enum trigger {
              description "Trace RIP triggered updates";
            }
            enum update {
              description "Trace RIP update packets";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
        container filter {
          description "Filter to apply to this flag";
          presence "enable filter";
          uses rip_filter_obj;
        }
      }
    }
    container rib-group {
      description "Routing table group for importing RIP routes";
      uses rib_group_inet_type;
    }
    leaf metric-in {
      description "Metric value to add to incoming routes";
      type union {
        type string {
          pattern "<.*>|$.*";
        }
        type uint32 {
          range "1 .. 15";
        }
      }
    }
    container send {
      description "Configure RIP send options";
      choice send-opts {
        case case_1 {
          leaf broadcast {
            description "Broadcast RIPv2 packets (RIPv1 compatible)";
            type empty;
          }
        }
        case case_2 {
          leaf multicast {
            description "Multicast RIPv2 packets";
            type empty;
          }
        }
        case case_3 {
          leaf none {
            description "Do not send RIP updates";
            type empty;
          }
        }
        case case_4 {
          leaf version-1 {
            description "Broadcast RIPv1 packets";
            type empty;
          }
        }
      }
    }
    container receive {
      description "Configure RIP receive options";
      choice receive-opts {
        case case_1 {
          leaf both {
            description "Accept both RIPv1 and RIPv2 packets";
            type empty;
          }
        }
        case case_2 {
          leaf none {
            description "Do not receive RIP packets";
            type empty;
          }
        }
        case case_3 {
          leaf version-1 {
            description "Accept RIPv1 packets only";
            type empty;
          }
        }
        case case_4 {
          leaf version-2 {
            description "Accept only RIPv2 packets";
            type empty;
          }
        }
      }
    }
    choice check-zero-choice {
      leaf check-zero {
        description "Check reserved fields on incoming RIPv2 packets";
        type empty;
      }
      leaf no-check-zero {
        description "Don't check reserved fields on incoming RIPv2 packets";
        type empty;
      }
    }
    leaf message-size {
      description "Number of route entries per update message";
      type union {
        type string {
          pattern "<.*>|$.*";
        }
        type uint32 {
          range "25 .. 255";
        }
      }
    }
    leaf-list import {
      ordered-by user;
      description "Import policy";
      type jt:policy-algebra;
    }
    leaf holddown {
      description "Hold-down time";
      units seconds;
      type union {
        type string {
          pattern "<.*>|$.*";
        }
        type uint32 {
          range "10 .. 180";
        }
      }
    }
    leaf route-timeout {
      description "Delay before routes time out";
      units seconds;
      type union {
        type string {
          pattern "<.*>|$.*";
        }
        type uint32 {
          range "30 .. 360";
        }
      }
    }
    leaf update-interval {
      description "Interval between regular route updates";
      units seconds;
      type union {
        type string {
          pattern "<.*>|$.*";
        }
        type uint32 {
          range "10 .. 60";
        }
      }
    }
    choice authentication {
      case case_1 {
        leaf authentication-type {
          type enumeration {
            enum none {
              description "No authentication";
            }
            enum simple {
              description "Simple password authentication";
            }
            enum md5 {
              description "MD5 authentication";
            }
          }
        }
      }
      case case_2 {
        list authentication-selective-md5 {
          key name;
          ordered-by user;
          description "MD5 authentication with one or more keys";
          leaf name {
            description "Key ID for MD5 authentication";
            type union {
              type string {
                pattern "<.*>|$.*";
              }
              type uint32 {
                range "0 .. 255";
              }
            }
          }
          leaf key {
            description "MD5 authentication key value";
            type jt:unreadable;
          }
          leaf start-time {
            description "Start time for key transmission (YYYY-MM-DD.HH:MM)";
            type jt:time;
          }
        }
      }
    }
    leaf authentication-key {
      description "Authentication key (password)";
      type jt:unreadable;
    }
    list group {
      key name;
      ordered-by user;
      description "Instance configuration";
      leaf name {
        description "Group name";
        type string;
      }
      leaf route-timeout {
        description "Delay before routes time out";
        units seconds;
        type union {
          type string {
            pattern "<.*>|$.*";
          }
          type uint32 {
            range "30 .. 360";
          }
        }
      }
      leaf update-interval {
        description "Interval between regular route updates";
        units seconds;
        type union {
          type string {
            pattern "<.*>|$.*";
          }
          type uint32 {
            range "10 .. 60";
          }
        }
      }
      leaf preference {
        description "Preference of routes learned by this group";
        type union {
          type uint32;
          type string {
            pattern "<.*>|$.*";
          }
        }
      }
      leaf metric-out {
        description "Default metric of exported routes";
        type union {
          type string {
            pattern "<.*>|$.*";
          }
          type uint32 {
            range "1 .. 15";
          }
        }
      }
      leaf-list export {
        ordered-by user;
        description "Export policy";
        type jt:policy-algebra;
      }
      leaf-list import {
        ordered-by user;
        description "Import policy";
        type jt:policy-algebra;
      }
      leaf demand-circuit {
        description "Enable demand circuit on this interface";
        type empty;
      }
      leaf max-retrans-time {
        description "Maximum time to re-transmit a message in demand-circuit";
        type union {
          type string {
            pattern "<.*>|$.*";
          }
          type uint32 {
            range "5 .. 180";
          }
        }
      }
      container bfd-liveness-detection {
        description "Bidirectional Forwarding Detection options";
        leaf version {
          description "BFD protocol version number";
          default "automatic";
          type enumeration {
            enum 0 {
              description "BFD version 0 (deprecated)";
            }
            enum 1 {
              description "BFD version 1";
            }
            enum automatic {
              description "Choose BFD version automatically";
            }
          }
        }
        leaf minimum-interval {
          description "Minimum transmit and receive interval";
          units milliseconds;
          type union {
            type string {
              pattern "<.*>|$.*";
            }
            type uint32 {
              range "1 .. 255000";
            }
          }
        }
        leaf minimum-transmit-interval {
          description "Minimum transmit interval";
          status deprecated;
          units milliseconds;
          type union {
            type string {
              pattern "<.*>|$.*";
            }
            type uint32 {
              range "1 .. 255000";
            }
          }
        }
        leaf minimum-receive-interval {
          description "Minimum receive interval";
          units milliseconds;
          type union {
            type string {
              pattern "<.*>|$.*";
            }
            type uint32 {
              range "1 .. 255000";
            }
          }
        }
        leaf multiplier {
          description "Detection time multiplier";
          default "3";
          type union {
            type string {
              pattern "<.*>|$.*";
            }
            type uint32 {
              range "1 .. 255";
            }
          }
        }
        leaf inline-disable {
          description "Disable inline mode for this BFD session";
          type empty;
        }
        leaf pdu-size {
          description "BFD transport protocol payload size";
          default "24";
          type union {
            type string {
              pattern "<.*>|$.*";
            }
            type uint32 {
              range "24 .. 9000";
            }
          }
        }
        choice adaptation-choice {
          case case_1 {
            leaf no-adaptation {
              description "Disable adaptation";
              type empty;
            }
          }
        }
        container transmit-interval {
          description "Transmit-interval options";
          leaf minimum-interval {
            description "Minimum transmit interval";
            units milliseconds;
            type union {
              type string {
                pattern "<.*>|$.*";
              }
              type uint32 {
                range "1 .. 255000";
              }
            }
          }
          leaf threshold {
            description "High transmit interval triggering a trap";
            units milliseconds;
            type union {
              type uint32;
              type string {
                pattern "<.*>|$.*";
              }
            }
          }
        }
        container detection-time {
          description "Detection-time options";
          leaf threshold {
            description "High detection-time triggering a trap";
            units milliseconds;
            type union {
              type uint32;
              type string {
                pattern "<.*>|$.*";
              }
            }
          }
        }
        container authentication {
          description "Authentication options";
          leaf key-chain {
            description "Key chain name";
            type string;
          }
          leaf algorithm {
            description "Algorithm name";
            type enumeration {
              enum simple-password {
                description "Simple password";
              }
              enum keyed-md5 {
                description "Keyed message Digest 5";
              }
              enum meticulous-keyed-md5 {
                description "Meticulous keyed message Digest 5";
              }
              enum keyed-sha-1 {
                description "Keyed secure hash algorithm (SHA1) ";
              }
              enum meticulous-keyed-sha-1 {
                description "Meticulous keyed secure hash algorithm (SHA1) ";
              }
            }
          }
          leaf loose-check {
            description "Verify authentication only if authentication is negotiated";
            type empty;
          }
        }
      }
      list neighbor {
        key name;
        ordered-by user;
        description "Neighbor configuration";
        leaf name {
          description "Interface name";
          type union {
            type jt:interface-name;
            type string {
              pattern "<.*>|$.*";
            }
          }
        }
        leaf route-timeout {
          description "Delay before routes time out";
          units seconds;
          type union {
            type string {
              pattern "<.*>|$.*";
            }
            type uint32 {
              range "30 .. 360";
            }
          }
        }
        leaf update-interval {
          description "Interval between regular route updates";
          units seconds;
          type union {
            type string {
              pattern "<.*>|$.*";
            }
            type uint32 {
              range "10 .. 60";
            }
          }
        }
        leaf interface-type {
          description "Interface type for the neighbor";
          type enumeration {
            enum p2mp {
              description "Point-to-multipoint link";
            }
          }
        }
        leaf dynamic-peers {
          description "Learn peers dynamically on a p2mp interface";
          type empty;
        }
        list peer {
          key name;
          ordered-by user;
          description "P2MP peer";
          leaf name {
            description "Address of peer";
            type jt:ipaddr;
          }
        }
        leaf metric-in {
          description "Metric value to add to incoming routes";
          type union {
            type string {
              pattern "<.*>|$.*";
            }
            type uint32 {
              range "1 .. 15";
            }
          }
        }
        container send {
          description "Configure RIP send options";
          choice send-opts {
            case case_1 {
              leaf broadcast {
                description "Broadcast RIPv2 packets (RIPv1 compatible)";
                type empty;
              }
            }
            case case_2 {
              leaf multicast {
                description "Multicast RIPv2 packets";
                type empty;
              }
            }
            case case_3 {
              leaf none {
                description "Do not send RIP updates";
                type empty;
              }
            }
            case case_4 {
              leaf version-1 {
                description "Broadcast RIPv1 packets";
                type empty;
              }
            }
          }
        }
        container receive {
          description "Configure RIP receive options";
          choice receive-opts {
            case case_1 {
              leaf both {
                description "Accept both RIPv1 and RIPv2 packets";
                type empty;
              }
            }
            case case_2 {
              leaf none {
                description "Do not receive RIP packets";
                type empty;
              }
            }
            case case_3 {
              leaf version-1 {
                description "Accept RIPv1 packets only";
                type empty;
              }
            }
            case case_4 {
              leaf version-2 {
                description "Accept only RIPv2 packets";
                type empty;
              }
            }
          }
        }
        leaf demand-circuit {
          description "Enable demand circuit on this interface";
          type empty;
        }
        leaf max-retrans-time {
          description "Maximum time to re-transmit a msg in demand-circuit";
          type union {
            type string {
              pattern "<.*>|$.*";
            }
            type uint32 {
              range "5 .. 180";
            }
          }
        }
        choice check-zero-choice {
          leaf check-zero {
            description "Check reserved fields on incoming RIPv1 packets";
            type empty;
          }
          leaf no-check-zero {
            description "Don't check reserved fields on incoming RIPv1 packets";
            type empty;
          }
        }
        leaf any-sender {
          description "Disable strict checks on sender address";
          type empty;
        }
        leaf message-size {
          description "Number of route entries per update message";
          type union {
            type string {
              pattern "<.*>|$.*";
            }
            type uint32 {
              range "25 .. 255";
            }
          }
        }
        leaf-list import {
          ordered-by user;
          description "Import policy";
          type jt:policy-algebra;
        }
        choice authentication {
          case case_1 {
            leaf authentication-type {
              type enumeration {
                enum none {
                  description "No authentication";
                }
                enum simple {
                  description "Simple password authentication";
                }
                enum md5 {
                  description "MD5 authentication";
                }
              }
            }
          }
          case case_2 {
            list authentication-selective-md5 {
              key name;
              ordered-by user;
              description "MD5 authentication with one or more keys";
              leaf name {
                description "Key ID for MD5 authentication";
                type union {
                  type string {
                    pattern "<.*>|$.*";
                  }
                  type uint32 {
                    range "0 .. 255";
                  }
                }
              }
              leaf key {
                description "MD5 authentication key value";
                type jt:unreadable;
              }
              leaf start-time {
                description "Start time for key transmission (YYYY-MM-DD.HH:MM)";
                type jt:time;
              }
            }
          }
        }
        leaf authentication-key {
          description "Authentication key (password)";
          type jt:unreadable;
        }
        container bfd-liveness-detection {
          description "Bidirectional Forwarding Detection options";
          leaf version {
            description "BFD protocol version number";
            default "automatic";
            type enumeration {
              enum 0 {
                description "BFD version 0 (deprecated)";
              }
              enum 1 {
                description "BFD version 1";
              }
              enum automatic {
                description "Choose BFD version automatically";
              }
            }
          }
          leaf minimum-interval {
            description "Minimum transmit and receive interval";
            units milliseconds;
            type union {
              type string {
                pattern "<.*>|$.*";
              }
              type uint32 {
                range "1 .. 255000";
              }
            }
          }
          leaf minimum-transmit-interval {
            description "Minimum transmit interval";
            status deprecated;
            units milliseconds;
            type union {
              type string {
                pattern "<.*>|$.*";
              }
              type uint32 {
                range "1 .. 255000";
              }
            }
          }
          leaf minimum-receive-interval {
            description "Minimum receive interval";
            units milliseconds;
            type union {
              type string {
                pattern "<.*>|$.*";
              }
              type uint32 {
                range "1 .. 255000";
              }
            }
          }
          leaf multiplier {
            description "Detection time multiplier";
            default "3";
            type union {
              type string {
                pattern "<.*>|$.*";
              }
              type uint32 {
                range "1 .. 255";
              }
            }
          }
          leaf inline-disable {
            description "Disable inline mode for this BFD session";
            type empty;
          }
          leaf pdu-size {
            description "BFD transport protocol payload size";
            default "24";
            type union {
              type string {
                pattern "<.*>|$.*";
              }
              type uint32 {
                range "24 .. 9000";
              }
            }
          }
          choice adaptation-choice {
            case case_1 {
              leaf no-adaptation {
                description "Disable adaptation";
                type empty;
              }
            }
          }
          container transmit-interval {
            description "Transmit-interval options";
            leaf minimum-interval {
              description "Minimum transmit interval";
              units milliseconds;
              type union {
                type string {
                  pattern "<.*>|$.*";
                }
                type uint32 {
                  range "1 .. 255000";
                }
              }
            }
            leaf threshold {
              description "High transmit interval triggering a trap";
              units milliseconds;
              type union {
                type uint32;
                type string {
                  pattern "<.*>|$.*";
                }
              }
            }
          }
          container detection-time {
            description "Detection-time options";
            leaf threshold {
              description "High detection-time triggering a trap";
              units milliseconds;
              type union {
                type uint32;
                type string {
                  pattern "<.*>|$.*";
                }
              }
            }
          }
          container authentication {
            description "Authentication options";
            leaf key-chain {
              description "Key chain name";
              type string;
            }
            leaf algorithm {
              description "Algorithm name";
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
            }
            leaf loose-check {
              description "Verify authentication only if authentication is negotiated";
              type empty;
            }
          }
        }
      }
    }
    container graceful-restart {
      presence "enable graceful-restart";
      description "RIP graceful restart options";
      choice enable-disable {
        case case_1 {
          leaf disable {
            description "Disable graceful restart";
            type empty;
          }
        }
      }
      leaf restart-time {
        description "Time after which RIP is declared out of restart";
        type union {
          type string {
            pattern "<.*>|$.*";
          }
          type uint32 {
            range "1 .. 600";
          }
        }
      }
    }
  }
  grouping juniper-protocols-ripng {
    container traceoptions {
      description "Trace options for RIPng";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum error {
              description "Trace RIPng errors";
            }
            enum expiration {
              description "Trace RIPng route expiration processing";
            }
            enum holddown {
              description "Trace RIPng hold-down processing";
            }
            enum packets {
              description "Trace all RIPng packets";
            }
            enum request {
              description "Trace RIPng information packets";
            }
            enum trigger {
              description "Trace RIPng triggered updates";
            }
            enum update {
              description "Trace RIPng update packets";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf metric-in {
      description "Metric value to add to incoming routes";
      type union {
        type string {
          pattern "<.*>|$.*";
        }
        type uint32 {
          range "1 .. 15";
        }
      }
    }
    container send {
      description "Configure RIPng send options";
      choice send-opts {
        case case_1 {
          leaf none {
            description "Do not send RIPng updates";
            type empty;
          }
        }
      }
    }
    container receive {
      description "Configure RIPng receive options";
      choice receive-opts {
        case case_1 {
          leaf none {
            description "Do not receive RIPng packets";
            type empty;
          }
        }
      }
    }
    leaf-list import {
      ordered-by user;
      description "Import policy";
      type jt:policy-algebra;
    }
    leaf holddown {
      description "Hold-down time";
      units seconds;
      type union {
        type string {
          pattern "<.*>|$.*";
        }
        type uint32 {
          range "10 .. 180";
        }
      }
    }
    leaf route-timeout {
      description "Delay before routes time out";
      units seconds;
      type union {
        type string {
          pattern "<.*>|$.*";
        }
        type uint32 {
          range "30 .. 360";
        }
      }
    }
    leaf update-interval {
      description "Interval between regular route updates";
      units seconds;
      type union {
        type string {
          pattern "<.*>|$.*";
        }
        type uint32 {
          range "10 .. 60";
        }
      }
    }
    list group {
      key name;
      ordered-by user;
      description "Instance configuration";
      leaf name {
        description "Group name";
        type string;
      }
      leaf route-timeout {
        description "Delay before routes time out";
        units seconds;
        type union {
          type string {
            pattern "<.*>|$.*";
          }
          type uint32 {
            range "30 .. 360";
          }
        }
      }
      leaf update-interval {
        description "Interval between regular route updates";
        units seconds;
        type union {
          type string {
            pattern "<.*>|$.*";
          }
          type uint32 {
            range "10 .. 60";
          }
        }
      }
      leaf preference {
        description "Preference of routes learned by this group";
        type union {
          type uint32;
          type string {
            pattern "<.*>|$.*";
          }
        }
      }
      leaf metric-out {
        description "Default metric of exported routes";
        type union {
          type string {
            pattern "<.*>|$.*";
          }
          type uint32 {
            range "1 .. 15";
          }
        }
      }
      leaf-list export {
        ordered-by user;
        description "Export policy";
        type jt:policy-algebra;
      }
      leaf-list import {
        ordered-by user;
        description "Import policy";
        type jt:policy-algebra;
      }
      list neighbor {
        key name;
        ordered-by user;
        description "Neighbor configuration";
        leaf name {
          description "Interface name";
          type union {
            type jt:interface-name;
            type string {
              pattern "<.*>|$.*";
            }
          }
        }
        leaf route-timeout {
          description "Delay before routes time out";
          units seconds;
          type union {
            type string {
              pattern "<.*>|$.*";
            }
            type uint32 {
              range "30 .. 360";
            }
          }
        }
        leaf update-interval {
          description "Interval between regular route updates";
          units seconds;
          type union {
            type string {
              pattern "<.*>|$.*";
            }
            type uint32 {
              range "10 .. 60";
            }
          }
        }
        leaf metric-in {
          description "Metric value to add to incoming routes";
          type union {
            type string {
              pattern "<.*>|$.*";
            }
            type uint32 {
              range "1 .. 15";
            }
          }
        }
        container send {
          description "Configure RIPng send options";
          choice send-opts {
            case case_1 {
              leaf none {
                description "Do not send RIPng updates";
                type empty;
              }
            }
          }
        }
        container receive {
          description "Configure RIPng receive options";
          choice receive-opts {
            case case_1 {
              leaf none {
                description "Do not receive RIPng packets";
                type empty;
              }
            }
          }
        }
        leaf-list import {
          ordered-by user;
          description "Import policy";
          type jt:policy-algebra;
        }
      }
    }
    container graceful-restart {
      presence "enable graceful-restart";
      description "RIPng graceful restart options";
      choice enable-disable {
        case case_1 {
          leaf disable {
            description "Disable graceful restart";
            type empty;
          }
        }
      }
      leaf restart-time {
        description "Time after which RIPng is declared out of restart";
        type union {
          type string {
            pattern "<.*>|$.*";
          }
          type uint32 {
            range "1 .. 600";
          }
        }
      }
    }
  }
  grouping juniper-protocols-router-discovery {
    choice enable-disable {
      case case_1 {
        leaf disable {
          description "Disable router discovery";
          type empty;
        }
      }
    }
    container traceoptions {
      description "Trace options for router discovery";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
      }
    }
    list interface {
      key name;
      ordered-by user;
      description "Interfaces on which to configure router discovery";
      leaf name {
        description "Interface name";
        type union {
          type jt:interface-name;
          type string {
            pattern "<.*>|$.*";
          }
        }
      }
      leaf max-advertisement-interval {
        description "Maximum time before sending advertisements";
        units seconds;
        type union {
          type string {
            pattern "<.*>|$.*";
          }
          type uint32 {
            range "4 .. 1800";
          }
        }
      }
      leaf min-advertisement-interval {
        description "Minimum time before sending advertisements";
        units seconds;
        type union {
          type string {
            pattern "<.*>|$.*";
          }
          type uint32 {
            range "3 .. 1800";
          }
        }
      }
      leaf lifetime {
        description "How long addresses in advertisements are valid";
        units seconds;
        type union {
          type string {
            pattern "<.*>|$.*";
          }
          type uint32 {
            range "3 .. 9000";
          }
        }
      }
    }
    list address {
      key name;
      ordered-by user;
      description "IP addresses to include in advertisements";
      leaf name {
        description "IP addresses to include in router advertisements";
        type jt:ipv4addr;
      }
      leaf advertise {
        description "Advertise the IP address in advertisements";
        type empty;
      }
      leaf ignore {
        description "Do not advertise the IP address in advertisements";
        type empty;
      }
      leaf broadcast {
        description "Include IP address only in broadcast advertisements";
        type empty;
      }
      leaf multicast {
        description "Include IP address only in multicast advertisements";
        type empty;
      }
      leaf ineligible {
        description "IP address can never become a default router";
        type empty;
      }
      leaf priority {
        description "Preference of the address to become a default router";
        type union {
          type int32;
          type string {
            pattern "<.*>|$.*";
          }
        }
      }
    }
  }
  grouping juniper-protocols-rsvp {
    description "RSVP options";
    choice enable-disable {
      case case_1 {
        leaf disable {
          description "Disable RSVP";
          type empty;
        }
      }
    }
    container graceful-restart {
      description "Configure graceful restart attributes";
      choice enable-disable {
        case case_1 {
          leaf disable {
            description "Disable RSVP graceful restart capability";
            type empty;
          }
        }
      }
      leaf helper-disable {
        description "Disable graceful restart helper capability";
        type empty;
      }
      leaf maximum-helper-restart-time {
        description "Maximum wait time from down event to neighbor dead";
        default "20";
        units seconds;
        type union {
          type string {
            pattern "<.*>|$.*";
          }
          type uint32 {
            range "1 .. 1800";
          }
        }
      }
      leaf maximum-helper-recovery-time {
        description "Maximum time restarting neighbor states are kept";
        default "180";
        units seconds;
        type union {
          type string {
            pattern "<.*>|$.*";
          }
          type uint32 {
            range "1 .. 3600";
          }
        }
      }
    }
    container tunnel-services {
      presence "enable tunnel-services";
      description "Use tunnel services for P2MP LSP ultimate-hop popping";
      leaf-list devices {
        ordered-by user;
        description "Tunnel services devices to use for P2MP LSPs";
        type union {
          type jt:interface-device;
          type string {
            pattern "<.*>|$.*";
          }
        }
      }
    }
    leaf no-p2mp-sublsp {
      description "Disable P2MP sub-LSP object generation";
      type empty;
    }
    leaf no-node-id-subobject {
      description "Do not include the node-id sub-object in the RRO";
      type empty;
    }
    leaf no-interface-hello {
      description "Disble interface Hellos on all RSVP interfaces";
      type empty;
    }
    container pop-and-forward {
      description "RSVP pop-and-forward specific global parameters";
      container application-label {
        description "Number of application labels under the RSVP transport";
        leaf depth {
          description "Application label depth";
          default "1";
          type union {
            type string {
              pattern "<.*>|$.*";
            }
            type uint32 {
              range "0 .. 3";
            }
          }
        }
      }
    }
    leaf hello-acknowledgements {
      description "Acknowledge Hellos on RSVP interfaces not having sessions";
      type empty;
    }
    leaf no-hello-acknowledgements {
      description "Do not ack Hellos on RSVP interfaces not having sessions";
      type empty;
    }
    container node-hello {
      presence "enable node-hello";
      description "Enable node-ID based Hellos on all RSVP interfaces";
      leaf hello-interval {
        description "Hello interval";
        default "9";
        units seconds;
        type union {
          type string {
            pattern "<.*>|$.*";
          }
          type uint32 {
            range "0 .. 60";
          }
        }
      }
    }
    leaf no-node-hello {
      description "Disable node-ID based Hellos on the router";
      type empty;
    }
    leaf allow-bidirectional {
      description "Enable bidirectional support in RSVP";
      status deprecated;
      type empty;
    }
    leaf local-reversion {
      description "Enable local reversion at this Point of Local Repair";
      type empty;
    }
    leaf no-local-reversion {
      description "Disable local reversion at this Point of Local Repair";
      type empty;
    }
    leaf rfc6510-lsp-attributes {
      description "Use RFC6510 compliant LSP_ATTRIBUTES";
      type empty;
    }
    container fast-reroute {
      description "One-to-one fast-reroute protection mechanism";
      leaf optimize-timer {
        description "Frequency of reoptimization for fast-reroute detour";
        units seconds;
        type union {
          type string {
            pattern "<.*>|$.*";
          }
          type int32 {
            range "0 .. 65535";
          }
        }
      }
    }
    container load-balance {
      description "Per-packet load-balancing algorithm";
      leaf bandwidth {
        description "Per-packet load balancing proportional to LSP bandwidth";
        type empty;
      }
    }
    container traceoptions {
      description "Trace options for RSVP";
      container file {
        description "Trace file options";
        leaf filename {
          description "Name of file in which to write trace information";
          type string {
            length "1 .. 1024";
          }
        }
        leaf replace {
          description "Replace trace file rather than appending to it";
          status deprecated;
          type empty;
        }
        leaf size {
          description "Maximum trace file size";
          type string;
        }
        leaf files {
          description "Maximum number of trace files";
          default "10";
          type union {
            type string {
              pattern "<.*>|$.*";
            }
            type uint32 {
              range "2 .. 1000";
            }
          }
        }
        leaf no-stamp {
          description "Do not timestamp trace file";
          status deprecated;
          type empty;
        }
        choice world-readable-choice {
          leaf world-readable {
            description "Allow any user to read the log file";
            type empty;
          }
          leaf no-world-readable {
            description "Don't allow any user to read the log file";
            type empty;
          }
        }
      }
      list flag {
        key name;
        ordered-by user;
        description "Tracing parameters";
        leaf name {
          type enumeration {
            enum io-event {
              description "Trace RSVP IO task related events";
            }
            enum io-packets {
              description "Trace all RSVP periodic refresh activity";
            }
            enum packets {
              description "Trace all RSVP trigger packets";
            }
            enum path {
              description "Trace RSVP trigger path messages";
            }
            enum resv {
              description "Trace RSVP trigger Resv messages";
            }
            enum pathtear {
              description "Trace RSVP PathTear messages";
            }
            enum resvtear {
              description "Trace RSVP ResvTear messages";
            }
            enum state {
              description "Trace state transitions";
            }
            enum error {
              description "Trace error conditions";
            }
            enum route {
              description "Trace routing information";
            }
            enum lmp {
              description "Trace RSVP-LMP related interactions";
            }
            enum event {
              description "Trace RSVP related events";
            }
            enum nsr-synchronization {
              description "Trace NSR synchronization events";
            }
            enum lsp-prefix {
              description "Prefix the trace messages with LSP information";
            }
            enum enhanced-frr {
              description "Enhanced FRR related information";
            }
            enum all {
              description "Trace everything";
            }
          }
        }
        leaf send {
          description "Trace transmitted packets";
          type empty;
        }
        leaf receive {
          description "Trace received packets";
          type empty;
        }
        leaf detail {
          description "Trace detailed information";
          type empty;
        }
        leaf disable {
          description "Disable this trace flag";
          type empty;
        }
      }
    }
    leaf refresh-time {
      description "Refresh time in seconds";
      default "1200";
      type union {
        type string {
          pattern "<.*>|$.*";
        }
        type uint32 {
          range "1 .. 65535";
        }
      }
    }
    leaf keep-multiplier {
      description "Keep multiplier";
      default "3";
      type union {
        type string {
          pattern "<.*>|$.*";
        }
        type uint32 {
          range "1 .. 255";
        }
      }
    }
    leaf graceful-deletion-timeout {
      description "Time to complete graceful deletion signaling";
      default "30";
      units seconds;
      type union {
        type string {
          pattern "<.*>|$.*";
        }
        type uint32 {
          range "1 .. 300";
        }
      }
    }
    leaf setup-protection {
      description "Enable setup protection";
      type empty;
    }
    leaf no-p2mp-re-merge {
      description "Enable p2mp remerge";
      type empty;
    }
    leaf cross-credibility-cspf {
      description "Compute CSPF paths spanning protocols for bypass LSP, detour LSP and loose hop expansion";
      type empty;
    }
    container preemption {
      description "Set RSVP session preemption attributes";
      choice preemption-type {
        case case_1 {
          leaf disabled {
            description "No RSVP session preemption";
            type empty;
          }
        }
        case case_2 {
          leaf normal {
            description "Run RSVP session preemption to accommodate new sessions";
            type empty;
          }
        }
        case case_3 {
          leaf aggressive {
            description "Run RSVP session preemption whenever necessary";
            type empty;
          }
        }
      }
      container soft-preemption {
        description "Options for establishing new path before tearing down a preempted LSP";
        leaf cleanup-timer {
          description "Time a soft-preempted LSP will be maintained";
          units seconds;
          type union {
            type string {
              pattern "<.*>|$.*";
            }
            type int32 {
              range "0 .. 10800";
            }
          }
        }
      }
    }
    leaf authentication-key {
      description "Authentication password";
      type jt:unreadable;
    }
    leaf no-authentication-check {
      description "Skip authentication check for received messages";
      type empty;
    }
    container associated-bidirectional-lsp {
      description "Set associated bidirectional LSP attributes";
      leaf single-sided-provisioning {
        description "Enable unidirectional reverse LSP setup for single sided provisioned forward LSP";
        type empty;
      }
    }
    leaf no-enhanced-frr-bypass {
      description "Disable enhanced facility backup FRR";
      type empty;
    }
    leaf no-node-hello-on-bypass {
      description "Do not send NodeID hello over bypass LSP";
      type empty;
    }
    container expand-flood-reflector-hop {
      presence "enable expand-flood-reflector-hop";
      description "Control expansion of flood reflector ERO strict hops";
    }
    list interface {
      key name;
      ordered-by user;
      description "RSVP interface options";
      leaf name {
        description "Interface name";
        type union {
          type jt:interface-name;
          type string {
            pattern "<.*>|$.*";
          }
        }
      }
      choice enable-disable {
        case case_1 {
          leaf disable {
            description "Disable RSVP on this interface";
            type empty;
          }
        }
      }
      leaf authentication-key {
        description "Authentication password";
        type jt:unreadable;
      }
      choice aggregate-choice {
        leaf aggregate {
          description "Permit refresh reduction extensions on the interface";
          status deprecated;
          type empty;
        }
        leaf no-aggregate {
          description "Don't permit refresh reduction extensions on the interface";
          status deprecated;
          type empty;
        }
      }
      choice reliable-choice {
        leaf reliable {
          description "Permit reliable message delivery on the interface";
          type empty;
        }
        leaf no-reliable {
          description "Don't permit reliable message delivery on the interface";
          type empty;
        }
      }
      leaf hello-interval {
        description "Hello interval";
        default "9";
        units seconds;
        type union {
          type string {
            pattern "<.*>|$.*";
          }
          type uint32 {
            range "0 .. 60";
          }
        }
      }
      container subscription {
        description "Link bandwidth percentage for RSVP reservation";
        uses subscription-type;
      }
      leaf bandwidth {
        description "Available bandwidth for the interface units bps";
        type string;
      }
      container update-threshold {
        description "Change in reserved bandwidth to trigger IGP update";
        container adaptive {
          description "Tune update-threshold dynamically";
          list limit {
            key name;
            description "Available Bandwidth threshold limit";
            leaf name {
              description "Upper limit of Available bandwidth for this range";
              type string;
            }
            leaf threshold-percent {
              description "Percentage change in reserved bandwidth to trigger IGP update";
              default "10.0";
              units percent;
              type decimal64 {
                fraction-digits 9;
                range "0.001 .. 20";
              }
            }
            leaf threshold-value {
              description "Change in reserved bandwidth to trigger IGP update (will be capped at 20% of link BW)";
              type string;
            }
          }
        }
        leaf threshold-percent {
          description "Percentage change in reserved bandwidth to trigger IGP update";
          default "10.0";
          units percent;
          type decimal64 {
            fraction-digits 9;
            range "0.001 .. 20";
          }
        }
        leaf threshold-value {
          description "Change in reserved bandwidth to trigger IGP update (will be capped at 20% of link BW)";
          type string;
        }
      }
      container update-threshold-max-reservable {
        description "Change in non-rsvp bandwidth to trigger IGP update ";
        leaf bandwidth {
          description "Change in non-rsvp bandwidth to trigger IGP update units bps";
          type string;
        }
        leaf percent {
          description "Percentage change in max-reservable bandwidth to trigger IGP update";
          units percent;
          type union {
            type string {
              pattern "<.*>|$.*";
            }
            type uint32 {
              range "1 .. 100";
            }
          }
        }
      }
      container non-rsvp-bandwdith {
        description "Config knobs relating to non-rsvp bandwidth";
        leaf local-bw-override-threshold {
          description "Overide threshold and update local bandwidth with non-rsvp bandwidth usage";
          type empty;
        }
      }
      container link-protection {
        presence "enable link-protection";
        description "Protect traffic with a label-stacked LSP";
        choice enable-disable {
          case case_1 {
            leaf disable {
              description "Disable link protection on this interface";
              type empty;
            }
          }
        }
        container bandwidth {
          description "Bandwidth for each bypass";
          uses bandwidth-type;
        }
        leaf max-bypasses {
          description "Max number of bypasses permitted for protecting this interface";
          default "1";
          type union {
            type string {
              pattern "<.*>|$.*";
            }
            type uint32 {
              range "0 .. 99";
            }
          }
        }
        leaf subscription {
          description "Percent of bandwidth guaranteed when admitting protected LSPs into bypasses";
          default "100";
          type union {
            type string {
              pattern "<.*>|$.*";
            }
            type uint32 {
              range "1 .. 65535";
            }
          }
        }
        leaf no-node-protection {
          description "Disallow node protection on this interface";
          type empty;
        }
        leaf optimize-timer {
          description "Interval between bypass reoptimizations";
          default "0";
          units seconds;
          type union {
            type string {
              pattern "<.*>|$.*";
            }
            type uint32 {
              range "0 .. 65535";
            }
          }
        }
        leaf class-of-service {
          description "Class of service for the bypass LSP";
          type union {
            type string {
              pattern "<.*>|$.*";
            }
            type int32 {
              range "0 .. 7";
            }
          }
        }
        leaf hop-limit {
          description "Maximum allowed router hops for bypass";
          type union {
            type string {
              pattern "<.*>|$.*";
            }
            type uint32 {
              range "2 .. 255";
            }
          }
        }
        leaf no-cspf {
          description "Disable automatic path computation";
          type empty;
        }
        leaf exclude-srlg {
          description "Exclude SRLG links";
          type empty;
        }
        container priority {
          presence "enable priority";
          description "Preemption priorities for the bypass LSP";
        }
        leaf setup-priority {
          description "Set-up priority";
          type union {
            type string {
              pattern "<.*>|$.*";
            }
            type uint32 {
              range "0 .. 7";
            }
          }
        }
        leaf reservation-priority {
          description "Reservation priority";
          type union {
            type string {
              pattern "<.*>|$.*";
            }
            type uint32 {
              range "0 .. 7";
            }
          }
        }
        list path {
          key name;
          ordered-by user;
          description "Explicit route of bypass path";
          leaf name {
            description "Address of next system in path";
            type jt:ipv4addr;
          }
          choice loose_strict_none {
            case case_1 {
              leaf loose {
                description "Next hop might not be adjacent";
                type empty;
              }
            }
            case case_2 {
              leaf strict {
                description "Next hop must be adjacent";
                type empty;
              }
            }
          }
        }
        container admin-group {
          description "Administrative group policy";
          uses admin_group_include_exclude;
        }
        list bypass {
          key name;
          ordered-by user;
          description "Bypass with specific constraints";
          leaf name {
            description "Name of bypass";
            type string {
              length "1 .. 64";
            }
          }
          leaf to {
            description "Address of egress router";
            type jt:ipv4addr;
          }
          container bandwidth {
            description "Bandwidth for each bypass";
            uses bandwidth-type;
          }
          container subscription {
            description "Bandwidth percent available on bypass for protected LSPs";
            presence "enable subscription";
            uses bypass-subscription-type;
          }
          leaf description {
            description "Text description of bypass";
            type string {
              length "1 .. 80";
            }
          }
          container priority {
            presence "enable priority";
            description "Preemption priorities for bypass";
          }
          leaf setup-priority {
            description "Set-up priority";
            type union {
              type string {
                pattern "<.*>|$.*";
              }
              type uint32 {
                range "0 .. 7";
              }
            }
          }
          leaf reservation-priority {
            description "Reservation priority";
            type union {
              type string {
                pattern "<.*>|$.*";
              }
              type uint32 {
                range "0 .. 7";
              }
            }
          }
          leaf class-of-service {
            description "Class of service for the bypass LSP";
            type union {
              type string {
                pattern "<.*>|$.*";
              }
              type int32 {
                range "0 .. 7";
              }
            }
          }
          leaf hop-limit {
            description "Maximum allowed router hops for bypass";
            type union {
              type string {
                pattern "<.*>|$.*";
              }
              type uint32 {
                range "2 .. 255";
              }
            }
          }
          leaf no-cspf {
            description "Disable automatic path computation";
            type empty;
          }
          leaf exclude-srlg {
            description "Exclude SRLG links";
            type empty;
          }
          list path {
            key name;
            ordered-by user;
            description "Explicit route of bypass path";
            leaf name {
              description "Address of next system in path";
              type jt:ipv4addr;
            }
            choice loose_strict_none {
              case case_1 {
                leaf loose {
                  description "Next hop might not be adjacent";
                  type empty;
                }
              }
              case case_2 {
                leaf strict {
                  description "Next hop must be adjacent";
                  type empty;
                }
              }
            }
          }
          container admin-group {
            description "Administrative group policy";
            uses admin_group_include_exclude;
          }
        }
        container optimize {
          description "Configure compute optimization algorithm";
          choice compute-algo {
            case case_1 {
              leaf bandwidth {
                description "Compute path optimized for available bandwidth";
                type empty;
              }
            }
          }
        }
      }
    }
    list peer-interface {
      key name;
      ordered-by user;
      description "Configuration for peer interface";
      leaf name {
        description "Name of peer interface";
        type string;
      }
      choice enable-disable {
        case case_1 {
          leaf disable {
            description "Disable RSVP on this control peer";
            type empty;
          }
        }
      }
      leaf authentication-key {
        description "Authentication password";
        type jt:unreadable;
      }
      choice aggregate-choice {
        leaf aggregate {
          description "Permit refresh reduction extensions on the interface";
          status deprecated;
          type empty;
        }
        leaf no-aggregate {
          description "Don't permit refresh reduction extensions on the interface";
          status deprecated;
          type empty;
        }
      }
      choice reliable-choice {
        leaf reliable {
          description "Permit reliable message delivery on the interface";
          type empty;
        }
        leaf no-reliable {
          description "Don't permit reliable message delivery on the interface";
          type empty;
        }
      }
      leaf hello-interval {
        description "Hello interval";
        default "9";
        units seconds;
        type union {
          type string {
            pattern "<.*>|$.*";
          }
          type uint32 {
            range "0 .. 60";
          }
        }
      }
      container dynamic-bidirectional-transport {
        presence "enable dynamic-bidirectional-transport";
        description "Enable dynamic setup of bidirectional packet LSP for transporting non-packet GMPLS LSP";
        leaf template {
          description "Template for the dynamic bidirectional packet LSP";
          type string;
        }
      }
    }
    list lsp-set {
      key name;
      ordered-by user;
      description "Configuration for lsp set";
      leaf name {
        description "Name of lsp set";
        type string;
      }
      choice enable-disable {
        case case_1 {
          leaf disable {
            description "Disable this lsp set";
            type empty;
          }
        }
      }
      container match-criteria {
        description "Match criteria for this lsp set";
        uses lsp-set-match-type;
      }
      container traceoptions {
        description "Trace options for this lsp set";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum io-event {
                description "Trace RSVP IO task related events";
              }
              enum io-packets {
                description "Trace all RSVP periodic refresh activity";
              }
              enum packets {
                description "Trace all RSVP packets";
              }
              enum path {
                description "Trace RSVP path messages";
              }
              enum resv {
                description "Trace RSVP Resv messages";
              }
              enum pathtear {
                description "Trace RSVP PathTear messages";
              }
              enum resvtear {
                description "Trace RSVP ResvTear messages";
              }
              enum state {
                description "Trace state transitions";
              }
              enum error {
                description "Trace error conditions";
              }
              enum route {
                description "Trace routing information";
              }
              enum lmp {
                description "Trace RSVP-LMP related interactions";
              }
              enum event {
                description "Trace RSVP related events";
              }
              enum nsr-synchronization {
                description "Trace NSR synchronization events";
              }
              enum lsp-prefix {
                description "Prefix the trace messages with LSP information";
              }
              enum enhanced-frr {
                description "Enhanced FRR related information";
              }
              enum all {
                description "Trace everything";
              }
            }
          }
          leaf send {
            description "Trace transmitted packets";
            type empty;
          }
          leaf receive {
            description "Trace received packets";
            type empty;
          }
          leaf detail {
            description "Trace detailed information";
            type empty;
          }
          leaf disable {
            description "Disable this trace flag";
            type empty;
          }
        }
      }
    }
  }
  grouping bypass-subscription-type {
    leaf subscription {
      description "Subscription percentage for bandwidth protection";
      default "100";
      type string;
    }
  }
  grouping juniper-protocols-stp {
    choice enable-disable {
      case case_1 {
        leaf disable {
          description "Disable STP";
          type empty;
        }
      }
    }
    leaf bpdu-destination-mac-address {
      description "Destination MAC address in the spanning tree BPDUs";
      type enumeration {
        enum provider-bridge-group {
          description "802.1ad provider bridge group address";
        }
      }
    }
    leaf bridge-priority {
      description "Priority of the bridge (in increments of 4k - 0,4k,8k,..60k)";
      type string;
    }
    leaf backup-bridge-priority {
      description "Priority of the bridge (in increments of 4k - 4k,8k,..60k)";
      type string;
    }
    leaf max-age {
      description "Maximum age of received protocol bpdu";
      units seconds;
      type union {
        type string {
          pattern "<.*>|$.*";
        }
        type uint16 {
          range "6 .. 40";
        }
      }
    }
    leaf hello-time {
      description "Time interval between configuration BPDUs";
      units seconds;
      type union {
        type string {
          pattern "<.*>|$.*";
        }
        type uint16 {
          range "1 .. 10";
        }
      }
    }
    leaf forward-delay {
      description "Time spent in listening or learning state";
      units seconds;
      type union {
        type string {
          pattern "<.*>|$.*";
        }
        type uint16 {
          range "4 .. 30";
        }
      }
    }
    leaf system-identifier {
      description "Sytem identifier to represent this node";
      type jt:mac-unicast;
    }
    container traceoptions {
      description "Tracing options for debugging protocol operation";
      uses stp-trace-options;
    }
    leaf vpls-flush-on-topology-change {
      description "Enable VPLS MAC flush on root protected CE interface receving topology change";
      type empty;
    }
    leaf priority-hold-time {
      description "Hold time before switching to primary priority when core domain becomes up";
      units seconds;
      type union {
        type string {
          pattern "<.*>|$.*";
        }
        type uint16 {
          range "1 .. 255";
        }
      }
    }
    list system-id {
      key name;
      ordered-by user;
      description "System ID to IP mapping";
      uses system-id-ip-map;
    }
    list interface {
      key name;
      description "Interface options";
      uses stp-interface;
    }
    leaf extended-system-id {
      description "Extended system identifier";
      type union {
        type string {
          pattern "<.*>|$.*";
        }
        type uint16 {
          range "0 .. 4095";
        }
      }
    }
    leaf force-version {
      description "Force protocol version";
      type enumeration {
        enum stp {
          description "Spanning tree protocol";
        }
      }
    }
    leaf bpdu-block-on-edge {
      description "Block BPDU on all interfaces configured as edge (BPDU Protect)";
      type empty;
    }
  }
  grouping juniper-protocols-vgd {
    container traceoptions {
      description "OVSDB trace options";
      leaf no-remote-trace {
        description "Disable remote tracing";
        type empty;
      }
      container file {
        description "Trace file information";
        leaf filename {
          description "Name of file in which to write trace information";
          type string {
            length "1 .. 1024";
          }
        }
        leaf size {
          description "Maximum trace file size";
          type string;
        }
        leaf files {
          description "Maximum number of trace files";
          default "3";
          type union {
            type string {
              pattern "<.*>|$.*";
            }
            type uint32 {
              range "2 .. 1000";
            }
          }
        }
        choice world-readable-choice {
          leaf world-readable {
            description "Allow any user to read the log file";
            type empty;
          }
          leaf no-world-readable {
            description "Don't allow any user to read the log file";
            type empty;
          }
        }
        leaf match {
          description "Regular expression for lines to be logged";
          type jt:regular-expression;
        }
        leaf microsecond-stamp {
          description "Timestamp with microsecond granularity";
          type empty;
        }
      }
      list flag {
        key name;
        ordered-by user;
        description "Tracing flag parameters";
        leaf name {
          type enumeration {
            enum interface {
              description "Trace OVSDB daemon interface events";
            }
            enum configuration {
              description "Trace OVSDB daemon configuration events";
            }
            enum core {
              description "Trace OVSDB daemon core events";
            }
            enum l2-client {
              description "Trace OVSDB daemon l2-client events";
            }
            enum ovs-client {
              description "Trace OVSDB daemon ovs-client events";
            }
            enum function {
              description "Trace OVSDB daemon function events";
            }
            enum netconf-client {
              description "Trace OVSDB daemon netconf-client events";
            }
            enum all {
              description "Trace everything";
            }
          }
        }
      }
    }
    list interfaces {
      key name;
      ordered-by user;
      description "Interfaces configured to be controlled by OVSDB";
      leaf name {
        description "Interface name";
        type union {
          type jt:interface-unit;
          type string {
            pattern "<.*>|$.*";
          }
        }
      }
    }
    list controller {
      key name;
      ordered-by user;
      description "Controller's IP address and port";
      leaf name {
        description "Controller's IPv4 address";
        type jt:ipaddr;
      }
      container protocol {
        description "Protocol type for controller connection";
        container tcp {
          description "Set protocol type to 'TCP'";
          leaf port {
            description "Controller's port number";
            type union {
              type string {
                pattern "<.*>|$.*";
              }
              type int32 {
                range "1024 .. 65535";
              }
            }
          }
        }
        container ssl {
          description "Set protocol type to 'SSL' (default)";
          leaf port {
            description "Controller's port number";
            type union {
              type string {
                pattern "<.*>|$.*";
              }
              type int32 {
                range "1024 .. 65535";
              }
            }
          }
        }
      }
      leaf maximum-backoff-duration {
        description "Maximum duration to wait between connection attempts";
        units milliseconds;
        type union {
          type string {
            pattern "<.*>|$.*";
          }
          type uint32 {
            range "1000 .. 4294967295";
          }
        }
      }
      leaf inactivity-probe-duration {
        description "Maximum idle duration before sending inactivity probe";
        units milliseconds;
        type union {
          type uint32;
          type string {
            pattern "<.*>|$.*";
          }
        }
      }
    }
  }
  grouping juniper-protocols-vni-options {
    list vni {
      key name;
      description "Per-vni options";
      leaf name {
        type union {
          type string {
            pattern "<.*>|$.*";
          }
          type int32 {
            range "1 .. 16777214";
          }
        }
      }
      container vrf-target {
        description "VRF target community configuration";
        leaf export {
          description "Target community to use when marking routes on export";
          status deprecated;
          type string;
        }
        leaf community {
          description "Target community";
          type string;
        }
      }
    }
  }
  grouping juniper-protocols-vstp {
    choice enable-disable {
      case case_1 {
        leaf disable {
          description "Disable VSTP";
          type empty;
        }
      }
    }
    leaf force-version {
      description "Force protocol version";
      type enumeration {
        enum stp {
          description "Spanning tree protocol";
        }
      }
    }
    leaf bpdu-block-on-edge {
      description "Block BPDU on all interfaces configured as edge (BPDU Protect)";
      type empty;
    }
    leaf vpls-flush-on-topology-change {
      description "Enable VPLS MAC flush on root protected CE interface receving topology change";
      type empty;
    }
    leaf priority-hold-time {
      description "Hold time before switching to primary priority when core domain becomes up";
      units seconds;
      type union {
        type string {
          pattern "<.*>|$.*";
        }
        type uint16 {
          range "1 .. 255";
        }
      }
    }
    list system-id {
      key name;
      ordered-by user;
      description "System ID to IP mapping";
      uses system-id-ip-map;
    }
    list interface {
      key name;
      description "Interface options";
      uses stp-interface;
    }
    list vlan {
      key name;
      description "VLAN spanning tree options";
      leaf name {
        description "VLAN id or all";
        type string;
      }
      leaf bridge-priority {
        description "Priority of the bridge (in increments of 4k - 0,4k,8k,..60k)";
        type string;
      }
      leaf backup-bridge-priority {
        description "Priority of the bridge (in increments of 4k - 4k,8k,..60k)";
        type string;
      }
      leaf max-age {
        description "Maximum age of received protocol bpdu";
        units seconds;
        type union {
          type string {
            pattern "<.*>|$.*";
          }
          type uint16 {
            range "6 .. 40";
          }
        }
      }
      leaf hello-time {
        description "Time interval between configuration BPDUs";
        units seconds;
        type union {
          type string {
            pattern "<.*>|$.*";
          }
          type uint16 {
            range "1 .. 10";
          }
        }
      }
      leaf forward-delay {
        description "Time spent in listening or learning state";
        units seconds;
        type union {
          type string {
            pattern "<.*>|$.*";
          }
          type uint16 {
            range "4 .. 30";
          }
        }
      }
      leaf system-identifier {
        description "Sytem identifier to represent this node";
        type jt:mac-unicast;
      }
      container traceoptions {
        description "Tracing options for debugging protocol operation";
        uses stp-trace-options;
      }
      list interface {
        key name;
        description "Interface options";
        uses stp-interface;
      }
    }
    container vlan-group {
      presence "enable vlan-group";
      description "Spanning tree options for group of VLANs";
      list group {
        key name;
        ordered-by user;
        description "Name if VLAN group";
        leaf name {
          description "VLAN group name";
          type string {
            length "1 .. 63";
          }
        }
        leaf-list vlan {
          ordered-by user;
          description "VLAN ID or VLAN ID range [1..4094]";
          type string;
        }
        leaf bridge-priority {
          description "Priority of the bridge (in increments of 4k - 0,4k,8k,..60k)";
          type string;
        }
        leaf backup-bridge-priority {
          description "Priority of the bridge (in increments of 4k - 4k,8k,..60k)";
          type string;
        }
        leaf max-age {
          description "Maximum age of received protocol bpdu";
          units seconds;
          type union {
            type string {
              pattern "<.*>|$.*";
            }
            type uint16 {
              range "6 .. 40";
            }
          }
        }
        leaf hello-time {
          description "Time interval between configuration BPDUs";
          units seconds;
          type union {
            type string {
              pattern "<.*>|$.*";
            }
            type uint16 {
              range "1 .. 10";
            }
          }
        }
        leaf forward-delay {
          description "Time spent in listening or learning state";
          units seconds;
          type union {
            type string {
              pattern "<.*>|$.*";
            }
            type uint16 {
              range "4 .. 30";
            }
          }
        }
        leaf system-identifier {
          description "Sytem identifier to represent this node";
          type jt:mac-unicast;
        }
        container traceoptions {
          description "Tracing options for debugging protocol operation";
          uses stp-trace-options;
        }
        list interface {
          key name;
          description "Interface options";
          uses stp-interface;
        }
      }
    }
  }
  grouping ldp-sync-obj {
    choice enable-disable {
      case case_1 {
        leaf disable {
          description "Disable LDP synchronization";
          type empty;
        }
      }
    }
    leaf hold-time {
      description "Time during which maximum metric is advertised";
      type union {
        type string {
          pattern "<.*>|$.*";
        }
        type uint32 {
          range "1 .. 65535";
        }
      }
    }
  }
  grouping ldp_filter_obj {
    description "Filter to apply to tracing";
    leaf match-on {
      description "Argument on which to match";
      type enumeration {
        enum fec {
          description "Filter based on FEC associated to the traced object.";
        }
        enum address {
          description "Filter based on packet source and destination addresses.";
        }
      }
    }
    leaf-list policy {
      ordered-by user;
      description "Filter policy";
      type jt:policy-algebra;
    }
  }
  grouping lmp_control_channel_type {
    leaf name {
      description "Control channel interface";
      type union {
        type jt:interface-name;
        type string {
          pattern "<.*>|$.*";
        }
      }
    }
    leaf remote-address {
      description "Control channel remote address";
      type jt:ipaddr;
    }
  }
  grouping lsp-set-match-type {
    leaf lsp-name {
      description "LSP name that matches this string";
      type string;
    }
    leaf lsp-regex {
      description "All LSPs that match this regular expression pattern";
      type string;
    }
    leaf p2mp-name {
      description "P2MP names that match this string";
      type string;
    }
    leaf p2mp-regex {
      description "P2MP names that match this regular expression pattern";
      type string;
    }
    choice router-type {
      case case_1 {
        leaf egress {
          description "All LSPs for which this router is egress";
          type empty;
        }
      }
      case case_2 {
        leaf ingress {
          description "All LSPs for which this router is ingress";
          type empty;
        }
      }
      case case_3 {
        leaf transit {
          description "All LSPs for which this router is transit";
          type empty;
        }
      }
    }
  }
  grouping macro-data-type {
    leaf name {
      description "Keyword part of the keyword-value pair";
      type string;
    }
    leaf value {
      description "Value part of the keyword-value pair";
      type string;
    }
  }
  grouping mrp-trace-options {
    description "Trace options for MMRP Protocol";
    container file {
      description "Trace file options";
      leaf filename {
        description "Name of file in which to write trace information";
        type string {
          length "1 .. 1024";
        }
      }
      leaf replace {
        description "Replace trace file rather than appending to it";
        status deprecated;
        type empty;
      }
      leaf size {
        description "Maximum trace file size";
        type string;
      }
      leaf files {
        description "Maximum number of trace files";
        default "10";
        type union {
          type string {
            pattern "<.*>|$.*";
          }
          type uint32 {
            range "2 .. 1000";
          }
        }
      }
      leaf no-stamp {
        description "Do not timestamp trace file";
        status deprecated;
        type empty;
      }
      choice world-readable-choice {
        leaf world-readable {
          description "Allow any user to read the log file";
          type empty;
        }
        leaf no-world-readable {
          description "Don't allow any user to read the log file";
          type empty;
        }
      }
    }
    list flag {
      key name;
      ordered-by user;
      description "Tracing parameters";
      leaf name {
        type enumeration {
          enum events {
            description "Trace events to the protocol state machine";
          }
          enum pdu {
            description "Trace RAPS PDU reception and transmission";
          }
          enum timers {
            description "Trace protocol timers";
          }
          enum state-machine {
            description "Trace information of the state machine";
          }
          enum socket {
            description "Trace soccket activity";
          }
          enum error {
            description "Trace all failure conditions";
          }
          enum all {
            description "Trace all";
          }
        }
      }
      leaf disable {
        description "Disable this trace flag";
        type empty;
      }
    }
  }
  grouping mstp-interface {
    leaf name {
      type string;
    }
    leaf priority {
      description "Interface priority (in increments of 16 - 0,16,..240)";
      type union {
        type string {
          pattern "<.*>|$.*";
        }
        type uint16 {
          range "0 .. 255";
        }
      }
    }
    leaf cost {
      description "Cost of the interface";
      type union {
        type string {
          pattern "<.*>|$.*";
        }
        type uint32 {
          range "1 .. 200000000";
        }
      }
    }
    leaf mode {
      description "Interface mode (P2P or shared)";
      type enumeration {
        enum point-to-point {
          description "Interface mode is point-to-point";
        }
        enum shared {
          description "Interface mode is shared";
        }
      }
    }
    leaf edge {
      description "Port is an edge port";
      type empty;
    }
    leaf access-trunk {
      description "Send/Receive untagged RSTP BPDUs on this interface";
      type empty;
    }
    container bpdu-timeout-action {
      presence "enable bpdu-timeout-action";
      description "Define action on BPDU expiry (Loop Protect)";
      leaf block {
        description "Block the interface";
        type empty;
      }
      leaf alarm {
        description "Generate an alarm";
        type empty;
      }
    }
    leaf no-root-port {
      description "Do not allow the interface to become root (Root Protect)";
      type empty;
    }
    leaf disable {
      description "Disable Spanning Tree on port";
      type empty;
    }
  }
  grouping pccd-traceoptions-type {
    description "Trace options for PCCD";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    list flag {
      key name;
      ordered-by user;
      description "Area of PCCD to enable debugging output";
      leaf name {
        type enumeration {
          enum pccd-main {
            description "Trace main module";
          }
          enum pccd-config {
            description "Trace configuration parsing operations";
          }
          enum pccd-core {
            description "Trace PCCD's core operations";
          }
          enum pccd-ui {
            description "Trace user interface handling";
          }
          enum pccd-rpd {
            description "Trace communication with RPD";
          }
          enum pccd-functions {
            description "Trace function entries/outs";
          }
          enum pccd-nsr {
            description "Trace NSR operations";
          }
          enum all {
            description "Trace all areas of PCCD code";
          }
        }
      }
    }
  }
  grouping peer-group {
    leaf name {
      description "IP address for this peer";
      type jt:ipv4addr;
    }
    leaf local-ip-addr {
      description "Local IP address to use for this peer alone.";
      type jt:ipv4addr;
    }
    leaf session-establishment-hold-time {
      description "Time within which connection must succeed with this peer";
      units seconds;
      type union {
        type string {
          pattern "<.*>|$.*";
        }
        type uint32 {
          range "45 .. 600";
        }
      }
    }
    leaf-list redundancy-group-id-list {
      ordered-by user;
      description "List of redundacy groups this peer is part of";
      type union {
        type uint32;
        type string {
          pattern "<.*>|$.*";
        }
      }
    }
    container backup-liveness-detection {
      presence "enable backup-liveness-detection";
      description "Backup liveness detection";
      leaf backup-peer-ip {
        description "Backup livelness detection peer's IP address";
        type jt:ipv4addr;
      }
    }
    container liveness-detection {
      presence "enable liveness-detection";
      description "Bidirectional Forwarding Detection options for the peer";
      leaf version {
        description "BFD protocol version number";
        default "automatic";
        type enumeration {
          enum 0 {
            description "BFD version 0 (deprecated)";
          }
          enum 1 {
            description "BFD version 1";
          }
          enum automatic {
            description "Choose BFD version automatically";
          }
        }
      }
      leaf minimum-interval {
        description "Minimum transmit and receive interval";
        units milliseconds;
        type union {
          type string {
            pattern "<.*>|$.*";
          }
          type uint32 {
            range "1 .. 255000";
          }
        }
      }
      leaf minimum-transmit-interval {
        description "Minimum transmit interval";
        status deprecated;
        units milliseconds;
        type union {
          type string {
            pattern "<.*>|$.*";
          }
          type uint32 {
            range "1 .. 255000";
          }
        }
      }
      leaf minimum-receive-interval {
        description "Minimum receive interval";
        units milliseconds;
        type union {
          type string {
            pattern "<.*>|$.*";
          }
          type uint32 {
            range "1 .. 255000";
          }
        }
      }
      leaf multiplier {
        description "Detection time multiplier";
        default "3";
        type union {
          type string {
            pattern "<.*>|$.*";
          }
          type uint32 {
            range "1 .. 255";
          }
        }
      }
      leaf inline-disable {
        description "Disable inline mode for this BFD session";
        type empty;
      }
      leaf pdu-size {
        description "BFD transport protocol payload size";
        default "24";
        type union {
          type string {
            pattern "<.*>|$.*";
          }
          type uint32 {
            range "24 .. 9000";
          }
        }
      }
      choice adaptation-choice {
        case case_1 {
          leaf no-adaptation {
            description "Disable adaptation";
            type empty;
          }
        }
      }
      container transmit-interval {
        description "Transmit-interval options";
        leaf minimum-interval {
          description "Minimum transmit interval";
          units milliseconds;
          type union {
            type string {
              pattern "<.*>|$.*";
            }
            type uint32 {
              range "1 .. 255000";
            }
          }
        }
        leaf threshold {
          description "High transmit interval triggering a trap";
          units milliseconds;
          type union {
            type uint32;
            type string {
              pattern "<.*>|$.*";
            }
          }
        }
      }
      container detection-time {
        description "Detection-time options";
        leaf threshold {
          description "High detection-time triggering a trap";
          units milliseconds;
          type union {
            type uint32;
            type string {
              pattern "<.*>|$.*";
            }
          }
        }
      }
    }
    leaf authentication-key {
      description "MD5 authentication key";
      type string {
        length "1 .. 126";
      }
    }
  }
  grouping periodic_oam {
    container mpls-tp-mode {
      presence "enable mpls-tp-mode";
      description "MPLS-TP Mode, Do not use IP addressing for OAM";
      container lsping-channel-type {
        description "Supported Control-channel types for MPLS-TP mode....";
        choice action-choice {
          case case_1 {
            leaf ipv4 {
              description "Use channel-type IPv4(0x0021), With IP-UDP encapsulation";
              type empty;
            }
          }
          case case_2 {
            leaf on-demand-cv {
              description "Use channel-type On-Demand-CV(0x0025), Without IP-UDP encapsulation";
              type empty;
            }
          }
        }
      }
    }
    container bfd-port {
      description "Egress knob to select MHOP-BFD port for MPLS BFD";
      leaf-list import {
        ordered-by user;
        description "Import policy";
        type jt:policy-algebra;
      }
    }
    container bfd-liveness-detection {
      description "Bidirectional Forwarding Detection options";
      leaf version {
        description "BFD protocol version number";
        default "automatic";
        type enumeration {
          enum 0 {
            description "BFD version 0 (deprecated)";
          }
          enum 1 {
            description "BFD version 1";
          }
          enum automatic {
            description "Choose BFD version automatically";
          }
        }
      }
      leaf minimum-interval {
        description "Minimum transmit and receive interval";
        units milliseconds;
        type union {
          type string {
            pattern "<.*>|$.*";
          }
          type uint32 {
            range "1 .. 255000";
          }
        }
      }
      leaf minimum-transmit-interval {
        description "Minimum transmit interval";
        status deprecated;
        units milliseconds;
        type union {
          type string {
            pattern "<.*>|$.*";
          }
          type uint32 {
            range "1 .. 255000";
          }
        }
      }
      leaf minimum-receive-interval {
        description "Minimum receive interval";
        units milliseconds;
        type union {
          type string {
            pattern "<.*>|$.*";
          }
          type uint32 {
            range "1 .. 255000";
          }
        }
      }
      leaf multiplier {
        description "Detection time multiplier";
        default "3";
        type union {
          type string {
            pattern "<.*>|$.*";
          }
          type uint32 {
            range "1 .. 255";
          }
        }
      }
      leaf inline-disable {
        description "Disable inline mode for this BFD session";
        type empty;
      }
      leaf pdu-size {
        description "BFD transport protocol payload size";
        default "24";
        type union {
          type string {
            pattern "<.*>|$.*";
          }
          type uint32 {
            range "24 .. 9000";
          }
        }
      }
      choice adaptation-choice {
        case case_1 {
          leaf no-adaptation {
            description "Disable adaptation";
            type empty;
          }
        }
      }
      container transmit-interval {
        description "Transmit-interval options";
        leaf minimum-interval {
          description "Minimum transmit interval";
          units milliseconds;
          type union {
            type string {
              pattern "<.*>|$.*";
            }
            type uint32 {
              range "1 .. 255000";
            }
          }
        }
        leaf threshold {
          description "High transmit interval triggering a trap";
          units milliseconds;
          type union {
            type uint32;
            type string {
              pattern "<.*>|$.*";
            }
          }
        }
      }
      container detection-time {
        description "Detection-time options";
        leaf threshold {
          description "High detection-time triggering a trap";
          units milliseconds;
          type union {
            type uint32;
            type string {
              pattern "<.*>|$.*";
            }
          }
        }
      }
      container failure-action {
        description "Action to take when BFD session goes down";
        choice action-choice {
          case case_1 {
            leaf teardown {
              description "Teardown label switched path and resignal";
              type empty;
            }
          }
          case case_2 {
            container make-before-break {
              presence "enable make-before-break";
              description "Resignal the label switched path before teardown";
              leaf teardown-timeout {
                description "Time to wait before teardown";
                units seconds;
                type union {
                  type string {
                    pattern "<.*>|$.*";
                  }
                  type uint32 {
                    range "0 .. 30";
                  }
                }
              }
            }
          }
        }
      }
      leaf no-router-alert-option {
        description "Do not set Router-Alert options in IP header for MPLS-BFD";
        type empty;
      }
      leaf use-ip-ttl-1 {
        description "Set TTL value to 1 in IP header for MPLS-BFD";
        type empty;
      }
    }
    container performance-monitoring {
      description "Performance monitoring options";
      container traceoptions {
        description "Trace options for PM";
        container file {
          description "Trace file options";
          leaf filename {
            description "Name of file in which to write trace information";
            type string {
              length "1 .. 1024";
            }
          }
          leaf replace {
            description "Replace trace file rather than appending to it";
            status deprecated;
            type empty;
          }
          leaf size {
            description "Maximum trace file size";
            type string;
          }
          leaf files {
            description "Maximum number of trace files";
            default "10";
            type union {
              type string {
                pattern "<.*>|$.*";
              }
              type uint32 {
                range "2 .. 1000";
              }
            }
          }
          leaf no-stamp {
            description "Do not timestamp trace file";
            status deprecated;
            type empty;
          }
          choice world-readable-choice {
            leaf world-readable {
              description "Allow any user to read the log file";
              type empty;
            }
            leaf no-world-readable {
              description "Don't allow any user to read the log file";
              type empty;
            }
          }
        }
        list flag {
          key name;
          ordered-by user;
          description "Tracing parameters";
          leaf name {
            type enumeration {
              enum init {
                description "Trace init commnad";
              }
              enum error {
                description "Trace error conditions";
              }
              enum event {
                description "Trace state machine events";
              }
              enum general {
                description "Trace general events";
              }
              enum packet {
                description "Trace various packets ";
              }
              enum timer {
                description "Trace timer processing";
              }
              enum all {
                description "Trace everything";
              }
            }
          }
        }
      }
      container querier {
        description "Querier options";
        container loss {
          description "Loss measurement options";
          list traffic-class {
            key name;
            description "Traffic class specific options";
            leaf name {
              description "Traffic class value";
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic class";
                }
                enum none {
                  description "No Traffic class";
                }
              }
            }
            leaf query-interval {
              description "Minimum transmit interval";
              units milliseconds;
              type union {
                type string {
                  pattern "<.*>|$.*";
                }
                type uint32 {
                  range "1000 .. 4294967295";
                }
              }
            }
            leaf measurement-quantity {
              description "Loss measurement quantity";
              default "packets";
              type enumeration {
                enum bytes {
                  description "Byte loss measurement";
                }
                enum packets {
                  description "Packet loss measurement";
                }
              }
            }
            leaf average-sample-size {
              description "Number of samples used in average calculation";
              type union {
                type string {
                  pattern "<.*>|$.*";
                }
                type uint16 {
                  range "1 .. 30";
                }
              }
            }
            leaf loss-threshold {
              description "Loss threshold value";
              type union {
                type string {
                  pattern "<.*>|$.*";
                }
                type uint32 {
                  range "1 .. 4294967295";
                }
              }
            }
            leaf loss-threshold-window {
              description "Number of samples for loss threshold calculation";
              type union {
                type string {
                  pattern "<.*>|$.*";
                }
                type uint32 {
                  range "1 .. 30";
                }
              }
            }
          }
        }
        container delay {
          description "Delay measurement options";
          list traffic-class {
            key name;
            description "Traffic class specific options";
            leaf name {
              description "Traffic class value";
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic classes";
                }
              }
            }
            leaf query-interval {
              description "Minimum transmit interval";
              units milliseconds;
              type union {
                type string {
                  pattern "<.*>|$.*";
                }
                type uint32 {
                  range "1000 .. 4294967295";
                }
              }
            }
            leaf padding-size {
              description "Size of padding";
              type union {
                type string {
                  pattern "<.*>|$.*";
                }
                type uint16 {
                  range "1 .. 1500";
                }
              }
            }
            leaf average-sample-size {
              description "Number of samples used in average calculation";
              type union {
                type string {
                  pattern "<.*>|$.*";
                }
                type uint16 {
                  range "1 .. 30";
                }
              }
            }
            leaf twcd-delay-threshold {
              description "Two way channel delay threshold value";
              units microseconds;
              type union {
                type string {
                  pattern "<.*>|$.*";
                }
                type uint32 {
                  range "1 .. 4294967295";
                }
              }
            }
            leaf rtt-delay-threshold {
              description "Round trip delay threshold value";
              units microseconds;
              type union {
                type string {
                  pattern "<.*>|$.*";
                }
                type uint32 {
                  range "1 .. 4294967295";
                }
              }
            }
          }
        }
        container loss-delay {
          description "Combined loss-delay measurement options";
          list traffic-class {
            key name;
            description "Traffic class specific options";
            leaf name {
              description "Traffic class value";
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic classes";
                }
                enum none {
                  description "No Traffic class";
                }
              }
            }
            leaf query-interval {
              description "Minimum transmit interval";
              units milliseconds;
              type union {
                type string {
                  pattern "<.*>|$.*";
                }
                type uint32 {
                  range "1000 .. 4294967295";
                }
              }
            }
            leaf measurement-quantity {
              description "Loss measurement quantity";
              default "packets";
              type enumeration {
                enum bytes {
                  description "Byte loss measurement";
                }
                enum packets {
                  description "Packet loss measurement";
                }
              }
            }
            leaf padding-size {
              description "Size of padding";
              type union {
                type string {
                  pattern "<.*>|$.*";
                }
                type uint16 {
                  range "1 .. 1500";
                }
              }
            }
            leaf average-sample-size {
              description "Number of samples used in average calculation";
              type union {
                type string {
                  pattern "<.*>|$.*";
                }
                type uint16 {
                  range "1 .. 30";
                }
              }
            }
            leaf loss-threshold {
              description "Loss threshold value";
              type union {
                type string {
                  pattern "<.*>|$.*";
                }
                type uint32 {
                  range "1 .. 4294967295";
                }
              }
            }
            leaf loss-threshold-window {
              description "Number of samples for loss threshold calculation";
              type union {
                type string {
                  pattern "<.*>|$.*";
                }
                type uint32 {
                  range "1 .. 30";
                }
              }
            }
            leaf twcd-delay-threshold {
              description "Two way channel delay threshold value";
              units microseconds;
              type union {
                type string {
                  pattern "<.*>|$.*";
                }
                type uint32 {
                  range "1 .. 4294967295";
                }
              }
            }
            leaf rtt-delay-threshold {
              description "Round trip delay threshold value";
              units microseconds;
              type union {
                type string {
                  pattern "<.*>|$.*";
                }
                type uint32 {
                  range "1 .. 4294967295";
                }
              }
            }
          }
        }
      }
      container responder {
        description "Responder options";
        container loss {
          description "Loss measurement options";
          leaf min-query-interval {
            description "Minimum query interval";
            units milliseconds;
            type union {
              type string {
                pattern "<.*>|$.*";
              }
              type uint32 {
                range "1000 .. 4294967295";
              }
            }
          }
        }
        container delay {
          description "Delay measurement options";
          leaf min-query-interval {
            description "Minimum query interval";
            units milliseconds;
            type union {
              type string {
                pattern "<.*>|$.*";
              }
              type uint32 {
                range "1000 .. 4294967295";
              }
            }
          }
        }
      }
    }
    leaf lsp-ping-interval {
      description "Time interval between LSP ping messages";
      units seconds;
      type union {
        type string {
          pattern "<.*>|$.*";
        }
        type uint16 {
          range "30 .. 3600";
        }
      }
    }
    leaf lsp-ping-multiplier {
      description "Number of ping reply missed before declaring BFD down";
      type union {
        type string {
          pattern "<.*>|$.*";
        }
        type uint8 {
          range "1 .. 5";
        }
      }
    }
    container traceoptions {
      description "Trace options for MPLSOAM process";
      leaf no-remote-trace {
        description "Disable remote tracing";
        type empty;
      }
      container file {
        description "Trace file information";
        leaf filename {
          description "Name of file in which to write trace information";
          type string {
            length "1 .. 1024";
          }
        }
        leaf size {
          description "Maximum trace file size";
          type string;
        }
        leaf files {
          description "Maximum number of trace files";
          default "3";
          type union {
            type string {
              pattern "<.*>|$.*";
            }
            type uint32 {
              range "2 .. 1000";
            }
          }
        }
        choice world-readable-choice {
          leaf world-readable {
            description "Allow any user to read the log file";
            type empty;
          }
          leaf no-world-readable {
            description "Don't allow any user to read the log file";
            type empty;
          }
        }
        leaf match {
          description "Regular expression for lines to be logged";
          type jt:regular-expression;
        }
      }
      list flag {
        key name;
        ordered-by user;
        description "Tracing parameters";
        leaf name {
          type enumeration {
            enum configuration {
              description "Trace configuration events";
            }
            enum pipe {
              description "Trace pipe activity";
            }
            enum rpc-packet-details {
              description "Trace RPC packet details";
            }
            enum database {
              description "Trace database activity";
            }
            enum network {
              description "Trace network activity";
            }
            enum traceroute {
              description "Trace traceroute activity";
            }
            enum all {
              description "Trace everything";
            }
          }
        }
      }
    }
  }
  grouping pim_bootstrap_options_type {
    leaf priority {
      description "Eligibility to be the bootstrap router";
      type union {
        type string {
          pattern "<.*>|$.*";
        }
        type uint32 {
          range "0 .. 255";
        }
      }
    }
    leaf-list import {
      ordered-by user;
      description "Bootstrap import policy";
      type jt:policy-algebra;
    }
    leaf-list export {
      ordered-by user;
      description "Bootstrap export policy";
      type jt:policy-algebra;
    }
  }
  grouping pim_filter_obj {
    description "Filter to apply to tracing";
    leaf match-on {
      description "Argument on which to match";
      type enumeration {
        enum prefix {
          description "Filter based on prefix";
        }
      }
    }
    leaf-list policy {
      ordered-by user;
      description "Filter policy";
      type jt:policy-algebra;
    }
  }
  grouping pim_rp_group_range_type {
    leaf name {
      type jt:ipprefix;
    }
    leaf nexthop-hold-time {
      description "Nexthop hold time in milliseconds";
      units milliseconds;
      type union {
        type string {
          pattern "<.*>|$.*";
        }
        type uint32 {
          range "1 .. 1000";
        }
      }
    }
  }
  grouping ppp-traceoptions-type {
    description "Trace options for PPP process";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    leaf level {
      description "Level of debugging output";
      default "error";
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
    }
    list flag {
      key name;
      ordered-by user;
      description "Area of PPP process to enable debugging output";
      leaf name {
        type enumeration {
          enum access {
            description "Trace access code";
          }
          enum address-pool {
            description "Trace address pool code";
          }
          enum auth {
            description "Trace authentication code";
          }
          enum chap {
            description "Trace CHAP code";
          }
          enum pap {
            description "Trace PAP code";
          }
          enum config {
            description "Trace configuration code";
          }
          enum ifdb {
            description "Trace interface database code";
          }
          enum lcp {
            description "Trace LCP state machine code";
          }
          enum memory {
            description "Trace memory management code";
          }
          enum message {
            description "Trace message processing code";
          }
          enum mlppp {
            description "Trace MLPPP code";
          }
          enum ncp {
            description "Trace NCP state machine code";
          }
          enum ppp {
            description "Trace PPP protocol processing code";
          }
          enum radius {
            description "Trace RADIUS processing code";
          }
          enum redundancy {
            description "Trace redundancy code";
          }
          enum rtsock {
            description "Trace routing socket code";
          }
          enum session {
            description "Trace session management code";
          }
          enum signal {
            description "Trace signal handling code";
          }
          enum timer {
            description "Trace timer code";
          }
          enum ui {
            description "Trace user interface code";
          }
          enum ci {
            description "Trace ci code";
          }
          enum all {
            description "Trace all areas of code";
          }
        }
      }
    }
  }
  grouping pppoe-traceoptions-type {
    description "Trace options for PPPoE process";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    leaf level {
      description "Level of debugging output";
      default "error";
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
    }
    list flag {
      key name;
      ordered-by user;
      description "Area of PPPoE process to enable debugging output";
      leaf name {
        type enumeration {
          enum config {
            description "Trace configuration code";
          }
          enum events {
            description "Trace event code";
          }
          enum gres {
            description "Trace GRES code";
          }
          enum init {
            description "Trace initialization code";
          }
          enum interface-db {
            description "Trace interface database code";
          }
          enum memory {
            description "Trace memory management code";
          }
          enum protocol {
            description "Trace PPPoE protocol processing code";
          }
          enum rtsock {
            description "Trace routing socket code";
          }
          enum session-db {
            description "Trace Session DB code";
          }
          enum signal {
            description "Trace signal handling code";
          }
          enum state {
            description "Trace state handling code";
          }
          enum stats {
            description "Trace Stats Handling code";
          }
          enum timer {
            description "Trace timer code";
          }
          enum ui {
            description "Trace user interface code";
          }
          enum all {
            description "Trace all areas of code";
          }
        }
      }
    }
    container filter {
      presence "enable filter";
      description "Trace filtering";
      leaf aci {
        description "Regular expression to match ACI";
        type string {
          length "1 .. 64";
        }
      }
      leaf ari {
        description "Regular expression to match ARI";
        type string {
          length "1 .. 64";
        }
      }
      leaf service-name {
        description "Service name";
        type string {
          length "1 .. 64";
        }
      }
      leaf underlying-interface {
        description "Underlying interface name";
        type string;
      }
      container user {
        presence "enable user";
        description "Filter by user name";
        leaf username {
          description "Name of the user to be filtered";
          type string {
            length "1 .. 64";
          }
        }
      }
    }
  }
  grouping r2cp-traceoptions-type {
    description "Trace options for R2CP process";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    leaf level {
      description "Level of debugging output";
      default "error";
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
    }
    list flag {
      key name;
      ordered-by user;
      description "Area of R2CP process to enable debugging output";
      leaf name {
        type enumeration {
          enum configuration {
            description "Trace configuration code";
          }
          enum event {
            description "Trace events";
          }
          enum interface {
            description "Trace interface processing";
          }
          enum node {
            description "Trace node table code";
          }
          enum packet {
            description "Trace packet processing";
          }
          enum rtsock {
            description "Trace routing socket code";
          }
          enum session {
            description "Trace session events";
          }
          enum socket {
            description "Trace socket calls";
          }
          enum timer {
            description "Trace timer code";
          }
          enum virtual-channel {
            description "Trace virtual channel mapping code";
          }
          enum all {
            description "Trace all areas of code";
          }
        }
      }
    }
  }
  grouping rib-inet3 {
    container inet.3 {
      presence "enable inet.3";
      description "Use inet.3 to exchange labeled unicast routes";
    }
  }
  grouping rib_group_inet_type {
    description "Routing table group";
    leaf ribgroup-name {
      description "Name of the routing table group";
      type string;
    }
  }
  grouping rib_group_type {
    leaf inet-old-style {
      description "Name of the IPv4 routing table group";
      status deprecated;
      type string;
    }
    leaf inet {
      description "Name of the IPv4 routing table group";
      type string;
    }
    leaf inet3 {
      description "Name of the IPv4 inet.3 routing table group";
      type string;
    }
    leaf inet6 {
      description "Name of the IPv6 routing table group";
      type string;
    }
    leaf inet63 {
      description "Name of the IPv6 inet6.3 routing table group";
      type string;
    }
  }
  grouping rip_filter_obj {
    description "Filter to apply to tracing";
    leaf match-on {
      description "Argument on which to match";
      type enumeration {
        enum prefix {
          description "Filter based on prefix";
        }
      }
    }
    leaf-list policy {
      ordered-by user;
      description "Filter policy";
      type jt:policy-algebra;
    }
  }
  grouping stp-interface {
    leaf name {
      type string;
    }
    leaf priority {
      description "Interface priority (in increments of 16 - 0,16,..240)";
      type union {
        type string {
          pattern "<.*>|$.*";
        }
        type uint16 {
          range "0 .. 255";
        }
      }
    }
    leaf cost {
      description "Cost of the interface";
      type union {
        type string {
          pattern "<.*>|$.*";
        }
        type uint32 {
          range "1 .. 200000000";
        }
      }
    }
    leaf mode {
      description "Interface mode (P2P or shared)";
      type enumeration {
        enum point-to-point {
          description "Interface mode is point-to-point";
        }
        enum shared {
          description "Interface mode is shared";
        }
      }
    }
    leaf edge {
      description "Port is an edge port";
      type empty;
    }
    leaf access-trunk {
      description "Send/Receive untagged RSTP BPDUs on this interface";
      type empty;
    }
    container bpdu-timeout-action {
      presence "enable bpdu-timeout-action";
      description "Define action on BPDU expiry (Loop Protect)";
      leaf block {
        description "Block the interface";
        type empty;
      }
      leaf alarm {
        description "Generate an alarm";
        type empty;
      }
    }
    leaf no-root-port {
      description "Do not allow the interface to become root (Root Protect)";
      type empty;
    }
    leaf disable {
      description "Disable Spanning Tree on port";
      type empty;
    }
  }
  grouping stp-trace-options {
    description "Trace options for Spanning Tree Protocol";
    container file {
      description "Trace file options";
      leaf filename {
        description "Name of file in which to write trace information";
        type string {
          length "1 .. 1024";
        }
      }
      leaf replace {
        description "Replace trace file rather than appending to it";
        status deprecated;
        type empty;
      }
      leaf size {
        description "Maximum trace file size";
        type string;
      }
      leaf files {
        description "Maximum number of trace files";
        default "10";
        type union {
          type string {
            pattern "<.*>|$.*";
          }
          type uint32 {
            range "2 .. 1000";
          }
        }
      }
      leaf no-stamp {
        description "Do not timestamp trace file";
        status deprecated;
        type empty;
      }
      choice world-readable-choice {
        leaf world-readable {
          description "Allow any user to read the log file";
          type empty;
        }
        leaf no-world-readable {
          description "Don't allow any user to read the log file";
          type empty;
        }
      }
    }
    list flag {
      key name;
      ordered-by user;
      description "Tracing parameters";
      leaf name {
        type enumeration {
          enum events {
            description "Trace events to the protocol state machine";
          }
          enum bpdu {
            description "Trace BPDU reception and transmission";
          }
          enum timers {
            description "Trace protocol timers";
          }
          enum port-information-state-machine {
            description "Trace port information state machine";
          }
          enum port-receive-state-machine {
            description "Trace port receive state machine";
          }
          enum port-role-select-state-machine {
            description "Trace port role selection state machine";
          }
          enum port-role-transit-state-machine {
            description "Trace port role transit state machine";
          }
          enum port-state-transit-state-machine {
            description "Trace port state transit state machine";
          }
          enum port-migration-state-machine {
            description "Trace port migration state machine";
          }
          enum port-transmit-state-machine {
            description "Trace port transmit state machine";
          }
          enum topology-change-state-machine {
            description "Trace topology change state machine";
          }
          enum bridge-detection-state-machine {
            description "Trace Bridge detection state machine";
          }
          enum state-machine-variables {
            description "Trace when state machine variables change";
          }
          enum ppmd {
            description "Trace state and events for ppmd process";
          }
          enum all-failures {
            description "Trace all failure conditions";
          }
          enum all {
            description "Trace all";
          }
        }
      }
      leaf disable {
        description "Disable this trace flag";
        type empty;
      }
    }
  }
  grouping subscription-type {
    leaf link-subscription {
      description "Link bandwidth percentage for RSVP reservation";
      default "100";
      type string;
    }
    leaf ct0 {
      description "Subscription percentage for traffic class 0";
      default "100";
      type string;
    }
    leaf ct1 {
      description "Subscription percentage for traffic class 1";
      default "100";
      type string;
    }
    leaf ct2 {
      description "Subscription percentage for traffic class 2";
      default "100";
      type string;
    }
    leaf ct3 {
      description "Subscription percentage for traffic class 3";
      default "100";
      type string;
    }
    list priority {
      key priority-value;
      ordered-by user;
      description "Subscription percentage for a specific priority";
      leaf priority-value {
        description "Priority for which subscription percent is being configured";
        type union {
          type string {
            pattern "<.*>|$.*";
          }
          type uint32 {
            range "0 .. 7";
          }
        }
      }
      leaf percent {
        description "Subscription percent for the specific priority";
        type string;
      }
    }
  }
  grouping system-id-ip-map {
    leaf name {
      type jt:mac-unicast;
    }
    leaf ip-address {
      description "Peer ID (IP Address)";
      type jt:ipv4prefix;
    }
  }
  grouping te-class-object {
    leaf traffic-class {
      description "Traffic class";
      type enumeration {
        enum ct0 {
          description "Traffic class 0";
        }
        enum ct1 {
          description "Traffic class 1";
        }
        enum ct2 {
          description "Traffic class 2";
        }
        enum ct3 {
          description "Traffic class 3";
        }
      }
    }
    leaf priority {
      description "Preemption priority for this class";
      type union {
        type string {
          pattern "<.*>|$.*";
        }
        type uint32 {
          range "0 .. 7";
        }
      }
    }
  }
  grouping timingd-traceoptions {
    description "Trace options for PTP stack and Servo";
    leaf no-remote-trace {
      description "Disable remote tracing";
      type empty;
    }
    container file {
      description "Trace file information";
      leaf filename {
        description "Name of file in which to write trace information";
        type string {
          length "1 .. 1024";
        }
      }
      leaf size {
        description "Maximum trace file size";
        type string;
      }
      leaf files {
        description "Maximum number of trace files";
        default "3";
        type union {
          type string {
            pattern "<.*>|$.*";
          }
          type uint32 {
            range "2 .. 1000";
          }
        }
      }
      choice world-readable-choice {
        leaf world-readable {
          description "Allow any user to read the log file";
          type empty;
        }
        leaf no-world-readable {
          description "Don't allow any user to read the log file";
          type empty;
        }
      }
      leaf match {
        description "Regular expression for lines to be logged";
        type jt:regular-expression;
      }
    }
    leaf level {
      description "Level of debugging output";
      default "error";
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
    }
    list flag {
      key name;
      ordered-by user;
      description "Tracing parameters";
      leaf name {
        type enumeration {
          enum init {
            description "Trace daemon start-up related events";
          }
          enum routing-socket {
            description "Trace routing-socket events";
          }
          enum ipc {
            description "Trace IPC messages";
          }
          enum configuration {
            description "Trace configuration events";
          }
          enum timer {
            description "Trace Timer events";
          }
          enum event {
            description "Trace generic events";
          }
          enum ptp-bmc {
            description "Trace PTP BMC messages";
          }
          enum ptp-tp {
            description "Trace PTP telecom profile messages";
          }
          enum ptp-sig {
            description "Trace PTP signalling messages";
          }
          enum ptp-mgmt {
            description "Trace PTP management messages";
          }
          enum ptp-servo {
            description "Trace PTP servo messages";
          }
          enum ptp-config {
            description "Trace PTP config messages";
          }
          enum ptp-announce {
            description "Trace PTP announce messages";
          }
          enum ptp-sync {
            description "Trace PTP sync messages";
          }
          enum ptp-delay-req {
            description "Trace PTP delay-req messages";
          }
          enum ptp-delay-resp {
            description "Trace PTP delay-resp messages";
          }
          enum ptp-sig-announce {
            description "Trace PTP sig-announce messages";
          }
          enum ptp-sig-sync {
            description "Trace PTP sig-sync messages";
          }
          enum ptp-sig-delay {
            description "Trace PTP sig-delay messages";
          }
          enum ptp-tie {
            description "Trace PTP TIE messages";
          }
          enum ptp-tc {
            description "Trace PTP TC messages";
          }
          enum ptp-learned-sl {
            description "Trace PTP learned slaves messages";
          }
          enum pkt-io {
            description "Trace PTP packet IO";
          }
          enum all {
            description "Trace everything";
          }
        }
      }
    }
  }
}
