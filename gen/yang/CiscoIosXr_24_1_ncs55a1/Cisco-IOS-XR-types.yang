module Cisco-IOS-XR-types {
  namespace "http://cisco.com/ns/yang/cisco-xr-types";
  prefix xr;

  import cisco-semver {
    prefix semver;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of IOS-XR derived YANG data
     types.
     
     Copyright (c) 2013-2021 by Cisco Systems, Inc.
     All rights reserved.";

  revision 2023-12-06 {
    description
      "Modified string match pattern of Node-id
       2022-03-09
         Included space in Cisco-ios-xr-string pattern.
       2021-10-19
         Added a new type Hex-long-integer";
    semver:module-version "2.2.0";
  }
  revision 2020-11-18 {
    description
      "Added a new type Hex-integer-8";
    semver:module-version "2.1.0";
  }
  revision 2019-12-03 {
    description
      "Modified string match pattern of Interface-name";
    semver:module-version "2.0.0";
  }
  revision 2019-04-05 {
    description
      "Establish semantic version baseline.";
    semver:module-version "1.0.0";
  }
  revision 2019-01-18 {
    description
      "This revision adds the following new data types:
       - Type10-password";
  }
  revision 2018-06-29 {
    description
      "Modified string match pattern of Interface-name";
  }
  revision 2017-12-01 {
    description
      "Modified string match pattern of Tty-escape-char-num";
  }
  revision 2017-03-07 {
    description
      "This revision adds the following new data types:
       - Type8-password
       - Type9-password";
  }
  revision 2015-06-29 {
    description
      "This revision adds the following new data types:
       - Rpl-policy
       - Rpl-set";
  }
  revision 2015-05-18 {
    description
      "Updated Node-id string pattern to match also shorter ncs4k
         node names.";
  }
  revision 2015-01-19 {
    description
      "This revision adds the following new data types:
       - Bgp-ipv4-flowspec-address
       - Bgp-ipv6-flowspec-address";
  }
  revision 2013-07-22 {
    description
      "Initial revision.";
  }

  typedef Interface-name {
    type string {
      pattern "[a-zA-Z0-9.:_/-]+";
    }
    description
      "An interface name specifying an interface type and
       instance.
       Interface represents a string defining an interface
       type and instance, e.g. MgmtEth0/4/CPU1/0 or
       TenGigE0/2/0/0.2 or Bundle-Ether9 or
       Bundle-Ether9.98 or Serial0/0/0/0/3/1:1";
  }

  typedef Controller-name {
    type string {
      pattern "[a-zA-Z0-9.:_/-]+";
    }
    description
      "A controller name specifying a controller type and
       instance.
       Controller represents a string defining a controller
       type and instance, e.g. dwdm0/4/0/0 or
       GigabitEthCtrlr0/2/0/0 or T10/0/0/0";
  }

  typedef Cisco-ios-xr-string {
    type string {
      pattern "[\\w\\-\\.:,_@#%$\\+=\\| ;]+";
    }
    description
      "Special characters are not allowed.";
  }

  typedef Ipv6-prefix-length {
    type uint8 {
      range "0..128";
    }
    description
      "An IPv6 address prefix length.
       Must lie between 0 and 32 inclusive.";
  }

  typedef Node-id {
    type string {
      pattern "([a-zA-Z0-9_]*\\d+/){1,2}([a-zA-Z0-9_]*\\d*)";
    }
    description
      "A location used as value information.";
  }

  typedef Pq-node-id {
    type string {
      pattern "((([a-zA-Z0-9_]*\\d+)|(\\*))/){2}(([a-zA-Z0-9_]*\\d+)|(\\*))";
    }
    description
      "Partially qualified location which is used for
       wildcarding location specifications, e.g. 1/*/*";
  }

  typedef Vpn-id {
    type string {
      pattern "([0-9a-f]{1,8}):([0-9a-f]{1,8})" {
        description
          "VPN ID format (OUI:VPN-Index in hex integer)";
      }
    }
    description
      "VPN ID format (OUI:VPN-Index in hex integer)";
  }
}
